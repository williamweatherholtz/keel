// =====================================================================
// EngineGuardConstraints — each PROCESS-BOUND guard as a base SysML v2 `constraint def` (D0139(D)).
//
// WHY THIS EXISTS. CLAUDE.md §1.7 already holds that "the guards ARE the constraint layer", so a
// Process asserting the constraints it enforces is base SysML v2 stating exactly what the engine means.
// Until now that mapping lived in `.engine/contracts/process-units.toml` — a table no `keel show trace`,
// declared view or viewpoint could reach, so an ENGINE FACT sat outside the model that is supposed to
// hold every engine fact.
//
// HOW IT IS READ. A process unit is a FILE in `.engine/processes/`. Its guards are the union of
// `assert constraint <member> : <ConstraintDef>;` across every `Process` part in that file — so an
// assert lands on the specific phase or step that enforces it (ceremony on the sprint phases, retro
// backlog on the retrospective) rather than on a file-level list. That is strictly more informative
// than the TOML it replaces.
//
// NAMING. Each constraint def is the camelCase form of its guard name; the binary lowercases and
// hyphenates to recover `sprint-coverage` from `sprintCoverage`. One mechanical rule, no lookup table
// to drift.
//
// CORE guards are deliberately ABSENT — identity, provenance, vocabulary, rootedness, well-formedness
// always run and belong to no process (D0138). Adding one here would make it deactivatable, which is
// the sanctioned-bypass failure D0138 exists to prevent.
// =====================================================================
package EngineGuardConstraints {

    // agile-workflow
    constraint def ceremony;
    constraint def sprintCoverage;
    constraint def retroBacklog;
    constraint def priorityInversion;
    constraint def verificationTrace;

    // decision-authoring
    constraint def decisionRationale;
    constraint def acceptanceEvents;
    constraint def decisionRequirementLink;
    constraint def attestationSubstance;
    constraint def confirmationAuthenticity;

    // issue-resolution
    constraint def issues;

    // element-critique
    constraint def criticIndependence;

    // render
    constraint def viewpointRenderer;

    // doc-sync
    constraint def docSync;

    // D0191: the admitted-gap guards, unit-owned by deploy and actor-enrollment.
    constraint def releaseRecorded;
    constraint def enrollmentBinding;
    // D0195 clause 1 (panel R1, aerospace flip 2): EVERY enforced guard has a constraint-def
    // identity, not only the unit-owned ones - the model identity the control map and any
    // future unit-ownership declaration binds to. Names are the guards' camelCased kebab names.
    constraint def actors;
    constraint def charter;
    constraint def processChange;
    constraint def manifestCoverage;
    constraint def processSkill;
    constraint def requirementRootedness;
    constraint def markerVocabulary;
    constraint def duplicateIdentity;
    constraint def engineLint;
    constraint def hookConfigIntegrity;
    constraint def activationManifest;
    constraint def sequenceMultiplicity;
    constraint def parserCoverage;
    constraint def baseFirstJustification;
    constraint def edgeEndpoints;
    constraint def ownership;
    constraint def attestationAuthority;
    constraint def typeCollision;
    constraint def attributeVocabulary;
    constraint def resolverKind;
    constraint def staleGateProse;
    constraint def impossibleEvidenceDate;
    constraint def identityPresent;
    constraint def identityWellFormed;
    constraint def toolReference;
    constraint def scaffoldPlaceholder;
    constraint def claudeSurfaceDrift;
    constraint def decisionScaffolding;
    constraint def controlEventCoverage;
    constraint def questionCoverage;      // guard 46 (D0161): declared knowledge facts are well-formed
    constraint def claimAncestry;         // guard 47 (issue229): claimedAt bounded by its introducing commit
    constraint def judgmentRequestQuality; // guard 48 (D0207): a fork decision must earn the ask
    // D0302 (issue370): twelve guards had NO constraint-def identity although this file's own rule
    // (D0195 clause 1, above) says every enforced guard has one - eight of them from before guard 49,
    // found when the vintage fixture needed a constraint the current rules define and an older
    // release does not. Named here so the control map, a unit's assert, and the K8 handshake all
    // have the identity to bind to.
    constraint def evidenceCited;
    constraint def gatingWorkflowHistory;
    constraint def processApplicability;
    constraint def docGuardCount;
    constraint def manifestKeyPortability;
    constraint def controlMapReconciled;
    constraint def sprintClosure;           // guard 55 (D0260); D0515 widens it to the Story's #Delivers targets
    constraint def untrustedRouting;
    constraint def controlDefectRegistry;
    constraint def cliSurfaceDeclared;      // guard 58 (D0271/D0283)
    constraint def decisionAmendsProcess;   // guard 59 (D0297), warning-tier
    constraint def unitExtrasPresent;       // guard 60 (D0300)
    constraint def acceptanceBindsToText;   // guard 61 (D0308): the text signed is the text carried
    constraint def stpaCurrency;            // guard 62 (D0313), warning-tier: the computed control structure says when STPA must run again
    constraint def untrustedTaint;          // guard 63 (D0314): the untrusted label travels through derivation to every sink
    constraint def gateEnvironmentParity;   // guard 64 (D0358, issue385): two workflows running the same gate supply the same environment
    constraint def instrumentsDeclared;     // guard 65 (D0361): every measurement instrument is declared, and every declaration resolves
    constraint def releaseChecksumsPublished; // guard 66 (D0385): a workflow that publishes release assets hashes them and publishes the hash
    constraint def wrapperPinChecksummed;   // guard 67 (D0385), warning-tier: the pinned engine has a wrapper checksum for every asset keelw can download
    constraint def planCoversStep;          // guard 68 (D0396): a PLAN-COVERED acceptance still holds its plan's three clauses against the tree
    constraint def idIsAUuid;               // guard 69 (D0430/issue454): an id dated on/after 2026-09-10, or on a line added in the working tree, is an RFC 4122 v4 UUID; earlier failures are history, counted by class
    constraint def stepCheckResolves;       // guard 70 (D0434, D0321 option A): a ProcessStep's checkedBy names a guard or declared rule that runs; a ghost or empty name is EHZ5
    constraint def consentScope;            // guard 71 (D0439/issue460): an AUTO-ACCEPTED Decision carries no marker part (from 2026-09-06) and its text names no marker word without NOT A PROCESS CHANGE (from 2026-09-10); earlier hits are history, counted
    constraint def workingTreeEol;          // guard 72 (issue478): every tracked path whose .gitattributes declares eol=lf or eol=crlf holds that ending in the working copy (git ls-files --eol, w/ vs attr/); text=auto and undeclared paths are not judged; suite --touched and land refuse on the same census
    constraint def cliReference;            // guard 74 (D0471/issue528): every `keel <verb>` a living doc names (processes, skills, docs, contracts, workflows, rules, CLAUDE.md, the output style; in code always, in prose when it carries a flag or a root) is a command this binary dispatches, and after a router or `show` a declared sub-verb or lens; a retired verb names the spelling that exists today
    constraint def directionCited;          // guard 73 (D0463/issue428): a Decision field or task DoD dated on/after 2026-09-12 that quotes the human (their words / the human's words / the human, YYYY-MM-DD, then a quoted span) reaches by DerivedFrom a Statement whose text holds the span verbatim; earlier citing Decisions and undated DoDs (issue513) are history, counted
    constraint def customHarnessRouted;     // guard 75 (issue542/D0475): every `harness = false` test target of every workspace member is, in every workflow that runs `cargo nextest run`, excluded from nextest and run under `cargo test -p <crate> --test <name>`, and nothing is routed that no manifest declares - the split is DERIVED from the manifests, so a new cucumber binary in any crate fails here before nextest dies at `--list` on ubuntu (CI concluded failure at 1e2ed25 and 593147c on keel-parser's four).
    constraint def sourceReference;         // guard 76 (D0514/issue591): every `file.rs:N[-M]` citation on the living doc surface names a file under a workspace member's src/ (a bare basename only when one file bears it), a range of its lines, and holds the identifier cited beside it within that range; red names the doc line and the identifier's line today; a root with no Cargo.toml scans nothing
    constraint def sittingReviewMethod;     // guard 77 (D0510/issue597): a Test named `sittingRev*` or titled a sitting review that carries method = confirmation and is not among the `verification` names present at D0510's introduction commit; the pre-D0510 ones are one counted HISTORY line; an unresolved boundary warns and forwards every match

}
