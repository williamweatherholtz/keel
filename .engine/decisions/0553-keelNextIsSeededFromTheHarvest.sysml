// D0553 (status: the `status` field below is the truth) — keelNextIsSeededFromTheHarvest: the next keel starts as a separate repository seeded with the knowledge harvest and the engine at its 0.5.1 pin, and this repository stays the engine's home
// Recorded via `keel record decision` (D0105 RMWX axis; issue054). Acceptance is a separate explicit
// human gate (method=confirmation, D0106): flip status + add the d0553Accept event on sign-off.
package Decision0553 {
    private import EngineElement::*;
    private import EngineWork::*;
    private import EngineVerification::*;
    private import EngineRelationships::*;

    part d0553 : Decision {
        :>> id = "852ee47f-b916-4f35-a65a-fc61e4aa8ad9";
        :>> title = "keelNextIsSeededFromTheHarvest: the next keel starts as a separate repository seeded with the knowledge harvest and the engine at its 0.5.1 pin, and this repository stays the engine's home";
        :>> createdAt = "2026-09-22";
        :>> createdBy = "claudeFable5";
        :>> status = DecisionStatus::accepted;
        :>> context = "The human, 2026-09-22 (st196): 'Ok I want to make a separate project and kickoff a new version of keel that aligns with this new direction. More than a fork, a different idea. But we've done a ton here, I might end up liking it better anyway, etc. But for now I want a hard split. Do a panel to prep all the critical knowlrdge. pointing out the most valuable directors we've gone in keel, most valuable processes, lessons learned from mistakes, critical insights and direction with keel, not able research and ideal next build specs, etc. etc. We'll seed the new project with this (and probably with keel itself), so make it easy to decouple eventually.' D0549 was accepted as OPTION B on those words: a separate project now, adopting the engine as a downstream, with two backlogs from the first day. Six read-only lens agents harvested the tree in parallel - directions, processes and skills, lessons with their controls, insights and design inputs, the next-build feature candidates with a Need, use case, requirement and component scaffold, and the code architecture with its adoption and removal steps - and the assembled record is docs/reviews/keel-next-handoff-2026-09-22.md with every lens report appended verbatim. No list of fifteen key features exists in this tree; the harvest derives twenty candidates and marks them as candidates for the human to confirm, strike or add.";
        :>> decision = "The next keel lives in the sibling repository keel-next, scaffolded by keel init at the 0.5.1 pin with a strict profile, its own git history from an empty root, and its own Decisions from D0001. It is seeded with the harvest as SysML text under its own .tracking - ten of the human's Statements copied verbatim with their ids, fourteen Needs derived from them, twelve use cases, twenty-six system requirements and fourteen components - and with a HANDOFF.md naming what came from keel and the one change that removes it. This repository remains the engine's home and the harvest's record; it authors nothing about keel-next's work beyond this Decision and the sprint that delivered the seed. NOT A FORK: the human chose the split and the seed in their own words, and D0549 carries the choice; this Decision records the harvest and the seed's shape. NOT A PROCESS CHANGE: no workflow, gate, schema or rule of this repository changes; the process used was the spike shape of D0187 with read-only lenses, as for the two landscapes before it.";
        :>> rationale = "A hard split with a seed keeps the facts the human called best-in-class - computed state, typed edges, Decisions, verbatim acceptance, the guard set - as a versioned dependency with a removal path, while a fork would make every later divergence a merge problem and carry this history as the new project's own. The harvest is recorded here because the six lens reports are facts about this tree, and D0196 asks that a knowledge spike be replicable from its record. The scaffold is recorded there because those are the new project's own facts and are edited there, never here.";
        :>> consequences = "Two backlogs from today; work on the harness is planned in keel-next and this tree's frontier no longer carries it. The two held forks D0546 and D0548 are inherited by keel-next as open questions; their acceptance, if it comes, is recorded here and read there. The feedback channel from keel-next to this engine is a downstream report through GitHub intake, the only channel the migration process names. The knowledge record .tracking/knowledge/keel-next-handoff-2026-09-22.sysml carries the replication text.";
    }

    // acceptance event (D0121 review-queue sign-off; D0066/D0106 — human-judged, not fabricated)
    verification d0553Accept : Test { :>> id = "aa69b088-7f29-449d-b28e-8f7da7b1160c"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0553AcceptR1 : TestResult { :>> id = "b4c588b7-315f-4688-b959-f4d7763d39a3"; :>> outcome = VerdictKind::pass; :>> judgedAgainst = "bfc654d5"; :>> judgedAt = "2026-09-22"; :>> judgedBy = "wweatherholtz"; :>> createdBy = "claudeFable5"; }
}
