// D0506 (status: the `status` field below is the truth) — The content key and the no-receipt predicate leave the guard member so the build-and-test tooling depends on no view and no guard
// Recorded via `keel record decision` (D0105 RMWX axis; issue054). Acceptance is a separate explicit
// human gate (method=confirmation, D0106): flip status + add the d0506Accept event on sign-off.
package Decision0506 {
    private import EngineElement::*;
    private import EngineWork::*;
    private import EngineVerification::*;
    private import EngineRelationships::*;

    // #ProspectiveChange (D0070) - this Decision governs a process/schema change; the co-committed
    // change rides the process-change guard's hard lock.
    #ProspectiveChange part d0506 : Decision {
        :>> id = "146ca3ad-ff80-4d9d-af70-70a590ce257d";
        :>> title = "The content key and the no-receipt predicate leave the guard member so the build-and-test tooling depends on no view and no guard";
        :>> createdAt = "2026-09-17";
        :>> createdBy = "claudeFable5";
        :>> status = DecisionStatus::accepted;
        :>> context = "Sprint 735 (dcSuiteIsAMember, chartered by D0479) moves suite.rs, touched.rs, verify.rs and hook_binary.rs out of keel-cli into members/keel-suite. Its DoD names the member's dependencies as leaves, keel-write and keel-guards' receipt module, and its known-positive as an edit to view/mod.rs leaving keel-suite Fresh. The two cannot both hold: keel-guards depends on keel-view (the guards read the views they check), so a crate depending on keel-guards is rebuilt on every view edit. touched.rs's only use of the guard member is contentkey (the D0474 content key: the code fingerprint a test binary is keyed on), and the three receipt writers' only use of receipt.rs is fn forced, the --no-receipt / KEEL_NO_RECEIPT predicate. Both files sit under members/keel-guards/src/, a GUARD_SOURCE_DIRS entry (enforcement.rs:71) since sprint 733, so removing pub mod contentkey from the guard member's lib.rs and replacing the body of forced meet the process-change lock, which refuses the commit without a co-committed marked Decision (D0209 clause 2, D0465). D0479 charters the sprint but carries no marker, so this Decision is the first door.";
        :>> decision = "The probe is the contract. contentkey.rs moves whole into members/keel-suite (it is the touched set's key, not a guard: no guard reads it, and its own text already named keel_git::gitx), and keel_guards::contentkey is re-exported from keel-cli's lib.rs as keel_suite::contentkey so every crate::contentkey path resolves. The --no-receipt predicate descends to keel_fs::fsx::no_receipt_forced, one line of logic unchanged (the flag in argv, or KEEL_NO_RECEIPT=1 in the environment), and keel_guards::receipt::forced becomes pub use keel_fs::fsx::no_receipt_forced as forced, so every guard caller keeps its name. keel-suite therefore depends on keel-fs, keel-git, keel-actor, keel-model and keel-perf only: on no view, no guard and not on keel-write, whose write_atomic is keel-fs's fact re-exported. Under members/keel-guards/src/ the only edits are the removed module line in lib.rs and the re-export replacing forced's body in receipt.rs; no guard's predicate, dispatch, severity, family table or gate set changes.";
        :>> rationale = "A tooling crate that depends on the guards is rebuilt whenever a view changes, which is most edits, and the extraction then buys nothing for the ladder's own binaries - the DoD's known-positive was written to refuse exactly that outcome, and when a DoD's prose and its probe disagree the probe is what the sprint is held to (sprint 734's retro reads the same rule for its counts). The two facts that tied the tooling to the guards were misfiled, not shared: the content key was authored in the guard member because keel-guards was the only member below keel-cli at the time, and forced lived in receipt.rs because the guard receipt was the first receipt. Placing each where its readers are is the D0479 rule itself. The lock fires on the path, not the logic, by design (D0209 clause 2; D0505 records the same reading for a test-only edit), so the honest response is this marked record saying what the two edits are, not a route around it that leaves keel-suite depending on keel-guards for one predicate.";
        :>> consequences = "keel-guards loses a module that was never a guard and re-exports one predicate it used to own; keel show guards, keel version's guard count (75: 66 hard-blocking, 9 warning-only) and keel --help are unchanged, read back byte-for-byte against the pre-move render. The receipt writers' census in verify.rs widens from keel-cli/src to every crate's src, so a fourth receipt planted in any member is named. Known-positive, chosen before the tree is read: touching members/keel-view/src/view/mod.rs leaves keel-suite Fresh under cargo build --release --verbose while keel-view, keel-guards and keel-cli recompile. Known-negative: a receipt writer with an outcome and no running form planted under a member's src makes the census red naming the file. Wrong if a future guard comes to need the content key or the predicate from keel-guards' side: keel-guards may depend on keel-fs already and on keel-suite never (layering), so the predicate is reachable and the key would have to be re-homed below both. NOT A FORK: the alternative, keeping keel-suite on keel-guards, fails the sprint's own probe.";
    }
    #DependsOn dependency from d0506 to d0479;
    #DependsOn dependency from d0506 to d0504;

    // acceptance event (D0121 review-queue sign-off; D0066/D0106 — human-judged, not fabricated)
    verification d0506Accept : Test { :>> id = "3815d5cd-01b7-49ec-addc-6ff27d2d8dc5"; :>> method = VerificationMethod::confirmation; :>> procedureText = "recorded from chat - their words, verbatim: “Accept all decisions as recommended. Proceed to release and fix downstream” WARN: read-back - the quoted words do not name d0506 (D0201 B); recorded as given (D0423)."; }
    part d0506AcceptR1 : TestResult { :>> id = "75b2a8a7-dbb3-42ca-8919-bbd4b52f08ea"; :>> outcome = VerdictKind::pass; :>> judgedAgainst = "4d00c1bc"; :>> judgedAt = "2026-09-18"; :>> judgedBy = "wweatherholtz"; :>> createdBy = "claudeFable5"; }
}
