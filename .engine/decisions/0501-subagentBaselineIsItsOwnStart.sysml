// D0501 (status: the `status` field below is the truth) — A subagent is gated against the tree at its OWN start - the subagent-stop hook reads the fingerprint written when that agent began (SubagentStart, else its first fire), and falls back to the session's first-fire baseline only for an agent no fire named
// Recorded via `keel record decision` (D0105 RMWX axis; issue054). Acceptance is a separate explicit
// human gate (method=confirmation, D0106): flip status + add the d0501Accept event on sign-off.
package Decision0501 {
    private import EngineElement::*;
    private import EngineWork::*;
    private import EngineVerification::*;
    private import EngineRelationships::*;

    // #SafetyChange (D0070) - this Decision governs a process/schema change; the co-committed
    // change rides the process-change guard's hard lock.
    #SafetyChange part d0501 : Decision {
        :>> id = "98acd3b9-39ec-4a8c-8c8c-7b6f63bdce89";
        :>> title = "A subagent is gated against the tree at its OWN start - the subagent-stop hook reads the fingerprint written when that agent began (SubagentStart, else its first fire), and falls back to the session's first-fire baseline only for an agent no fire named";
        :>> createdAt = "2026-09-16";
        :>> createdBy = "claudeFable5";
        :>> status = DecisionStatus::accepted;
        :>> context = "The subagent-stop hook (D0174/P0.6) gates a stopping subagent only when the tree changed during its lifetime, and it measures that change against ONE fingerprint per session: the tree at the session's first hook fire (main.rs hook_subagent_stop reads baseline-{session}.fp). A session's first fire is hours before most subagents start. Any edit the PRIMARY made in between - a retro placeholder, a half-filled record - is a difference the hook attributes to the subagent, so a subagent that wrote nothing is gated over a tree it never touched and, when that tree is red, blocked with the turn gate's instruction to make it green (issue578: sprint 730's verifier, six blocks, 16:38 to 16:41, hooks.jsonl). Claude Code fires SubagentStart when an agent is spawned and every hook fired inside a subagent carries agent_id and agent_type (hooks reference, 2.1.270), so the tree at the agent's own start is observable and was simply never recorded.";
        :>> decision = "The dispatcher writes agent-{agent_id}.fp under .keel/metrics on the first fire that carries an agent_id and is not that agent's stop - SubagentStart when the harness fires it, else the agent's first tool fire - and never overwrites it. hook_subagent_stop compares the tree at stop against that agent's own start fingerprint when one exists; the session baseline is read only for a stop payload that names no agent_id or whose agent left no start file. The gate itself is unchanged: an agent whose own fingerprint did not move pays nothing, one whose fingerprint moved is gated over the tree as it is. The hook registration gains SubagentStart in the one home keel sync-claude renders from (claude_surface.rs keel_hooks), and the event is a counted control event (control-events.toml, guards.rs EMITTED_LEDGER).";
        :>> rationale = "A control that measures the wrong interval blocks the wrong actor. The session baseline was chosen when the only subagents were the primary's own short forks and the tree between session start and subagent start was assumed still; delegated ceremony (D0425) broke that assumption by design - the verifier is dispatched INTO a tree the primary is mid-way through changing. Baselining at the agent's own start restores the hook's stated meaning, gate ONLY when the tree changed during the subagent's lifetime, without weakening it for an agent that did write. The fallback to the session baseline keeps the pre-2.1.270 payload shape gated rather than silently ungated. This is a safety change: the subagent-stop hook is a hazard control (ctlTurnBoundaryGate) and its measurement interval moves. NOT A FORK: the interval an agent is accountable for is its own lifetime by the hook's own doc comment; no alternative was weighed.";
        :>> consequences = "main.rs cmd_hook writes agent-{id}.fp beside baseline-{session}.fp; hook_subagent_stop resolves its baseline through one pure function the probe pair pins (own start present and equal - silent; own start present and moved - gate; absent - session baseline as before). claude_surface.rs registers SubagentStart, is_keel_hook recognises it, the six-events test becomes seven. control-events.toml and EMITTED_LEDGER name subagent-start. The event list in cliHook is retired by a #Supersede edge beside it (D0108) and cli_facts.rs agrees. Known-positive, chosen before the tree is read: a stop payload over a tree that differs from the session baseline but not from the agent's own start routes to silent. Known-negative: a stop payload whose own-start fingerprint differs routes to the gate, and one with no agent_id routes to the session baseline exactly as today. Wrong if a subagent's hook fires arrive without agent_id in this harness version - then every agent falls back to the session baseline and issue578 recurs; the ledger's subagent-start count answers that within one dispatch. D0502 stands on this record for the verifier's own control.";
    }

    // acceptance event (D0121 review-queue sign-off; D0066/D0106 — human-judged, not fabricated)
    verification d0501Accept : Test { :>> id = "3c4d15fb-5019-4072-8643-eb08e160196a"; :>> method = VerificationMethod::confirmation; :>> procedureText = "recorded from chat - their words, verbatim: “Accept all decisions as recommended. Proceed to release and fix downstream” WARN: read-back - the quoted words do not name d0501 (D0201 B); recorded as given (D0423)."; }
    part d0501AcceptR1 : TestResult { :>> id = "6e0f9a5b-d270-493c-a128-7a544b03b97e"; :>> outcome = VerdictKind::pass; :>> judgedAgainst = "4d00c1bc"; :>> judgedAt = "2026-09-18"; :>> judgedBy = "wweatherholtz"; :>> createdBy = "claudeFable5"; }

    // grounded (D0098 rootedness): this Decision serves the Need that a pass is never AI testimony alone -
    // st065, the human's words behind the D0425 ceremony line (verifier, recorder, ladder, rendered receipt)
    #DerivedFrom dependency from d0501 to nVerificationByAuthorityAndMethod;
}
