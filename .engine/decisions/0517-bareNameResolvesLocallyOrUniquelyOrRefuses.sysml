// D0517 (status: the `status` field below is the truth) — bareNameResolvesLocallyOrUniquelyOrRefuses: a bare reference resolves to its own package's declaration, else to the one declaration in the model, else REFUSES naming every candidate and its file - the model never picks one of two same-named items silently
// Recorded via `keel record decision` (D0105 RMWX axis; issue054). Acceptance is a separate explicit
// human gate (method=confirmation, D0106): flip status + add the d0517Accept event on sign-off.
package Decision0517 {
    private import EngineElement::*;
    private import EngineWork::*;
    private import EngineVerification::*;
    private import EngineRelationships::*;

    // #ProspectiveChange (D0070) - this Decision governs a process/schema change; the co-committed
    // change rides the process-change guard's hard lock.
    #ProspectiveChange part d0517 : Decision {
        :>> id = "865fbfee-8fa6-4f4f-a976-b25f55f8cc31";
        :>> title = "bareNameResolvesLocallyOrUniquelyOrRefuses: a bare reference resolves to its own package's declaration, else to the one declaration in the model, else REFUSES naming every candidate and its file - the model never picks one of two same-named items silently";
        :>> createdAt = "2026-09-18";
        :>> createdBy = "claudeFable5";
        :>> status = DecisionStatus::accepted;
        :>> context = "GH#85 (st160; untrusted source, D0264 - a downstream project's agent session) demonstrates on a tree keel init created that two packages may declare `part st001`, every gate stays green, and `#DerivedFrom dependency from us001 to st001` written INSIDE the package that declares its own st001 binds to the OTHER file's st001. Read against this tree before triage: members/keel-model/src/model.rs:70 keys `items` by the bare declared name and model.rs:244 inserts last-writer-wins, so a second declaration silently replaces the first for every edge, lens and guard; members/keel-guards/src/identity.rs:309 scopes the duplicate-name check to one package (violation text at :389 reads `in package`), so the guard whose name promises this passes it; CLAUDE.md invariant 3 says `Items never collide on name` and nothing enforces it. MEASURED on this tree, 2026-09-18, by a text scan of part/action/verification/item declarations under .tracking and .engine (reference excluded): 270 names are declared more than once - 243 are gate names declared only in sprint delivery files (asCloseOutGate is declared in sprint241, sprint251 and sprint276; `keel show why asCloseOutGate` answers with sprint276 alone, the other two unreachable by name), and 27 are declared outside or across those, among them `intake`, `migration` and `docSync` declared once as a Process and once as a Skill registry part, and pf51-pf55 in two propriety files. The engine's own tree carries the defect the report found downstream. In the reporting project eleven names collided after a merge of two branches, two SysReq edges point at the wrong UserStory, and guard direction-cited's prescribed fix bound to the wrong Statement, so that guard cannot be discharged by any edge the grammar accepts (a qualified target does not parse: `expected Semicolon, got ColonColon`).";
        :>> decision = "RESEARCH: read before asking. The map by bare name is the identity the whole engine computes over; `unique within a package` was the invariant one guard checked, never one the code kept. OPTION A (recommended): resolution follows the language. The model build keeps EVERY declaration (no replacement), and a bare reference resolves in this order - a declaration in the referencing package; else the single declaration anywhere in the model; else the build REFUSES the reference naming every candidate with its file and line, so no lens answers over a silent pick. A qualified `Package::name` target parses and resolves to that package's declaration, so an author the refusal stops has a way to say which item they mean (the reporter's fix 3; us116). duplicate-identity's per-package name scan is unchanged - a same-named part in two packages is legal, as in SysML - and a WARNING row names each cross-package duplicate so the 270 here are visible, not gated. COST: the model's item key changes from the bare name to a declaration identity with a resolution step, touching every member that reads `items` by name; a parser and resolver change for the qualified target; a D0388 pair (two packages, one name, a cross-package bare edge refused naming both; the same edge written inside the declaring package resolves locally). The 270 engine-tree duplicates need no migration: a sprint's gates are referenced from their own package. OPTION B: the declared name is unique across the model - duplicate-identity's scan drops the per-package key and reports a second declaration anywhere as a VIOLATION, and the build refuses a duplicate. COST: a migration renaming 270 declarations across every reference in this tree (243 sprint gates, with their `<gate>R<n>` results) under D0067 control totals before the guard can harden, and every downstream tree that reused a gate or process name goes red on the same day; no qualified target needed. The merge-time renumbering automaton (the reporter's fix 4) is adopted under neither: under A the merged tree's cross-package bare edges refuse naming both declarations, under B the land gate goes red, and the rename is the author's migration.";
        :>> rationale = "The report's own repro is an edge written inside the package that declares the name it uses, and it bound elsewhere - that is a resolution defect before it is a uniqueness defect, and the language already says what the right answer is: local first, then unique, then ambiguous. OPTION A makes the engine compute what the text means and turns the silent pick into a refusal that names the candidates, which is the one control that helps the author who did NOT notice (the reporter's fix 2); the qualified target is the way out the refusal then requires (fix 3), so the two ride one Decision. OPTION B is cheaper to state and expensive to keep: the measurement shows this tree reuses 247 gate names by design (sprint files are packages; a gate's name is local to its ceremony), and forcing them unique renames history for a property the language does not require. A guard on the name axis (fix 1) is under A the WARNING row, not a violation, because a duplicate is only a defect when something refers to it ambiguously. Refusing at the model build rather than at a guard matters because the build is what every lens and every guard read; a guard alone leaves `why`, `trace` and coverage answering over a collapsed map between the write and the next guard run.";
        :>> consequences = "Under A: keel-model's build keeps all declarations and resolves references locally-then-uniquely-then-refuses; the parser accepts `Package::name` as an edge target; duplicate-identity gains a cross-package WARNING row (270 here today, asserted by its test); `keel show why <name>` answers for every declaration, not the last read; a downstream tree carrying a mis-bound bare edge goes red at its next build naming both candidates, which is the intended loud failure; CLAUDE.md invariant 3 is reworded to the rule the engine keeps (a bare name is unambiguous where it is used). GH#85 is answered on GitHub with the tracked ids once this record's status is known. HELD proposed under D0337 for the human's word: a build refusal is an enforcement change (D0209 cl.2) and the source is untrusted (D0264), so nothing is implemented before acceptance; the delivering item is dcBareNameResolvesLocallyOrUniquelyOrRefuses and issue605's resolution is computed from its #Resolves edge.";
    }

    // acceptance event (D0121 review-queue sign-off; D0066/D0106 — human-judged, not fabricated)
    verification d0517Accept : Test { :>> id = "e3f119f2-6d8a-4a25-a284-7f896a80c65c"; :>> method = VerificationMethod::confirmation; :>> procedureText = "OPTION A chosen (the recommended option; the brief's verdict was A on both forks) - their words, verbatim: “Accept all decisions as recommended. Proceed to release and fix downstream” WARN: read-back - the quoted words do not name d0517 (D0201 B); recorded as given (D0423)."; }
    part d0517AcceptR1 : TestResult { :>> id = "5bdf0b89-faee-403e-b3fd-bd8e9f27b150"; :>> outcome = VerdictKind::pass; :>> judgedAgainst = "4d00c1bc"; :>> judgedAt = "2026-09-18"; :>> judgedBy = "wweatherholtz"; :>> createdBy = "claudeFable5"; }
}
