// D0469 (status: the `status` field below is the truth) — gateDecisionCarriesItsMeasuredCost: a proposed process-change Decision that names the land or push path carries a MEASURED: token in its rationale - the run, the host, the seconds on a live set - or decision-scaffolding warns naming it
// Recorded via `keel record decision` (D0105 RMWX axis; issue054). Acceptance is a separate explicit
// human gate (method=confirmation, D0106): flip status + add the d0469Accept event on sign-off.
package Decision0469 {
    private import EngineElement::*;
    private import EngineWork::*;
    private import EngineVerification::*;
    private import EngineRelationships::*;

    // RESEARCH: issue444 (D0421 proposed at the fixture's price - 'about two seconds' - and the first live set cost 528 s, 90 percent of the suite the human withdrew for cost under D0356). D0388: a figure stated before the check that would establish it is the recurrence class; a KEPT check carries its known positive and negative. D0308: acceptance binds to text, so the text the human accepts must hold the cost. D0337: a process-change Decision is held proposed and the control it adds is inert until a human accepts it. D0188/D0303: decision-scaffolding is the guard that already reads every marked Decision. The live tree on 2026-09-13 holds five proposed marked Decisions (d0376, d0461, d0463, d0467, d0468); one names a path word (d0467, 'gate').
    // #ProspectiveChange (D0070) - this Decision governs a process/schema change; the co-committed
    // change rides the process-change guard's hard lock.
    #ProspectiveChange part d0469 : Decision {
        :>> id = "cbd3f0f1-8911-4d3a-a5ed-4225498fe2e4";
        :>> title = "gateDecisionCarriesItsMeasuredCost: a proposed process-change Decision that names the land or push path carries a MEASURED: token in its rationale - the run, the host, the seconds on a live set - or decision-scaffolding warns naming it";
        :>> createdAt = "2026-09-13";
        :>> createdBy = "claudeFable5";
        :>> status = DecisionStatus::accepted;
        :>> context = "issue444: D0421 asked the human to accept a refusal on the land path priced from its fixture - one binary, about two seconds - and was never run on a live set before the ask. The first live set named 15 binaries plus the lib and cost 528 s wall on this host, against the 585 s of the full suite the human had withdrawn for cost. dcTouchedCostIsMeasuredNotQuoted corrected D0421's text (its rationale carries MEASURED: 5fbe410, 528 s); dcGateDecisionCarriesItsMeasuredCost asks for the control that keeps the class from recurring: the guard that already reads every marked Decision reads whether one that names the land or push path prices itself. The rule is a WARNING in decision-scaffolding, not a refusal - it stands between me and the ask, not between the human and their acceptance.";
        :>> decision = "NOT A FORK: the DoD fixed the words, the token and the tier. A PROPOSED #ProspectiveChange Decision whose decision text names land, push, refuse or gate as a whole word in any case carries a MEASURED: token in its rationale - the run it was measured on, the host and the seconds the control cost on a live set - or the decision-scaffolding guard WARNS naming the Decision and the words it matched. Accepted Decisions are the human's word already and are not read; the rule arms on this Decision's own human acceptance (D0337) and an auto-acceptance confers nothing (D0291).";
        :>> rationale = "The word test is the DoD's four words as whole words and no more: it names the path a refusal would sit on, not the refusal, so a Decision that merely says 'gates nothing' is named while proposed - on the live tree that is d0467, whose text says a retro finding is not a gate - and the remedy is one line of measured cost or the acceptance the Decision is waiting for anyway; a narrower test that read for a refusal verb AND a path noun would have fitted the words to the tree it was checked on, which is the D0388 class this Decision exists to close. A WARNING and not a violation because the asking is mine and the accepting is theirs: a red guard on a proposed Decision would hold the human's queue hostage to my ceremony (D0204). MEASURED: keel gate guard --no-receipt on the working tree at 61bb6a9 plus this change, host 0F3DGVX25193H7, 2026-09-13, three runs each alternating: the binary before the clause 7.6 s median (7.2 / 7.6 / 10.4), the binary holding it 7.3 s median (6.5 / 7.3 / 7.8) - the inert clause costs nothing the run-to-run noise can see. The ARMED path is not measurable before the acceptance that arms it; its shape is one pass over the same corpus lines the candidate loop already walks plus one acceptance_kind read per marked Decision (218 files on this tree), and the first fire after acceptance is the figure that belongs here, read from the ledger phase guard:decision-scaffolding - if it moves the p90 the hook indicator (D0468) surfaces it.";
        :>> consequences = "Held proposed for the human (process-change marker, D0337): until accepted, decision-scaffolding carries the rule and emits nothing from it. Co-committed: the rule and its pure core in keel-cli/src/guards.rs (unmeasured_path_decisions, PATH_WORDS), the D0388 trio as a unit test, the guards.md row. On acceptance the guard names d0467 on the current tree unless it has been accepted or priced by then - that is the honest state of the tree, not a defect of the rule. What would change it: a proposed Decision that adds a refusal on the land or push path without using any of the four words is the word list's gap, and the fix is a fifth word with its own recorded anchor, not a semantic test; a Decision named for a passing mention that the human judges noise twice is the tier's signal to narrow the words by a superseding clause. Recording it discharges obligation7d57a5b8: the stop hook yielded red twice while the guards.rs clause sat in the working tree ahead of this Decision, and the co-committed Decision is the correction the yield named.";
    }

    // acceptance event (D0121 review-queue sign-off; D0066/D0106 — human-judged, not fabricated)
    verification d0469Accept : Test { :>> id = "81639819-c02c-413d-b461-9da3b9e8170b"; :>> method = VerificationMethod::confirmation; :>> procedureText = "Said in chat 2026-09-14 over the twenty-eighth publish of the decision brief, which carried fifteen held asks; one instruction covers the fourteen non-forks, d0469 among them. The fork d0466 is not covered - it needs an option letter and stays held. - their words, verbatim: “Accept all proposals. Proceed to design with needs, etc.” WARN: read-back - the quoted words do not name d0469 (D0201 B); recorded as given (D0423)."; }
    part d0469AcceptR1 : TestResult { :>> id = "05cbcc62-af09-4b89-9fd9-952d2a7353e7"; :>> outcome = VerdictKind::pass; :>> judgedAgainst = "d110d0a"; :>> judgedAt = "2026-09-14"; :>> judgedBy = "wweatherholtz"; :>> createdBy = "claudeFable5"; }
}
