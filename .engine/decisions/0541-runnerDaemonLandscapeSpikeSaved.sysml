// D0541 (status: the `status` field below is the truth) — runnerDaemonLandscapeSpikeSaved: the runner-daemon landscape - the field's practice across 57 tools and protocols and 122 user threads dispositioned against our design - is saved as a spike; no tool is adopted and the design changes the findings force are inputs to the unapproved tool-owns-the-task design, not the backlog
// Recorded via `keel record decision` (D0105 RMWX axis; issue054). Acceptance is a separate explicit
// human gate (method=confirmation, D0106): flip status + add the d0541Accept event on sign-off.
package Decision0541 {
    private import EngineElement::*;
    private import EngineWork::*;
    private import EngineVerification::*;
    private import EngineRelationships::*;

    part d0541 : Decision {
        :>> id = "2fccda4a-c403-4e7c-babd-2604fce17ade";
        :>> title = "runnerDaemonLandscapeSpikeSaved: the runner-daemon landscape - the field's practice across 57 tools and protocols and 122 user threads dispositioned against our design - is saved as a spike; no tool is adopted and the design changes the findings force are inputs to the unapproved tool-owns-the-task design, not the backlog";
        :>> createdAt = "2026-09-21";
        :>> createdBy = "claudeFable5";
        :>> status = DecisionStatus::accepted;
        :>> context = "The human, 2026-09-21 (st188): 'browser only for the user, runner-facing (i.e. CLI, yes?) protocol is fine too. as far as what the runner daemon actually is, etc., do some more research for best practices with existing frameworks, lookup complaints from 50 threads in forums to see user-identified weaknesses of their approach, and let's set ourselves apart.' The runner question was the one D0540 left open: the server never executes, runner daemons claim ready steps under a lease and push harvested outputs with the step's run token, the human's only surface is a browser and the runner-facing surface is a versioned JSON protocol with thin CLI clients. The design is not approved; the brainstorm's HARD-GATE holds. The spike ran as an adversarial-panel-review (D0187) on the sprint 758 shape: five parallel read-only web-enabled lenses with one shared brief and a minimum thread count each, one round, every thread dated, URL-cited and quoted verbatim in at most 25 words, every thread dispositioned against our design as ADDRESSED, VULNERABLE or N/A with a clause why. 122 threads across CI runner daemons, workflow and queue workers, agent-harness runners, cross-cutting complaints about unattended agents, and the runner-facing wire protocols as specified; 67 addressed, 45 vulnerable, 9 not applicable, 1 conditional. Every lens claim about keel's own code was re-checked against source before use and the check is named beside it in the synthesis; one count was corrected there (CLAUDE.md section 4 is 98 lines of working rules, not 40). Reddit and Lobsters were unreachable to every lens; the review says so and keeps every 'not found' the lenses wrote. The external facts are lens-reported and were not re-fetched by the synthesiser.";
        :>> decision = "The spike is saved: docs/reviews/runner-daemon-landscape-2026-09-21.md is the record - what a runner daemon is as a seventeen-row practice table each row naming the tool the practice runs in and the thread it answers, the per-lens tally, ten complaint themes ranked by recurrence with the thread ids behind them, a seventeen-row set-apart table giving per weakness the structural mechanism or the honest statement that the design is vulnerable, what the spike does not do, and the five lens reports appended verbatim with their sources - and this Decision is its charter; the knowledge record .tracking/knowledge/runner-daemon-landscape-2026-09-21.sysml holds the D0196 replication text. No tool or protocol is adopted; Buildkite's Agent API, Temporal's worker-versioning lifecycle and REAPI's execution metadata are shapes to copy, not dependencies. No backlog item is raised against the design, because the design is not approved and an item against an unapproved design would author state ahead of the decision; the design changes the findings force are listed in the consequences as inputs to the next design section, where each enters the draft or is declined with a reason. The one backlog item this spike touches is its own, dcRunnerDaemonLandscapeIsRecorded, which sprint 759 delivers. NOT A FORK: the human asked for research and a differentiation, not a choice between alternatives; the two genuine forks the review surfaces (the unconstrained step in a real checkout; the gate set bound to the frozen meta-process) are stated as forks in the review and left for the design section, not decided here. NOT A PROCESS CHANGE: no workflow, gate, schema or rule moves; the word 'process' above names the software process a runner spawns.";
        :>> rationale = "The finding worth a record is that the field's runners fail at the seams between seven things a daemon must do - enrol, pull, hold under a renewing lease, get a per-job credential, run disposably, report checkably, retire - and that a third of all 122 complaints (35 threads) are one defect: a stored flag standing in for a live fact, whether a Jenkins agent 'online' with no work, an Airflow zombie retried into a duplicate, a Paperclip issue 'bricked' with all liveness paths rejecting, or a Nomad client disconnected and still running its allocations. State computed from a live lease with server-side expiry is the design's founding invariant, so that theme is answered by construction, and the record says so with the thread ids. The second finding is what nobody does: renew the job credential on the heartbeat, so the final report routinely outlives its token (GitLab, Argo, Woodpecker, ARC); kill the child process group on lease loss; give startup its own timeout and failure class; name the blocked host in an egress denial; record claim attempts and refusals where a human can read them; meter human minutes per accepted change. Each is a fact about the work rather than the worker, which is why a work-tracker can hold it and a CI runner cannot, and why saving these as the differentiators is the answer to 'let's set ourselves apart'. The third finding is adversarial and is the reason the review is not a victory lap: the UNCONSTRAINED step in a real checkout with the developer's ambient credentials is precisely the surface behind the loudest destructive-action and rules-govern-nothing threads, and prose working rules a runner cannot enforce are the failure one thread describes as 'read, quoted, governed nothing'. Saving the spike as a record rather than re-deriving it is D0040; the threads are dated because the vendors' responses will move.";
        :>> consequences = "docs/reviews/runner-daemon-landscape-2026-09-21.md exists and names its check date, its epistemic status and its sources; sprint 759 is chartered by this Decision and delivers dcRunnerDaemonLandscapeIsRecorded; the knowledge record carries the replication text with a passing result at HEAD. The findings force these changes to the design draft before it is next presented, each entering the draft or being declined with a reason: an explicit per-process session credential between enrolment and the per-acquire run token; the server dictates lease and heartbeat cadence in the claim response and may revise them on every heartbeat reply; a rejected heartbeat is fatal to the run and never refreshes the lease; the heartbeat is its own cheapest call, in its own process, echoing sent and received timestamps and carrying progress, so a stalled step is distinguished from an expired one; the maximum lease lifetime and the wall-clock deadline are declared properties of the step type, never global caps; the run token is renewed on every accepted heartbeat and the final report is accepted under the token the lease last issued; harvest is a server pull after exit, one write with completion, fenced against an expired or superseded run token; the runner kills the step's process group on lease loss and reports it, and a heartbeat or harvest after expiry is a recorded refusal; startup is a timed phase with its own failure class; the egress proxy's denial names the blocked host; a token and cost ceiling is a mandatory second lease bound per step type, attributed through the proxy; awaiting-human is a step state that is not leasable; the proxy stores the provider-returned model id on the run and a mismatch with the declared model fails the step; version negotiation precedes enrolment with a structured refusal and the daemon never self-updates; retirement is a server state machine (current, ramping, draining, drained) with quiet, terminate and retire-at as heartbeat replies, and an idle runner is told why it is idle; a poison-pill counter stops offering a step re-leased N times and raises an Issue; an unclaimed ready step is a fault after a declared interval; claim attempts and refusals are records the human reads in the browser; enrolment refuses a person's subscription token and takes an organisation key or a federated identity only; sign-off queue depth and human minutes per landed step are computed indicators with a cap that stops assigning new unconstrained steps while the queue is full; sandboxes and worktrees are reaped on lease expiry; the heartbeat carries the daemon's own resource facts and recycling is a declared property. Two forks go to the design section for the human: whether the unconstrained step runs in a scrubbed environment inside a snapshotted worktree or the human states the accepted class of loss in that mode; and whether static analysis and secret scanning are bound gates in the frozen meta-process. Nothing in the engine, the process set or the tracking model changes.";
    }

    // acceptance event (D0121 review-queue sign-off; D0066/D0106 — human-judged, not fabricated)
    verification d0541Accept : Test { :>> id = "92abf9c8-cb32-4944-93d9-dec970c23032"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0541AcceptR1 : TestResult { :>> id = "6a6840d5-fbb9-4c92-b533-bb3992f7ef7e"; :>> outcome = VerdictKind::pass; :>> judgedAgainst = "0bef913f"; :>> judgedAt = "2026-09-21"; :>> judgedBy = "wweatherholtz"; :>> createdBy = "claudeFable5"; }
}
