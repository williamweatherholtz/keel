// D0520 (status: the `status` field below is the truth) — A gate that runs in an adopting project holds the adopter to its own claims; a claim the engine ships is held in the self-build
// Recorded via `keel record decision` (D0105 RMWX axis; issue054). Acceptance is a separate explicit
// human gate (method=confirmation, D0106): flip status + add the d0520Accept event on sign-off.
package Decision0520 {
    private import EngineElement::*;
    private import EngineWork::*;
    private import EngineVerification::*;
    private import EngineRelationships::*;

    // #ProspectiveChange (D0070) - this Decision governs a process/schema change; the co-committed
    // change rides the process-change guard's hard lock.
    #ProspectiveChange part d0520 : Decision {
        :>> id = "fd908d5f-daca-4075-8b5f-f437c6e5c7b4";
        :>> title = "A gate that runs in an adopting project holds the adopter to its own claims; a claim the engine ships is held in the self-build";
        :>> createdAt = "2026-09-18";
        :>> createdBy = "claudeFable5";
        :>> status = DecisionStatus::accepted;
        :>> context = "Three GitHub reports from one downstream migration (GH#88 st164, GH#89 st163, GH#90 st162; public repo, untrusted, D0264), each a guard going red inside `keel migrate` on content the ENGINE shipped, so the run reverted itself and the adopter had no act that could make it green. Read against this tree before triage. (1) guard source-reference (members/keel-guards/src/surface.rs:227) scopes itself by one test, `Cargo.toml` at the root (:228), and then walks every living doc under `.engine/` (living_doc_files, :485) - files the resync deployed verbatim, among them .engine/processes/project-migration.sysml:15 and .engine/skills/project-migration/SKILL.md:10 citing `members/keel-process/src/migrate.rs`, a file only this repository holds; any adopter with a Rust workspace (plotwright) is red, and a scaffold passes only because it has no corpus (0 scanned), which is comfort, not a pass. (2) keel_model::onboard::charter_resolves (members/keel-model/src/onboard.rs:72) resolved a manifest's `charteredBy` against .engine/decisions/ alone while the resync deploys engine Decisions to .engine/reference/decisions/, so the shipped `charteredBy = 'd0226'` was unresolvable in every adopting tree and guard activation-manifest (enforcement.rs:1168) was red. (3) step_engine_resync (migrate.rs) guarded project-owned contracts against OVERWRITE (`is_project_owned_contract && dst.exists()`) but not against ADDITION, so a first-time adopter received parser-coverage-baseline.toml with `skipped = 7` - the engine's own census of its legacy successions - as that project's ratchet; guard parser-coverage totals `.tracking/` and `.engine/` together (identity.rs), so one skipped statement of the adopter's own reads 1 + 7 > 7 and the run reverts. The human's direction, verbatim in st167 and st168: migrate is blocked in many projects, migration should be smooth, make downstream projects whole. The peer session that recorded D0519 authored the code for (2) and (3) in this working tree and handed it to this sprint uncommitted; (1) is authored here.";
        :>> decision = "A guard whose population includes content the engine ships into an adopting project judges that content where the claim is made - in the self-build, where the source it names exists - and holds the adopter only to what the adopter authored or measured. Applied to the three: in a root that is not the self-build (keel_model::corpus::is_self_build), source-reference reads only living docs the embedded engine does not ship - the project's CLAUDE.md and any file the project added under .engine/ - and counts the shipped ones as outside its population, not as passes; the resync never seeds a contract that is a COUNT over the project's own corpus (parser-coverage-baseline.toml) into a project that has none, absence being the stated passing state (D0136); and a manifest's `charteredBy` resolves against .engine/decisions/ and .engine/reference/decisions/ both, a charter naming nothing in either still failing (issue380's property holds).";
        :>> rationale = "A claim is checkable only where its referent is. `members/keel-process/src/migrate.rs:908-911` is a true sentence about this repository and an unresolvable one about plotwright; reading it there and calling the miss a violation is not a stricter gate, it is a gate measuring the wrong tree. The same holds for a count: `skipped = 7` describes a corpus the engine has seen and the adopter has not, so written into the adopter it is a claim nobody made. The alternative shapes were weaker. Skipping every `.engine/` file in every root would blind the self-build to its own drift, which is the defect source-reference exists to catch (issue591: the skill cited a function 141 lines from where it sat). A per-guard exemption list an adopter edits is a flag, and D0519 already rejected the claimable shape for the ownership guard. Distinguishing shipped from authored by the embedded engine's file set is not a flag: it is the engine's own manifest of what it deployed, read the way the resync reads it. The self-build predicate already exists and already gates the suite; reusing it means the two meanings of self-build cannot drift apart.";
        :>> consequences = "Five backlog tasks deliver this sprint (745): dcSourceReferenceReadsTheAdoptersOwnClaims (GH#88, issue612), dcCharterResolvesInBothDecisionDirectories (GH#89, issue611), dcRatchetOverTheProjectsCorpusIsNeverSeeded (GH#90, issue610); D0521 and D0522 carry the other two reports. source-reference's report in an adopting root says how many shipped docs it set aside. Stated residual: a project-owned contract the engine ships a default for (activation.toml) is in the embedded set and so is set aside in an adopter even after the project edits it; a citation the project adds there is unread until the file is one the engine does not ship. The three living-doc citations of check_preconditions move to 908-911 in this same commit because the GH#90 code shifted the function by 25 lines - the guard reddened all three on that unrelated diff, a known-positive for it. GH#88, #89 and #90 are answered on GitHub with the tracked ids once this record's status is known. HELD proposed under D0337 for the human's word and applied under the marker in the same commit, as D0519 was: the human's direction is recorded (st167, st168), the change is a guard-population change (D0209 cl.2), and their word keeps or reverts it.";
    }
    #DerivedFrom dependency from d0520 to st167;
    #DerivedFrom dependency from d0520 to st168;

    // acceptance event (D0121 review-queue sign-off; D0066/D0106 — human-judged, not fabricated)
    verification d0520Accept : Test { :>> id = "fc78c10d-730a-43fd-85c9-17a5e0f74ea4"; :>> method = VerificationMethod::confirmation; :>> procedureText = "recorded from chat - their words, verbatim: “Accept all decisions as recommended. Proceed to release and fix downstream” WARN: read-back - the quoted words do not name d0520 (D0201 B); recorded as given (D0423)."; }
    part d0520AcceptR1 : TestResult { :>> id = "33db42f3-5b38-4399-a24f-ca144d990791"; :>> outcome = VerdictKind::pass; :>> judgedAgainst = "4d00c1bc"; :>> judgedAt = "2026-09-18"; :>> judgedBy = "wweatherholtz"; :>> createdBy = "claudeFable5"; }
}
