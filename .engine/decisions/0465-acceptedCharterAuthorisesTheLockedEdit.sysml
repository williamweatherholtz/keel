// D0465 (status: the `status` field below is the truth) — acceptedCharterAuthorisesTheLockedEdit: a locked-surface edit is authorised by a human-accepted marked Decision that the co-committed sprint names as its charter, not only by a marked Decision riding the commit
// Recorded via `keel record decision` (D0105 RMWX axis; issue054). Acceptance is a separate explicit
// human gate (method=confirmation, D0106): flip status + add the d0465Accept event on sign-off.
package Decision0465 {
    private import EngineElement::*;
    private import EngineWork::*;
    private import EngineVerification::*;
    private import EngineRelationships::*;

    // #SafetyChange (D0070) - this Decision governs a process/schema change; the co-committed
    // change rides the process-change guard's hard lock.
    #SafetyChange part d0465 : Decision {
        :>> id = "205e8d9b-7b5a-41ae-be2f-395b80cea768";
        :>> title = "acceptedCharterAuthorisesTheLockedEdit: a locked-surface edit is authorised by a human-accepted marked Decision that the co-committed sprint names as its charter, not only by a marked Decision riding the commit";
        :>> createdAt = "2026-09-13";
        :>> createdBy = "claudeFable5";
        :>> status = DecisionStatus::accepted;
        :>> context = "The keystone lock (D0070, extended by D0209 clause 2) refuses a commit that changes a process definition or the enforcement surface unless a Decision file among the commit's own changed files carries #ProspectiveChange or #SafetyChange. D0337 then required a process-change Decision to be HELD proposed until the human accepts it. Together they leave one path through the lock: record the marked Decision and the edit in the same commit, before acceptance. The path the two rules describe as the correct one - the human accepts first, the edit lands after - is refused, because by then the Decision is not a changed file. Found 2026-09-13 applying D0460 (accepted 2026-09-13 at 8469f80; its consequence is exactly three skill-wording edits): guard process-change FAIL, locked file(s) changed with NO co-committed process-change Decision (issue517). The lock reads the marker and never the acceptance, so a proposed Decision authorises an edit and an accepted one does not.";
        :>> decision = "The process-change guard gains a second authorising source. A locked-surface change passes when a changed sprint record (.tracking/delivery/*.sysml, added or modified in the same commit) carries a #CharteredBy edge whose target Decision, read from that project's .engine/decisions, both bears the #ProspectiveChange or #SafetyChange marker AND is accepted by a human - a passing dNNNNAcceptR result whose Accept Test is not marked AUTO-ACCEPTED (acceptance_kind == Human, D0106/D0291). A proposed, rejected, auto-accepted or unmarked charter authorises nothing. The pass names the charter in one warning line: the Decision and the sprint file. The existing source - a marked Decision among the commit's changed files - is unchanged, so the record-and-edit-together path still works. The workspace gate's keystone check for files outside any project accepts the same source. The guard's refusal message names both paths. NOT A FORK: the alternative - touching the accepted Decision's file so it counts as changed - is an edit made to satisfy a guard, which is the class of act the lock exists to refuse.";
        :>> rationale = "The lock's purpose is that a control changes only under a human-signed Decision. An accepted Decision is the strongest form of that signature the engine has, and the sprint's #CharteredBy edge is the engine's own statement of which Decision a piece of work executes (D0068), already required of every sprint by the charter guard. Reading that edge makes the authorisation an authored fact with one home rather than a coincidence of which files a commit happens to touch. Requiring HUMAN acceptance, not merely accepted status, keeps standing consent (D0291) from reaching the enforcement surface, which is the D0337 boundary. The charter is read from the project that owns the sprint file, so a workspace with several projects cannot borrow another project's Decision by path.";
        :>> consequences = "keel-cli/src/guards.rs: keystone_violations takes the accepted charters as a third input; a helper reads #CharteredBy targets from changed sprint texts and resolves each to a Decision file, marker and acceptance kind; process_change and workspace.rs's staged keystone check both feed it; the guard message names the second path. Unit tests: a locked edit with a human-accepted marked charter passes; the same charter proposed, auto-accepted, or unmarked fails; keystone_selftest unchanged. .engine/docs/guards.md process-change row states the second path. Applied in sprint 692 together with D0460's skill edits, which this change is what lets land. Held proposed for the human as a safety-change (D0337): the guard is the enforcement surface.";
    }

    // acceptance event (D0121 review-queue sign-off; D0066/D0106 — human-judged, not fabricated)
    verification d0465Accept : Test { :>> id = "fa86327e-b872-4a45-8a49-98192968fa82"; :>> method = VerificationMethod::confirmation; :>> procedureText = "Said in chat 2026-09-14 over the twenty-eighth publish of the decision brief, which carried fifteen held asks; one instruction covers the fourteen non-forks, d0465 among them. The fork d0466 is not covered - it needs an option letter and stays held. - their words, verbatim: “Accept all proposals. Proceed to design with needs, etc.” WARN: read-back - the quoted words do not name d0465 (D0201 B); recorded as given (D0423)."; }
    part d0465AcceptR1 : TestResult { :>> id = "71d6d8fb-c947-4068-9b13-64a3aed596f8"; :>> outcome = VerdictKind::pass; :>> judgedAgainst = "d110d0a"; :>> judgedAt = "2026-09-14"; :>> judgedBy = "wweatherholtz"; :>> createdBy = "claudeFable5"; }
}
