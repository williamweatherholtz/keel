// D0477 (status: the `status` field below is the truth) — cliSurfaceReadsTheFactsInForceAndEveryField: guard cli-surface-declared reads the CliCommand facts IN FORCE - a fact retired by a #Supersede edge beside it is not authored - and compares the invocation with the four fields, so facts = help = dispatch holds for the field the help renders
// Recorded via `keel record decision` (D0105 RMWX axis; issue054). Acceptance is a separate explicit
// human gate (method=confirmation, D0106): flip status + add the d0477Accept event on sign-off.
package Decision0477 {
    private import EngineElement::*;
    private import EngineWork::*;
    private import EngineVerification::*;
    private import EngineRelationships::*;

    // #ProspectiveChange (D0070) - this Decision governs a process/schema change; the co-committed
    // change rides the process-change guard's hard lock.
    #ProspectiveChange part d0477 : Decision {
        :>> id = "99bedf91-b875-48d1-8d16-23305f715cb3";
        :>> title = "cliSurfaceReadsTheFactsInForceAndEveryField: guard cli-surface-declared reads the CliCommand facts IN FORCE - a fact retired by a #Supersede edge beside it is not authored - and compares the invocation with the four fields, so facts = help = dispatch holds for the field the help renders";
        :>> createdAt = "2026-09-14";
        :>> createdBy = "claudeFable5";
        :>> status = DecisionStatus::accepted;
        :>> context = "issue547 (High) and issue548 (Medium), tracked as dcCliFactSupersessionIsHonoured, sprint 712. D0271 made the CLI surface an authored fact and guard cli-surface-declared its control: every part X : CliCommand line in .engine/cli/commands.sysml is compared to cli_facts.rs and to dispatch. D0108 says a non-owner ADDS or SUPERSEDES another actor's item and never overwrites it, and guard ownership enforces it - but parse_cli_facts read every CliCommand line and never a #Supersede edge, so a superseder of the same command name was a second fact and the retired one still spoke. Twice (74c1923 cliGithub, sprint 711 cliRecord) the only passing path was to delete the part and re-author it under a new id, discarding Invariant 3's immutable identity to satisfy a rule whose own remedy the enforcing reader could not see; every fact authored by a retired actor meets the same wall at its next change. Reading that code found issue548: cli_surface_violations compared family, effect, stability and synopsis and never the invocation, and accept already differed between its two homes (fact --words|--note, mirror --note only) with the guard green - 86 facts diffed, one drift, on the mirror side.";
        :>> decision = "Guard cli-surface-declared reads the facts in force: parse_cli_facts carries each fact's part name, collects the targets of every line #Supersede dependency from X to Y; in the same text, and drops a fact whose part is a target - the edge lives beside the fact in commands.sysml, one home, and supersede_edges scans .engine/cli so the retired set every kernel-free reader shares agrees. cli_surface_violations compares the invocation alongside the four fields and reports two facts in force declaring one command name as a violation naming both parts. The two delete-and-re-author precedents are left as they landed. NOT A FORK: D0108 already names the remedy and D0271 already names the guard; this makes the one read the other.";
        :>> rationale = "A rule whose remedy its enforcing reader cannot see is not a rule but a wall: D0108 said supersede, the guard behind D0271 could not read a supersession, and two sprints paid in discarded identity what the rule said they need not. Reading the edge where the facts live keeps one home for the fact and its retirement, which is why the parser reads it from the same text rather than a second file. The invocation is the field --help renders as the command's shape; a comparison that skipped it held facts = help = dispatch for everything but the part a reader sees first, and the one drift found was real. Both new violation classes were probed against the real tree before being enabled - one invocation drift, zero duplicate names - so the tightening claims exactly what the tree showed. This is a change to an enforced guard's reader and comparison, so it carries the process-change marker and waits for the human's word (D0337); the sprint record co-committed with it is chartered by this Decision (D0465).";
        :>> consequences = "guards.rs: AuthoredCliFact gains part; parse_cli_facts honours #Supersede in its text; cli_surface_violations compares invocation and reports duplicate names in force; four probe tests beside the_live_facts_mirror_and_dispatch_agree (D0388). lib.rs supersede_edges adds .engine/cli. cli_facts.rs accept invocation regenerated to the .sysml. .engine/docs/guards.md and CLAUDE.md section 1.8 state the read. A CliCommand fact another actor owns is now retired by a #Supersede edge beside it and re-declared under its own id - the ownership guard is untouched. Removal path: drop the retired-set filter and the invocation tuple from the two functions and the two tests; the guard returns to reading every CliCommand line.";
    }

    // acceptance event (D0121 review-queue sign-off; D0066/D0106 — human-judged, not fabricated)
    verification d0477Accept : Test { :>> id = "616e7abe-0888-4b4b-8fca-8262e60dff6e"; :>> method = VerificationMethod::confirmation; :>> procedureText = "Said in chat 2026-09-14 over the twenty-eighth publish of the decision brief, which carried fifteen held asks; one instruction covers the fourteen non-forks, d0477 among them. The fork d0466 is not covered - it needs an option letter and stays held. - their words, verbatim: “Accept all proposals. Proceed to design with needs, etc.” WARN: read-back - the quoted words do not name d0477 (D0201 B); recorded as given (D0423)."; }
    part d0477AcceptR1 : TestResult { :>> id = "4dfafc8b-e228-4a0a-8304-62e7825ce358"; :>> outcome = VerdictKind::pass; :>> judgedAgainst = "d110d0a"; :>> judgedAt = "2026-09-14"; :>> judgedBy = "wweatherholtz"; :>> createdBy = "claudeFable5"; }
}
