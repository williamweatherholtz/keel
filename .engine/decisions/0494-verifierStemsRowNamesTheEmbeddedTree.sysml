// D0494 (status: the `status` field below is the truth) — The verifier's stems check names the embedded tree - a changed path under .engine contributes init, as the binary already attributes it
// Recorded via `keel record decision` (D0105 RMWX axis; issue054). Acceptance is a separate explicit
// human gate (method=confirmation, D0106): flip status + add the d0494Accept event on sign-off.
package Decision0494 {
    private import EngineElement::*;
    private import EngineWork::*;
    private import EngineVerification::*;
    private import EngineRelationships::*;

    // #ProspectiveChange (D0070) - this Decision governs a process/schema change; the co-committed
    // change rides the process-change guard's hard lock.
    #ProspectiveChange part d0494 : Decision {
        :>> id = "4bc18190-b130-4727-aca6-20f772cc8703";
        :>> title = "The verifier's stems check names the embedded tree - a changed path under .engine contributes init, as the binary already attributes it";
        :>> createdAt = "2026-09-15";
        :>> createdBy = "claudeFable5";
        :>> status = DecisionStatus::accepted;
        :>> context = "The test-verify skill's receipt-honesty table (step 5, the `stems` row) told the VERIFIER to expect the touched receipt's `stems` to equal the changed `keel-cli/src/<stem>.rs` set alone. touched.rs has attributed a changed or untracked path under `.engine/` to the stem `init` since D0474's content keys landed (`embedded_stem`, keel-cli/src/touched.rs:122, its own test `a_change_under_the_embedded_tree_names_init`), because that tree is compiled into the binary and every test that runs `keel init` reads it. issue530 (2026-09-13, sprint 702) recorded the drift: a correct receipt over an .engine change reads MISMATCH under the skill's rule. Sprint 725's second VERIFIER hit it again on this tree - the untracked `.engine/decisions/0493-*.sysml` contributed `init`, the ladder was green at 865 passed, and the receipt reported `stems=[init, suite, touched, verify] changed=[suite, touched, verify] MISMATCH` as its one discrepancy. Two verifiers in two sprints have reported a correct receipt as dishonest from a procedure row that no longer describes the binary.";
        :>> decision = "The `stems` row of the test-verify skill's receipt-honesty table says what the binary does: the sorted stem set of every changed `keel-cli/src/<stem>.rs` PLUS `init` when any path under `.engine/` is changed or untracked (`git status --short -- .engine`), naming `embedded_stem` in touched.rs as the rule's home and issue530 as the reason. Nothing else in the skill, the process or the receipt shape changes.";
        :>> rationale = "The verifier's job is to read the receipt against the binary's rule, not to re-derive a rule of its own; when the two rows disagree the receipt is right and the procedure is stale, and a stale procedure that reports MISMATCH on a green tree teaches the reader to ignore MISMATCH - the issue490 failure in the other direction. The correction is one table row, and it is the procedure half of issue530; the receipt half - the receipt stating the changed paths it attributed each stem from, so no reader re-derives the rule at all - remains dcTouchedReceiptStatesItsOwnAttribution's. This is a process-change: the skill is a process definition under D0070's lock, and the change is co-committed with this Decision under D0209 clause 2 and held for the human under D0337.";
        :>> consequences = ".engine/skills/test-verify/SKILL.md step 5 `stems` row corrected; `.claude/skills/test-verify/SKILL.md` regenerated by sync-claude in the same commit. A verifier over a tree with an .engine change expects `init` and writes MATCH; the sprint 725 receipt's stems line was re-derived under this row from the receipts on disk, the ladder not re-run. Resolves obligation1ab52489 and obligation87f79374 (the Stop hook and the verifier's SubagentStop each yielded red on the locked-file edit before this Decision existed). issue530 stays open on dcTouchedReceiptStatesItsOwnAttribution for the receipt half.";
    }

    // acceptance event (D0121 review-queue sign-off; D0066/D0106 — human-judged, not fabricated)
    verification d0494Accept : Test { :>> id = "4b47ff67-f81d-42f7-8842-2d15a1167691"; :>> method = VerificationMethod::confirmation; :>> procedureText = "recorded from chat - their words, verbatim: “Accept all decisions as recommended. Proceed to release and fix downstream” WARN: read-back - the quoted words do not name d0494 (D0201 B); recorded as given (D0423)."; }
    part d0494AcceptR1 : TestResult { :>> id = "e4417904-f849-490f-870c-ef8f83cf5f88"; :>> outcome = VerdictKind::pass; :>> judgedAgainst = "4d00c1bc"; :>> judgedAt = "2026-09-18"; :>> judgedBy = "wweatherholtz"; :>> createdBy = "claudeFable5"; }
}
