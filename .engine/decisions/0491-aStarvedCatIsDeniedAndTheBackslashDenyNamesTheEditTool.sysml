// D0491 (status: the `status` field below is the truth) — A cat or tee with nothing feeding it is DENIED by the pre-bash hook - the second blocking pre-bash verdict beside D0309 - and the backslash deny now names the byte-exact channel: Edit tool for a replacement, Write tool for a new file
// Recorded via `keel record decision` (D0105 RMWX axis; issue054). Acceptance is a separate explicit
// human gate (method=confirmation, D0106): flip status + add the d0491Accept event on sign-off.
package Decision0491 {
    private import EngineElement::*;
    private import EngineWork::*;
    private import EngineVerification::*;
    private import EngineRelationships::*;

    // RESEARCH: Read 2026-09-15. The hung command: `cat > '$SCRATCH/fix721.py' 2>/dev/null || SCRATCH=...; cat > '$SCRATCH/fix721.py' <<'EOF' ...` with $SCRATCH unset - the first cat had no heredoc, no operand and no producer, so it opened /fix721.py and waited on a stdin this harness never closes until the two-minute tool timeout (wc -c /fix721.py = 0). The pre-bash hook did not fire: its one deny is heredoc_with_backslash (main.rs hook_pre_bash; shellcheck.rs), and the heredoc in that command carried no backslash. The wider pattern the human named: fix_decisions.py, edges721.py, fix721.py in one sitting were each a string replacement in one file - the Edit tool's job, no shell in the path - written as Python and run by path because the bypass-mode harness text says to work through Bash heredocs, and D0309 measured that a backslash pair collapses before bash runs even inside a quoted heredoc, so no shell-side wrapper can make that path byte-exact.
    // #SafetyChange (D0070) - this Decision governs a process/schema change; the co-committed
    // change rides the process-change guard's hard lock.
    #SafetyChange part d0491 : Decision {
        :>> id = "22749289-ba25-4a2b-8e01-ea48895c805a";
        :>> title = "A cat or tee with nothing feeding it is DENIED by the pre-bash hook - the second blocking pre-bash verdict beside D0309 - and the backslash deny now names the byte-exact channel: Edit tool for a replacement, Write tool for a new file";
        :>> createdAt = "2026-09-15";
        :>> createdBy = "claudeFable5";
        :>> status = DecisionStatus::accepted;
        :>> context = "The human, 2026-09-15: Good heaven are we still having trailing backslash issues. Write a wrapper around it, already and be done with this issue. What failed was not D0309's shape but the neighbouring one - a redirected cat starved of input - and the friction they see is real either way: the agent keeps routing one-file string replacements through the shell, where the only byte-exact channels the harness offers are the Edit and Write tools. Every prior control on this class was a deny of one shape plus a reminder to use the Write tool; the reminder did not carry the instruction that ends the pattern (which TOOL does a replacement), and the starved-cat hang had no control at all - it cost the whole tool timeout each time and reported nothing.";
        :>> decision = "keel hook pre-bash refuses (PreToolUse deny, every profile) a Bash command whose pipeline head is cat or tee with nothing feeding it - no heredoc, no `<` input and, for cat, no file operand - naming the starved segment; detection is shellcheck::stdin_starved_write, which scans only the lines outside heredoc bodies and only the head of each pipeline, so a heredoc-to-file, a cat with operands, a piped tee and a `<` redirect all pass. The D0309 deny's reason text names the channel that ends the class: a string replacement in an existing file is the Edit tool (or scripts/textpatch.py), a new file is the Write tool run by path. Both denies are recorded in the fire-ledger under their control names, heredoc-backslash and stdin-starved-write.";
        :>> rationale = "WHY DENY: a starved cat is never useful in this harness - stdin never closes - so there is no legitimate command the deny loses, and the hang it prevents costs two minutes and a zero-byte file every time; D0047 says the third recurrence of a class gets a control, not a reminder. WHY THE MESSAGE CHANGE IS PART OF IT: the human asked for a wrapper; the honest answer is that the wrapper already exists in the harness (Edit and Write are the byte-exact channels) and the control's job is to say so at the moment the agent reaches for the shell instead - a deny that names the wrong remedy (write a script, run it by path) reproduces the two-step the human is tired of. WHY NOT A SHELL WRAPPER: D0309 measured the rewrite happening before bash runs; a wrapper inside bash sees the collapsed text and cannot recover it. KNOWN FALSE POSITIVE, ACCEPTED: `while read f; do cat > '$f'; done < list` reads the loop's redirected stdin and is denied; the shape has not been used in this repo. THE PAIR: the positive is the hung command verbatim, the negative is the sanctioned prose heredoc plus `cat a.txt b.txt > c.txt`, both run against the built hook before this record (shellcheck starved_tests; ledger rows control=stdin-starved-write deny and allow).";
        :>> consequences = "Held proposed for the human (a safety change: the pre-bash hook gains a second deny). The rule is live in the binary this commit ships and ledgered from its first fire; control-map.sysml gains the hook-rule row ctlStdinStarvedWrite bound to EHZ4 beside ctlHeredocBackslash so the census names it; issue564 tracks the hang with this Decision as its resolver. What changes for the agent: a one-file replacement is an Edit call and a new file is a Write call, and the shell is for running things - the two denies now say exactly that when it forgets. Depends on nothing; D0309 stands whole.";
    }
    #DerivedFrom dependency from d0491 to st127;

    // acceptance event (D0121 review-queue sign-off; D0066/D0106 — human-judged, not fabricated)
    verification d0491Accept : Test { :>> id = "75442276-c083-4475-b23c-fd60d125247c"; :>> method = VerificationMethod::confirmation; :>> procedureText = "recorded from chat - their words, verbatim: “Accept the three process-hook clauses in order - Read, Bind, Rung - and the starved-cat deny. [x] Accept: the pre-bash hook denies a pipeline-head cat or tee with nothing feeding it, and the backslash deny's reason names the Edit tool for a replacement and the Write tool for a new file (recommended)”"; }
    part d0491AcceptR1 : TestResult { :>> id = "c14d7876-518a-4aa8-a0cb-9d1bf2e980a0"; :>> outcome = VerdictKind::pass; :>> judgedAgainst = "85613c8"; :>> judgedAt = "2026-09-15"; :>> judgedBy = "wweatherholtz"; :>> createdBy = "claudeFable5"; }
}
