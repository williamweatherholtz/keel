// D0487 (status: the `status` field below is the truth) — projectDecisionInKeelIssues: whether a project's own Decision - its recorded 'we will not do X' - is authored from the keel-issues member or only from the governance member above it
// Recorded via `keel record decision` (D0105 RMWX axis; issue054). Acceptance is a separate explicit
// human gate (method=confirmation, D0106): flip status + add the d0487Accept event on sign-off.
package Decision0487 {
    private import EngineElement::*;
    private import EngineWork::*;
    private import EngineVerification::*;
    private import EngineRelationships::*;

    // RESEARCH: Read 2026-09-15 before asking. st126's words (intake-2026-09-14.sysml): 'make keel-issues or something, which can manage the subset of processes related to items/issues (and not e.g. decisions about keel itself)'. D0480 (accepted) writes the boundary as 'the processes that govern keel itself - decisions, acceptance, activation, guards, change requests - stay out of it'. The schema lets an Issue's resolver be a backlog action OR a Decision (.engine/schema/core/relationships.sysml:56, D0077), and the resolver-kind guard refuses anything else. On this tree every Decision lives under .engine/decisions/ (485 files) and exactly one project file declares a Decision (intake-2026-09-13.sysml); no downstream project exists yet to count. keel accept, standing consent (D0207/D0291), the process-change hold (D0337/D0439) and consent-scope are all code about DECISIONS, 1,948 lines of process_cmd.rs and the accept path in main.rs. Nothing in the model says where a downstream project's own Decision is recorded from, so it is not answerable by reading.
    part d0487 : Decision {
        :>> id = "23351a87-47ed-43d3-9e6e-5d8e88c69151";
        :>> title = "projectDecisionInKeelIssues: whether a project's own Decision - its recorded 'we will not do X' - is authored from the keel-issues member or only from the governance member above it";
        :>> createdAt = "2026-09-15";
        :>> createdBy = "claudeFable5";
        :>> status = DecisionStatus::accepted;
        :>> context = "The keel-issues member (D0480, srItemVerbsBuildFromKeelIssues) carries the item and issue processes and excludes the processes that govern keel: decisions about keel, acceptance, activation, guards, change requests. A project that tracks only items and issues will still say 'we will not do X' - keel's own invariant 4 makes that a Decision, and an Issue may be resolved by one (relationships.sysml:56). The question D0480 leaves open is whether that project's OWN Decision - not one about keel - is recorded and accepted from keel-issues, or whether recording any Decision means depending on the governance member above it. The metric here is a boundary, not a number: which verbs a project gets from the small member. What one verb means for the reader: a project that only has keel-issues can (or cannot) record 'we will not do X' and have an Issue close on it, without building or installing the rest of keel.";
        :>> decision = "OPTION A (recommended - the boundary D0480 drew, read narrowly): keel-issues KNOWS the Decision type - it resolves a Decision named as an Issue's resolver, reads its status, and computes the Issue resolved when that Decision is accepted - but carries NO record decision and NO accept verb. A project that wants to author Decisions depends on the governance member as well; a project that only tracks items and issues can still consume Decisions someone else recorded. COST: a keel-issues-only project cannot record its own 'we will not do X'; to get that verb it installs the governance member, the larger build the member exists to spare it. What I do with this answer: srItemVerbsBuildFromKeelIssues stands as written and the keel-issues DoD names the Decision type as read-only in the member. OPTION B (a project's own Decision is an item): keel-issues carries record decision and accept for a project's own Decisions, and the engine-governance parts - the process-change and safety-change holds, standing consent, consent-scope, the Change Request process - stay in the governance member; a Decision recorded from keel-issues cannot carry a governance marker. COST: the human-only acceptance channel (confirmation-authenticity, attestation-authority) is compiled into two members, and D0480's clause is narrowed by a SupersedeClause a day after its acceptance. What I do with this answer: a SupersedeClause on D0480's clause 'decisions ... stay out of it' narrowing it to decisions about keel; srItemVerbsBuildFromKeelIssues gains record decision and accept in its verb list and its closure test excludes the marker holds instead of the Decision type. OPTION C (do nothing): keel-issues does not know the Decision type at all; an Issue in a keel-issues-only project can be resolved by a backlog action only, and resolver-kind in that member refuses a Decision resolver. COST: invariant 4 does not hold for keel-issues projects - their 'decided not to' becomes a backlog action, a stored verdict in an item. What I do with this answer: the DoD says so and the relationships comment at line 56 gains the member qualification.";
        :>> rationale = "WHY THIS IS THE HUMAN'S: st126 excluded 'decisions about keel itself' by example ('e.g.'), and the two readings of that example - all Decisions are governance, or only keel's are - each fit the words. Which one they meant is a value only they hold; the model does not say. WHY A OVER B: a Decision's whole force in keel is its acceptance by a human, and acceptance is the one write that must never be defaulted or inferred (D0051, D0129). Putting accept into the small member duplicates the human-only channel (confirmation-authenticity, attestation-authority) into a second code path, the D0105 one-home defect at the most sensitive fact keel holds. Reading a Decision costs the member nothing - the type is in keel-schema, a leaf. WHY NOT C: it makes invariant 4 ('we will not do X is a Decision') false for keel-issues projects, so their Issues would close on an action that says 'decided not to', which is the stored-status defect in another coat. FALSIFIER: a downstream project that installs keel-issues alone and finds it needs record decision on its first week would show A was the wrong reading; the count of such projects today is 0.";
        :>> consequences = "Held proposed for the human on the decision brief. Under A: no schema or process change; D0480 stands; the keel-issues Component description and srItemVerbsBuildFromKeelIssues stand as authored; the member's dependency closure includes keel-schema for the Decision type and nothing from process_cmd.rs. Under B: a SupersedeClause on D0480 authored with the acceptance in the same commit (D0398, D0352); srItemVerbsBuildFromKeelIssues edited by its owner to name the two verbs; the confirmation-authenticity and attestation-authority guards move to whichever member hosts accept, one home. Under C: the relationships.sysml comment at the Resolves marker gains the member qualification and the resolver-kind guard in keel-issues refuses a Decision resolver. In every case this Decision governs no process and changes no gate on this tree today - NOT A PROCESS CHANGE: it assigns a type and two verbs to a member that does not yet exist.";
    }
    #DerivedFrom dependency from d0487 to st126;
    #DependsOn dependency from d0487 to d0480;

    // acceptance event (D0121 review-queue sign-off; D0066/D0106 — human-judged, not fabricated)
    verification d0487Accept : Test { :>> id = "eb2d2a04-8fa7-4926-9f2d-14705d9e424d"; :>> method = VerificationMethod::confirmation; :>> procedureText = "recorded from chat - their words, verbatim: “on the scope fork take A: the items member reads Decisions, never writes them. [x] Option A: keel-issues knows the Decision type read-only - it resolves an Issue by a Decision and computes it resolved - but carries no record decision and no accept; a project that authors Decisions depends on the governance member (recommended)”"; }
    part d0487AcceptR1 : TestResult { :>> id = "c17893ef-d1df-4efa-a970-71511ea4d44b"; :>> outcome = VerdictKind::pass; :>> judgedAgainst = "85613c8"; :>> judgedAt = "2026-09-15"; :>> judgedBy = "wweatherholtz"; :>> createdBy = "claudeFable5"; }
}
