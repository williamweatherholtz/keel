// D0538 (PROPOSED — NOT YET ACCEPTED) — check_receipt.py reads the verifier's receipt against the ladder that ended - keel verify --wait, then verify-receipt.toml and touched-receipt.toml - and refuses one that says the ladder did not end, describes another run, or disagrees with a rung verdict or the touched counts
// Recorded via `keel record decision` (D0105 RMWX axis; issue054). Acceptance is a separate explicit
// human gate (method=confirmation, D0106): flip status + add the d0538Accept event on sign-off.
package Decision0538 {
    private import EngineElement::*;
    private import EngineWork::*;
    private import EngineVerification::*;
    private import EngineRelationships::*;

    // #ProspectiveChange (D0070) - this Decision governs a process/schema change; the co-committed
    // change rides the process-change guard's hard lock.
    #ProspectiveChange part d0538 : Decision {
        :>> id = "2cc05c0a-4413-433f-8f47-4b78f144016c";
        :>> title = "check_receipt.py reads the verifier's receipt against the ladder that ended - keel verify --wait, then verify-receipt.toml and touched-receipt.toml - and refuses one that says the ladder did not end, describes another run, or disagrees with a rung verdict or the touched counts";
        :>> createdAt = "2026-09-20";
        :>> createdBy = "claudeFable5";
        :>> status = DecisionStatus::proposed;
        :>> context = "The D0425 verifier renders its receipt with scripts/verify_receipt.py (D0533) after keel verify --wait returns, and the primary reads the receipt's DISCREPANCIES line before dispatching the recorder. Nothing reads the receipt against the ladder it describes. Sprint 743 (issue603): the verifier returned a receipt typed by hand - LADDER -> KILLED during touched; exit=2, touched=killed, TOUCHED RECEIPT outcome=running passed=0 failed=0, DISCREPANCIES naming pid 29824 as dead - while that pid was alive and the ladder was still running the touched rung. The ladder ended 977 seconds into the touched rung with fail (101), 880 passed and 23 failed, at=1789725917. The receipt described a ladder that never ended, and no control compared it with the one that did; the primary found the difference by running keel verify --wait itself after the receipt was in hand. The recorder's report has had such a check since D0473 (check_report.py, nine refusals); the verifier's receipt, the file the recorder writes ceremony from, had none.";
        :>> decision = "check_receipt.py, beside check_report.py under the delegated-ceremony skill's references, is given the verifier's receipt file and --root, runs keel verify --wait ROOT, reads .keel/metrics/verify-receipt.toml and touched-receipt.toml, and REFUSES a receipt that disagrees with the ladder that ended: --wait reporting no ended ladder is itself the refusal (in flight, KILLED or no receipt - nothing to check against, so relaunch); otherwise a receipt is refused for saying the ladder did not end while it did (no VERIFIER RECEIPT header, KILLED in its LADDER line, outcome=running, a rung verdict killed - the refusal names the ended rung and exit), for carrying a LADDER at= other than the ended ladder's or none at all (a render of another run), for a LADDER outcome, stopped_at or rung verdict other than the file's, for TOUCHED RECEIPT at=, outcome, passed or failed values other than touched-receipt.toml's when the ladder reached that rung (or touched counts quoted for a ladder that stopped before it, or a missing file), and for a verify-receipt.toml whose at= moved between --wait and the read. The pure refusals() takes the --wait text and exit and the two decoded receipts as arguments so the D0388 pair pins it without a tree. The verifier runs it as its last step before returning and its verdict line rides the receipt; the delegated-ceremony process carries the check as the trigger of dcyDispatchRecorder - a recorder is dispatched only on a receipt check_receipt.py has passed. Fixtures under references/fixtures hold sprint 743's receipt as returned, its corrected D0533 render, the --wait output, and the ladder and touched receipts as reconstructed from the sprint's recorded counts.";
        :>> rationale = "D0047: the receipt is the one file two later actors read as fact - the primary for the go/no-go, the recorder for the ceremony it writes - and a receipt that describes a ladder other than the one that ended lets a failing touched set be recorded as unrun. Reading the receipt against the toml files is the check wording cannot satisfy: the rung verdicts and the touched counts are either the file's or they are not. keel verify --wait is the right first step because it blocks while the writer's pid lives, so the check cannot itself run early - the sprint 743 defect - and its exit is the ladder's own. Matching on at= rather than head pins the receipt to one run: sprint 743's tree had two ladders at the same head fifty minutes apart, one fail (101) and one pass, and only the timestamp tells them apart. The check sits with the verifier, mirroring check_report.py with the recorder (D0473), and gates the recorder's dispatch because that is the step whose input the receipt is.";
        :>> consequences = "A verifier whose receipt is refused returns the refusal lines beside the receipt, and the primary reads them before deciding whether to relaunch the ladder or dispatch the recorder; a receipt rendered by verify_receipt.py after --wait passes by construction, so the check costs one --wait call on an ended ladder. The check's own probe table carries the sprint 743 pair and two more rows; check_receipt.py --probe reports every pair holds. The toml fixtures are reconstructions - the sprint 743 verify-receipt.toml was overwritten by the next ladder - and say so in their comments. The delegated-ceremony skill's verifier brief, the test-verify skill's procedure, the process file's dcyVerifierReceipt and dcyDispatchRecorder steps, the verifier agent definition (.claude/agents/verifier.md) and CLAUDE.md say what the code does. No guard, hook or CI workflow changes; the guard count stays 76. The .claude copies are regenerated by keel sync-claude in the same commit.";
    }
}
