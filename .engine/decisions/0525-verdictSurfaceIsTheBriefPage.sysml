// D0525 (PROPOSED — NOT YET ACCEPTED) — verdictSurfaceIsTheBriefPage: the decision brief page captures the verdict itself - a tap or a sentence on the published page is written into the page's next version by the viewer's browser, the watching keel session reads it back and records the acceptance citing that version - or the console is hosted remotely, or nothing changes
// Recorded via `keel record decision` (D0105 RMWX axis; issue054). Acceptance is a separate explicit
// human gate (method=confirmation, D0106): flip status + add the d0525Accept event on sign-off.
package Decision0525 {
    private import EngineElement::*;
    private import EngineWork::*;
    private import EngineVerification::*;
    private import EngineRelationships::*;

    // RESEARCH: the runtime contract 0.2.52 of the page host (capabilities artifact, user, comments, db, room; the session's own tool list has no db reader, checked 2026-09-19), st074 behind D0289, the D0411 device receipt, D0173's mobile inbox transport that never got a carrier, and the seven-row channel inventory in st175
    // #ProspectiveChange (D0070) - this Decision governs a process/schema change; the co-committed
    // change rides the process-change guard's hard lock.
    #ProspectiveChange part d0525 : Decision {
        :>> id = "06eefe7b-db1a-4c3f-80f0-56ad6eaf9f3f";
        :>> title = "verdictSurfaceIsTheBriefPage: the decision brief page captures the verdict itself - a tap or a sentence on the published page is written into the page's next version by the viewer's browser, the watching keel session reads it back and records the acceptance citing that version - or the console is hosted remotely, or nothing changes";
        :>> createdAt = "2026-09-19";
        :>> createdBy = "claudeFable5";
        :>> status = DecisionStatus::proposed;
        :>> context = "st174 (their words today: 'GitHub ingest and backlog ingest. We need a permanent solution to decision capture') and st175, GH#96, quoting the same human on a fresh project: 'I'm not going to start another terminal to copy and paste words and manually edit things to accept a decision ... we need a perfectly reliable, easy way for me to drive development that works local or remote. So far, everything has been a compromise (keel serve is local, pages don't actually capture feedback so I have to manually copy text, etc.)'. The pain is tracked as issue632, resolver dcVerdictChannelIsOneSurface, whose DoD names five properties: one surface reachable from a phone; a tap or a sentence there IS the gesture, written through the write API with the D0192/D0198 substance; local and remote; a delegation grant is itself a gesture on that surface; every other channel retired or named as the transport. What the DoD does not choose is the surface. The channel inventory in st175 shows why none of the existing seven has all five: keel serve captures with a re-verifiable device receipt (D0411) but is local; the GitHub gesture is remote but deprecated with its workflow and pushes notifications the human refused (st088); the rendered decision page is remote and shows the substance but captures nothing, so the human reads it and then retypes elsewhere; quoted chat words (D0289) capture by hand and only where a project has already hand-edited attestation-policy.toml (issue376/issue621). The page host this project already publishes its briefs to now offers the page runtime abilities: a published page may publish its own next version from the viewer's browser (capability artifact, every open view reloads to it, versions are kept), may read the viewer's opaque per-organisation identity and whether they own the page (capability user; a public-link visitor reads as absent), and a republish from any view reaches the session that published the page as a notification telling it to re-read. The page is already the channel by D0359; what it lacks is the return path.";
        :>> decision = "RESEARCH: read before asking - the runtime contract of the page host (0.2.52: artifact, user, comments, db, room, sample), st074 and D0289, the D0411 receipt design, D0173, and the st175 inventory. OPTION A (recommended): the decision brief page is the verdict surface. The brief carries, per pending Decision, the courses as tappable choices and one sentence field; a tap writes a verdict record - decision id, the chosen course's label verbatim, the typed sentence verbatim, the viewer's opaque organisation id, the page version it was tapped on, the time - into the page's own state and the page publishes its next version from the human's browser; the record is appended, never replaced, so the live page carries every verdict ever given on it. The keel session that published the page is notified of the republish, reads the page back through the same tool that published it, and records the acceptance through the write API with the words the page captured, the Person the viewer id is bound to, and a citation naming the page and the version; the citation is re-verifiable by reading the live page and finding that record. The binding of a viewer id to a Person is the first gesture on the page - 'I am wweatherholtz' - and the session writes it as the project's recording delegation, so a fresh project's human meets a tap, not a TOML file. keel serve's console, the GitHub gesture and quoted chat words are named as fallback transports for a project whose human has no page host; the D0173 inbox design is retired. COST: a vendor surface - the page host and its runtime contract - becomes the primary verdict channel, and .keel/decision-page.toml stays machine-local, so a second clone forks the queue until reconciled (D0359's stated residual, unchanged); the viewer identity is an opaque id bound by one self-declaring tap, weaker than the HMAC device receipt because anyone in the organisation who can edit the page can tap; the receipt is re-verifiable only by someone who can open the page, not from the git record alone; and a verdict tapped while no session is alive lands in the tree at the next session start, not at the tap - the page is the durable receipt in the interval. One spike proves the loop before the process changes: this very brief carries the prototype, and the human's answer to this fork is its first capture. OPTION B: host the existing keel serve console remotely per project (a tunnel or a small host) so the D0411 device-receipt tap is reachable from a phone. COST: a host, an authentication story and a device enrolment per project, none of which a fresh project has on day one, so the bootstrap the human refused becomes a deployment instead of a TOML edit; the console shows less of the substance than the brief does today. OPTION C: do nothing - the brief stays read-only, verdicts stay quoted chat words under D0289 where the policy grants them. COST: exactly the st175 failure, restated: the human reads a page and retypes elsewhere, and a fresh project's first act is a hand-edit of attestation-policy.toml.";
        :>> rationale = "The DoD asks for one surface with five properties, and the inventory shows the five are split across seven channels because each channel was built where it was easy to capture (the machine) or easy to reach (a page) but not both. The page runtime removes the split: the surface the human already reads gains a return path that the same session already listens on, so capture, reach and substance meet on one artefact without a new host, a new login or a new process step - the decision-surfacing process already publishes and republishes this page (D0269/D0359) and the acceptance write path already accepts a recorder distinct from the judge under a declared delegation (D0289/D0411). A is recommended because every property the DoD names is satisfied by something that exists today and can be exercised this week, and because its weakest link - an opaque identity bound by one tap - is stronger than the channel it replaces, where the identity is whatever the agent typed after --by. B keeps the strongest receipt but moves the bootstrap cost onto every project's human, which is the cost they refused. The residuals of A are stated in its COST and one of them - who may tap - is what the delegation grant on the page is for.";
        :>> consequences = "dcVerdictChannelIsOneSurface's DoD is unchanged; this Decision chooses its surface and is its charter. If A: the brief builder gains the capture block and the page declares the artifact and user capabilities; decision-surfacing gains a step between publish and record - read back any verdict the page captured since the last read, record it through keel accept with the page citation, and republish; attestation-policy.toml's decisionAcceptance delegatedRecording is written by that step from the page's binding gesture, so a fresh project never edits it by hand; the citation form is added beside the D0411 device receipt in the substance rule as a second surface-written form; keel serve, the GitHub gesture and chat words are named fallbacks in the process file; D0173 is retired by a follow-on Decision recorded with --supersedes. If B: a hosting sprint per project and no change to the brief. If C: issue632 is dispositioned accept-risk with the human's words. The frontier effect of accepting A is read from keel show whats-next after the spike passes on this page; nothing is re-ranked by the acceptance itself.";
    }
    #DerivedFrom dependency from d0525 to st174;
    #DerivedFrom dependency from d0525 to st175;
}
