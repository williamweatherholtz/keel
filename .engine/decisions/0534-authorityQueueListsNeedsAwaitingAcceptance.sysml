// D0534 (status: the `status` field below is the truth) — A Need awaiting the human's acceptance is a row of the authority queue: needAcceptance, computed from the #Verify-linked confirmation Tests that reach it and who judged their results
// Recorded via `keel record decision` (D0105 RMWX axis; issue054). Acceptance is a separate explicit
// human gate (method=confirmation, D0106): flip status + add the d0534Accept event on sign-off.
package Decision0534 {
    private import EngineElement::*;
    private import EngineWork::*;
    private import EngineVerification::*;
    private import EngineRelationships::*;

    part d0534 : Decision {
        :>> id = "af746ca8-bc52-47dc-809f-f15e12efd337";
        :>> title = "A Need awaiting the human's acceptance is a row of the authority queue: needAcceptance, computed from the #Verify-linked confirmation Tests that reach it and who judged their results";
        :>> createdAt = "2026-09-19";
        :>> createdBy = "claudeFable5";
        :>> status = DecisionStatus::accepted;
        :>> context = "The Business workflow orders the engine's own work: no SystemRequirement or architecture Decision is recorded until the Needs it serves exist and are accepted, acceptance being a human's word on that claim (method=confirmation, judgedBy a Person - D0051, D0192). On 2026-09-19 the three EngineSelfAnalysisNeeds recorded on 2026-09-02 from the human's own words (st065, st066, translated as us069-us071) had no acceptance Test and no result, while ten Decisions (D0425 through D0533) and eleven sprints had been recorded against the verification Need among them. Nothing computed showed the wait: keel show authority-queue lists what waits for the human as decisionAcceptance, findingDisposition and contentionAdjudication rows and has no kind for a Need. Need acceptance exists only as a per-file convention - a set-level Test named <set>NeedsAccept with a result judgedBy the human - bound to its Needs by #Verify edges inconsistently (engine-needs binds one of thirteen, modular-members none of eight), so a view that wanted to compute it could not. issue661 records the defect. NOT A FORK: the row kind and the edge are the only shape the model already uses for acceptance (D0016, D0066); the alternative - a stored accepted flag on the Need - is authored state, ruled out by D0018. NOT A PROCESS CHANGE: no workflow step, gate, guard or schema member changes; the lens that the decision-surfacing procedure already reads at its first step grows a row kind, and the procedure's steps are unchanged.";
        :>> decision = "keel show authority-queue computes a needAcceptance row for every Need that no method=confirmation Test with a passing TestResult judgedBy a Person reaches through a #Verify edge. The row carries the Need's shortName, its createdAt, the days it has waited, and the name of the confirmation Test that reaches it without a passing human result - or the words no acceptance test when none reaches it. The binding between a Need and its acceptance is the #Verify edge and nothing else: every existing passing confirmation Test under .tracking/business whose words accept a set is bound to each Need of that set by copy-and-add edges, no result touched or fabricated; a Need no existing Test's words cover is a true row until the human speaks. The decision-surfacing brief lists these rows beside the decisionAcceptance rows it already lists. Delivered by dcAuthorityQueueListsNeedsAwaitingAcceptance.";
        :>> rationale = "A decision the human cannot find is not one they have been asked to make (D0269), and a Need is the first decision the Business workflow asks of them. The queue exists so that what waits for the human is computed, not remembered; leaving Need acceptance out of it made the one ordering rule of the Business workflow unobservable, and the ordinary autonomous run (D0052) walked past it for seventeen days without any gate able to say so. The edge, not a flag, carries the binding because acceptance is a verdict, a verdict is a TestResult (D0066), and the same edge already makes a Need's verification traceable; a stored accepted state would be a second truth beside the result. Backfilling edges rather than results keeps every existing attestation exactly as the human gave it.";
        :>> consequences = "Three needAcceptance rows appear at once, naming engineSelfAnalysisNeedsAccept; any other Need no existing Test's words cover appears too, and each such row is either bound by an edge from a Test whose words do cover it or is a genuine wait the human sees for the first time. The decision-surfacing state test treats a needAcceptance row entering or leaving the set as a change, so the brief is republished when a Need arrives or is accepted. The confirmation-authenticity guard already refuses an AI-judged confirmation result, so an AI cannot clear a row by writing one. A future Need set with no acceptance Test is visible from its first commit. Not changed: how acceptance is recorded (keel accept, or a confirmation result judgedBy the Person), the Need type, the Business workflow's steps.";
    }
    #DerivedFrom dependency from d0534 to us070;

    // acceptance event (D0121 review-queue sign-off; D0066/D0106 — human-judged, not fabricated)
    verification d0534Accept : Test { :>> id = "1cef730d-c5c5-4137-9263-57978b0af5fc"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0534AcceptR1 : TestResult { :>> id = "2231cfd4-d59a-4cf1-b27c-a25ab7fa29cc"; :>> outcome = VerdictKind::pass; :>> judgedAgainst = "f39cac91"; :>> judgedAt = "2026-09-19"; :>> judgedBy = "wweatherholtz"; :>> createdBy = "claudeFable5"; }
}
