// D0514 (status: the `status` field below is the truth) — livingDocsCiteSourceThatResolves: a file.rs:N citation on the living doc surface resolves to a source file under a workspace member and holds the identifier cited beside it - the source-reference guard, the seventy-sixth, red at the doc line that names a moved module's stale line
// Recorded via `keel record decision` (D0105 RMWX axis; issue054). Acceptance is a separate explicit
// human gate (method=confirmation, D0106): flip status + add the d0514Accept event on sign-off.
package Decision0514 {
    private import EngineElement::*;
    private import EngineWork::*;
    private import EngineVerification::*;
    private import EngineRelationships::*;

    // #ProspectiveChange (D0070) - this Decision governs a process/schema change; the co-committed
    // change rides the process-change guard's hard lock.
    #ProspectiveChange part d0514 : Decision {
        :>> id = "33bd0605-d5e1-4eca-b2ca-8fb791768d72";
        :>> title = "livingDocsCiteSourceThatResolves: a file.rs:N citation on the living doc surface resolves to a source file under a workspace member and holds the identifier cited beside it - the source-reference guard, the seventy-sixth, red at the doc line that names a moved module's stale line";
        :>> createdAt = "2026-09-18";
        :>> createdBy = "claudeFable5";
        :>> status = DecisionStatus::accepted;
        :>> context = "The living doc surface - processes, skills, docs, contracts, workflows, rules and CLAUDE.md - names code by file and line so that a reader, human or delegated agent, opens what the doc means. D0479 moved most of keel-cli's modules into members; migrate.rs went to members/keel-process/src/migrate.rs and check_preconditions moved from line 664 to line 804, and the two docs that cite it (.engine/skills/project-migration/SKILL.md line 10 and .engine/processes/project-migration.sysml line 15) still said migrate.rs:664-666 (issue591). No control reads a source citation: tool-reference holds a doc's script paths to files that exist and cli-reference (D0471) holds its keel verbs to the dispatched surface, but a .rs:N citation is checked by nobody, so a moved module leaves every doc that cited it pointing at a line that now holds something else, and the doc keeps reading as authority. The backlog item dcSourceCitationsOnTheLivingDocsResolve is chartered by D0471, whose accepted marker authorises the skill, process and guard-source edits under D0465; this Decision is the guard's own clause (D0303: one clause per Decision), held for the human because it adds a hard guard to the enforced set.";
        :>> decision = "A hard guard source-reference joins the enforced set as the seventy-sixth. Its population is every <name>.rs:N and <name>.rs:N-M citation on the living doc surface, tool-reference's scope: .engine/processes, skills, docs, contracts, workflows, rules and CLAUDE.md; .engine/decisions and .tracking are history and may cite what was. Its corpus is every .rs file under a [workspace] member's src/, read from the root Cargo.toml at run time. A cited path must be in the corpus; a bare basename resolves only when exactly one corpus file bears it, and two or more is a violation that asks for the path. The range must be lines of that file. The identifier cited beside the citation - the nearest identifier-shaped backtick span on the same line outside the citation, else the last one on the non-blank line above, because the real citations wrap - must appear within the range, and the violation names the doc line, the token and the line the identifier is at today. A citation with no identifier in reach is counted and held to file and range only. A path under target/ and a citation of any other extension are outside the population. A root with no Cargo.toml has no corpus and scans nothing: the engine docs a scaffolded project receives cite keel's own source, which that project does not hold, so the claim is made in the self-build alone - the first touched run reddened all 23 scaffold-and-gate tests before this sentence existed. The guard's known-positive is the tree at HEAD before this sprint: both stale citations red, naming line 804; both green once repointed to members/keel-process/src/migrate.rs:804-807.";
        :>> rationale = "A doc line that says where the code is carries the same authority as the doc's verbs and script paths, and those two are already held to the tree by cli-reference and tool-reference; the source citation was the one kind of reference that nothing read. The check is bound to the tree, not to a remembered layout: the corpus is derived from the manifest so a new member's sources enter it without a constant, and the identifier is held to the range so a file that keeps its name but moves its function is caught, which the file-exists check alone would not - migrate.rs still existed and still bore that basename uniquely. The identifier reach of one line above is chosen from the citations that exist: both wrap the citation onto the line after the identifier, and a same-line rule would have made the known-positive green at HEAD. The two issue591 citations are repointed to 804-807 and not 805-807 because line 804 is the one that names check_preconditions and a range that excluded it would fail the guard it was cited to satisfy.";
        :>> consequences = "A living doc that cites a moved or renamed source line is red before commit at the doc line, with the line the identifier is at today, so the fix is a repoint and not a search. Retiring or moving a member's source file reds every living doc that cites it, which is the cost this Decision accepts: the docs are meant to follow the code. Deleting an identifier a doc cites reds the doc too. A citation the guard cannot hold to an identifier - none in reach - is a stated residual held to file and range, not a warning; the count of such citations is visible in the guard's scanned total against the violations, and a later clause may narrow it. The guard count from keel version rises from 75 to 76, guards.md, guard-constraints.sysml and control-map.sysml carry the row, and GUARD_NAMES and the guards member change under the enforcement lock this Decision's marker and D0471's acceptance authorise.";
    }
    #DependsOn dependency from d0514 to d0471;
    #DependsOn dependency from d0514 to d0209;

    // acceptance event (D0121 review-queue sign-off; D0066/D0106 — human-judged, not fabricated)
    verification d0514Accept : Test { :>> id = "fe9915bc-d34c-4cd3-bdb1-1291a8fd7eec"; :>> method = VerificationMethod::confirmation; :>> procedureText = "recorded from chat - their words, verbatim: “Accept all decisions as recommended. Proceed to release and fix downstream” WARN: read-back - the quoted words do not name d0514 (D0201 B); recorded as given (D0423)."; }
    part d0514AcceptR1 : TestResult { :>> id = "08679e16-3d2c-4b38-b158-e2ce91553296"; :>> outcome = VerdictKind::pass; :>> judgedAgainst = "4d00c1bc"; :>> judgedAt = "2026-09-18"; :>> judgedBy = "wweatherholtz"; :>> createdBy = "claudeFable5"; }
}
