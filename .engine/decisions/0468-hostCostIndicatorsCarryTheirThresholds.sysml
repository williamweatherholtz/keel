// D0468 (status: the `status` field below is the truth) — hostCostIndicatorsCarryTheirThresholds: the stop-hook p90 and the git-facts byte length are computed Indicators, each with a declared trigger - 10 000 ms and 8 000 000 bytes - that surfaces named work and gates nothing
// Recorded via `keel record decision` (D0105 RMWX axis; issue054). Acceptance is a separate explicit
// human gate (method=confirmation, D0106): flip status + add the d0468Accept event on sign-off.
package Decision0468 {
    private import EngineElement::*;
    private import EngineWork::*;
    private import EngineVerification::*;
    private import EngineRelationships::*;

    // RESEARCH: issue442 (both measured every fire, owned by no indicator; issue439/440/441 sat visible in the ledger and on disk). D0389: the hook cost is a distribution, never a single figure - the indicator binds its p90, and the phases field says where the time went. D0414: SLOW_FIRE_MS 3000 marks one fire slow. D0333: the triggers contract and what crossing one does. The last 25 stop fires on 2026-09-13: p90 14125 ms, median 7328, 13 of the 14 fires past the receipt with guard:decision-scaffolding on the critical path (4645-12463 ms) - issue520. git-facts.toml 4 055 880 bytes after dcChangedCacheKeepsOneHead; 26.9 MB with 24 MB dead when issue440 was found.
    // #ProspectiveChange (D0070) - this Decision governs a process/schema change; the co-committed
    // change rides the process-change guard's hard lock.
    #ProspectiveChange part d0468 : Decision {
        :>> id = "17dc29cf-7953-4b99-abb5-23c40e7d54c2";
        :>> title = "hostCostIndicatorsCarryTheirThresholds: the stop-hook p90 and the git-facts byte length are computed Indicators, each with a declared trigger - 10 000 ms and 8 000 000 bytes - that surfaces named work and gates nothing";
        :>> createdAt = "2026-09-13";
        :>> createdBy = "claudeFable5";
        :>> status = DecisionStatus::accepted;
        :>> context = "issue442: the per-turn hook cost and the git-facts cache size are measured on every fire (the ledger's ms and phases) and on disk (the file's length), and neither was an Indicator, so no threshold could be declared in indicator-triggers.toml and nothing surfaced when they grew - issue440 sat visible for fourteen commits and issue439/issue441 in the ledger's critical path. dcHookLatencyIsAnIndicator asks for both as computed, direction-aware Indicators with a trigger each. indicator-triggers.toml is under .engine/contracts/, a keystone-locked path, so the two thresholds are recorded here as the Decision the edit is co-committed with; the numbers are a judgment the human can reject, which is why they are a Decision and not a comment in the contract.";
        :>> decision = "NOT A FORK: the DoD fixed both indicators and their direction; this records the two thresholds and their anchors. hookLatencyIndicator binds hook_stop_p90_ms - the 90th-percentile ms by nearest rank over the last 25 stop-hook fires in .keel/metrics/hooks.jsonl, receipt-answered fires included at their real cost - with goal minimize and a trigger of above = 10000. gitFactsSizeIndicator binds git_facts_bytes - the byte length of .keel/cache/git-facts.toml, 0 when absent - with goal minimize and a trigger of above = 8000000. Each trigger's surfaces line names the work: the stop hook's critical path as the ledger's phases attribute it (issue520 at declaration), and the cache's one-head rule. Crossing a trigger surfaces work in keel show indicators and orient's burndown; it gates nothing (D0088), and both remain indicators, never requirements.";
        :>> rationale = "Ten seconds at the p90 is anchored on the figures the Issues were raised on: issue442's known positive was a 5711 ms MEDIAN and issue441's an 8337 ms single fire, with D0414 calling one fire slow at 3000 ms - a p90 past 10 000 says one turn boundary in ten holds the turn longer than either figure that was already judged worth an Issue. Eight megabytes is twice the size the cache settled at once the dead heads were cut, and a third of the size issue440 reached unnoticed; the one-head rule holds the file near four, so twice that is something the rule is not dropping. The p90 rather than the median because a turn boundary is felt at its tail, and the last 25 fires rather than all time because the all-time distribution (652 fires, p99 85 699) carries the cost of guards that no longer exist. The hook indicator triggers on the tree that declares it (14125 > 10000): that is the honest state, not a defect of the threshold - the work it surfaces is tracked as issue520.";
        :>> consequences = "Held proposed for the human (process-change marker, D0337 - the keystone requires the marked Decision for the contract edit; the thresholds themselves gate nothing). Co-committed with the edit: two Indicator items in .tracking/indicators.sysml informing d0389, two trigger sections in indicator-triggers.toml, two metric keys in reports::metric_value read from the ledger and the cache before any model build, pm::recent_event_ms and gitfacts::cache_bytes. What would change it: the hook indicator still triggering after issue520's resolver lands says the threshold is reading a floor the guard set cannot go under, and the number moves with a superseding clause and its own measured anchor; the cache indicator firing with the one-head rule intact says the rule has a gap, not that 8 MB was wrong.";
    }

    // acceptance event (D0121 review-queue sign-off; D0066/D0106 — human-judged, not fabricated)
    verification d0468Accept : Test { :>> id = "02e18dfa-3387-45e2-8ee0-0640aac434f3"; :>> method = VerificationMethod::confirmation; :>> procedureText = "Said in chat 2026-09-14 over the twenty-eighth publish of the decision brief, which carried fifteen held asks; one instruction covers the fourteen non-forks, d0468 among them. The fork d0466 is not covered - it needs an option letter and stays held. - their words, verbatim: “Accept all proposals. Proceed to design with needs, etc.” WARN: read-back - the quoted words do not name d0468 (D0201 B); recorded as given (D0423)."; }
    part d0468AcceptR1 : TestResult { :>> id = "2e04d000-bcc2-4de5-a2e1-637cedc0cb10"; :>> outcome = VerdictKind::pass; :>> judgedAgainst = "d110d0a"; :>> judgedAt = "2026-09-14"; :>> judgedBy = "wweatherholtz"; :>> createdBy = "claudeFable5"; }
}
