// D0466 (status: the `status` field below is the truth) — ruleReadsAtWhichSample: D0464's weighted rule picks 1.1 on the bench's default 50 cases and 1.25 on 100 - which sample does the rule read, or must a challenger win both
// Recorded via `keel record decision` (D0105 RMWX axis; issue054). Acceptance is a separate explicit
// human gate (method=confirmation, D0106): flip status + add the d0466Accept event on sign-off.
package Decision0466 {
    private import EngineElement::*;
    private import EngineWork::*;
    private import EngineVerification::*;
    private import EngineRelationships::*;

    // RESEARCH: Measured 2026-09-13 with .engine/tools/recall_bench.py --sweep, binary keel 0.4.1 build 25e4c04+dirty (knowledge.rs at HEAD, DOMINANCE 1.25; every row sets KEEL_RECALL_DOMINANCE explicitly, so the compiled default does not enter). Default sample, 50 cases, tree 25e4c04, one-hop then two-hop: 0 -> hits 46/50 median position 3 top-3 30/46 mean rows 12, then 20/50 median 5 top-3 2/20 mean rows 13; 1.1 -> 46/50 median 4 top-3 20/46 rows 12, then 24/50 median 3 top-3 15/24 rows 12; 1.25 -> 46/50 median 3 top-3 27/46 rows 12, then 23/50 median 4 top-3 8/23 rows 13; 1.5 -> 46/50 median 3 top-3 30/46, then 20/50 median 5 top-3 2/20. Verdict lines: DISCRIMINATED on KEEL_RECALL_DOMINANCE: median position moved - hits 46..46; median position 3..4 (0=3, 1.1=4, 1.25=3, 1.5=3); top-3 20..30; and: DISCRIMINATED on KEEL_RECALL_DOMINANCE: hits and median position moved - hits 20..24 (0=20, 1.1=24, 1.25=23, 1.5=20); median position 3..5 (0=5, 1.1=3, 1.25=4, 1.5=5). Plain runs of the same binary (compiled 1.25): 46/50 median 3 top-3 27/46 and 23/50 median 4 top-3 8/23 - the 1.25 rows exactly. 100 cases (--cases 100), tree eda9647 (differs from 25e4c04 by two backlog items and two Issues), one-hop then two-hop: 0 -> 89/100 median 2 top-3 57/89 rows 12, then 39/100 median 5 top-3 3/39 rows 12; 1.1 -> 90/100 median 4 top-3 39/90 rows 12, then 53/100 median 3 top-3 31/53 rows 12; 1.25 -> 90/100 median 3 top-3 51/90 rows 12, then 48/100 median 4 top-3 18/48 rows 12. Verdict lines: DISCRIMINATED on KEEL_RECALL_DOMINANCE: hits and median position moved - hits 89..90 (0=89, 1.1=90, 1.25=90); median position 2..4 (0=2, 1.1=4, 1.25=3); top-3 39..57 (0=57, 1.1=39, 1.25=51); and: DISCRIMINATED on KEEL_RECALL_DOMINANCE: hits and median position moved - hits 39..53 (0=39, 1.1=53, 1.25=48); median position 3..5 (0=5, 1.1=3, 1.25=4); top-3 3..31 (0=3, 1.1=31, 1.25=18). Hand set (recall_ab.py, 8 questions, 7 reachable) at the rebuilt binary: 1.25 bar MET 7/7, the rebase question's d0129 at position 8; 1.1 bar MET 7/7, d0129 at position 8; 0 bar NOT MET 6/7, d0129 absent.
    part d0466 : Decision {
        :>> id = "7519fb7c-59f8-48f9-8a5a-61187907bc67";
        :>> title = "ruleReadsAtWhichSample: D0464's weighted rule picks 1.1 on the bench's default 50 cases and 1.25 on 100 - which sample does the rule read, or must a challenger win both";
        :>> createdAt = "2026-09-13";
        :>> createdBy = "claudeFable5";
        :>> status = DecisionStatus::accepted;
        :>> context = "D0464 option B, accepted 2026-09-13, weighted D0364's rule: the highest two-hop hit count subject to the one-hop arm's hits and mean rows holding and its median position moving by at most one, only where the two-hop arm gains at least three hits. Its text predicted, from the sweep at 33c398a, that under the weighted rule 1.25 stands and 1.1 is still refused (median 4 against off's 2). Re-read on the tree as it stands the prediction splits by sample size. On the bench's default 50 cases at 25e4c04, off's one-hop median is 3, not 2, so 1.1 moves it by one (3 to 4), holds hits (46) and rows (12), gains four two-hop hits (20 to 24), and is admissible - and with 24 against 1.25's 23 the rule picks 1.1. On 100 cases at eda9647, off's median is 2 again, 1.1 moves it by two (2 to 4) and is refused, 1.25 moves it by one and gains nine (39 to 48): the rule picks 1.25. The rule as written names no sample size; D0364's original sweep and every sweep since ran at the default. The one-position median move the rule tolerates is the size of the difference between two samples of the same tree, which is what the two readings show.";
        :>> decision = "OPTION A (the rule reads at the bench default, as D0364's did): DOMINANCE moves to 1.1. The plain runs then predict 46/50 median 4 top-3 20/46 and 24/50 median 3 top-3 15/24; the hand set stays 7/7. COST: the near arm - the searcher's ordinary case - loses seven top-3 placements of 46 and one median position at 50 cases, twelve of 90 and two positions at 100, where the same setting breaks the rule's own bound; the constant chases a move that reverses between two samples of one tree. OPTION B (the rule reads at 100 cases): the sample size becomes a clause of the weighted rule, sweeps for this constant run with --cases 100 on both arms, and 1.25 stands (48 against 39, near median 2 to 3, hits 90 held, rows 12 held); the plain runs predict 46/50 median 3 top-3 27/46 and 23/50 median 4 top-3 8/23, which they already print. COST: a clause added after seeing that it favours the incumbent - the fitting D0364 exists to forbid - and every sweep takes about four minutes per setting per arm instead of one. OPTION C (a challenger must win at both 50 and 100): the rule is read at both sizes and the constant changes only where one setting is admissible and highest at both; today no challenger is, and 1.25 stands as the incumbent. COST: the same post-hoc origin as B, doubled sweep time, and a rule under which a setting that is genuinely better at every size the bench can draw but one never lands. DO NOTHING: 1.25 stays with a rule that, read at its default, picks 1.1; issue430's resolver cannot record its pass because its VERIFY clause asks for lines the constant does not print.";
        :>> rationale = "WHY THIS IS THE HUMAN'S: D0464's acceptance words carry both the rule and the reading '1.25 stands', and on the tree as it stands they disagree. Choosing between them is choosing what was accepted - the procedure or its predicted output - and that is theirs. What is mine is the measurement: the split is real, reproducible from the research line with the named binary and trees, and not an artefact of the stale-stamp defect (issue516), because every row sets the knob explicitly and the rebuilt binary's plain runs print the 1.25 rows exactly. What decides it is a value only they hold: whether a one-position median move at the bench's own sample size is a signal the rule should act on (A) or noise the rule should be shielded from (B or C). If reading the model answered that, I would have answered it; the model holds the rule, and the rule is silent on the sample.";
        :>> consequences = "Held proposed for the human through decision-surfacing with both sweeps as the evidence. Under A: knowledge.rs DOMINANCE 1.25 to 1.1 with the two sweeps in its provenance comment, a pass result on dcDominanceRechosenUnderItsOwnRuleDoD once the plain runs print the predicted lines, issue430 resolved; the unit test's DOMINATED case (30 against 10) still holds. Under B or C: the constant unchanged, the provenance comment gaining the re-choice and the sample clause, a pass result on the same DoD quoting the 100-case lines, issue430 resolved; recall_bench.py's --sweep gains no flag (--cases 100 exists). Until they answer the constant stays 1.25, D0464's two SupersedeClause edges on D0364 and D0365 stand as accepted, and the provenance comment in knowledge.rs is not rewritten, because the wording it would carry depends on the answer.";
    }

    // the weighted rule this Decision reads at two samples
    #DependsOn dependency from d0466 to d0464;

    // option B taken 2026-09-14 (d0466AcceptR1): the weighted rule reads at 100 cases; DOMINANCE 1.25 stands, the sample clause lives in knowledge.rs's provenance comment
    // acceptance event (D0121 review-queue sign-off; D0066/D0106 — human-judged, not fabricated)
    verification d0466Accept : Test { :>> id = "e8a00f8b-7914-44c0-b7f9-e2110d05e323"; :>> method = VerificationMethod::confirmation; :>> procedureText = "Option B chosen in chat 2026-09-14 after the metric was explained in plain terms (recall bench near/far arms, DOMINANCE bonus, the 50-vs-100 split); the recommended course - their words, verbatim: “Sure accept B then.”"; }
    part d0466AcceptR1 : TestResult { :>> id = "8b8fedf8-f55e-4394-9598-0fe235428f5b"; :>> outcome = VerdictKind::pass; :>> judgedAgainst = "2beaa66"; :>> judgedAt = "2026-09-14"; :>> judgedBy = "wweatherholtz"; :>> createdBy = "claudeFable5"; }
}
