// D0523 (status: the `status` field below is the truth) — A verb fold travels with migrate: the spelling a retired verb has today is one shipped fact, the guard names it and migrate writes it into the project's own living docs
// Recorded via `keel record decision` (D0105 RMWX axis; issue054). Acceptance is a separate explicit
// human gate (method=confirmation, D0106): flip status + add the d0523Accept event on sign-off.
package Decision0523 {
    private import EngineElement::*;
    private import EngineWork::*;
    private import EngineVerification::*;
    private import EngineRelationships::*;

    // #ProspectiveChange (D0070) - this Decision governs a process/schema change; the co-committed
    // change rides the process-change guard's hard lock.
    #ProspectiveChange part d0523 : Decision {
        :>> id = "fd8a1d2e-e5c5-4746-8ddc-b54c8ae5579f";
        :>> title = "A verb fold travels with migrate: the spelling a retired verb has today is one shipped fact, the guard names it and migrate writes it into the project's own living docs";
        :>> createdAt = "2026-09-18";
        :>> createdBy = "claudeFable5";
        :>> status = DecisionStatus::accepted;
        :>> context = "The downloaded v0.5.0 binary, run over a tree `keel init` 0.4.1 had scaffolded (issue622), applied its resync and rolled itself back on `[guard:cli-reference] FAIL - 16 violation(s)`. Every violation sat in a file the run never writes: the adopter's CLAUDE.md, where the 0.4.1 scaffold template said `keel orient`, `keel validate`, `keel add-task`, `keel report`; and the comments of attestation-policy.toml and github-actors.toml, the two contracts is_project_owned_contract (members/keel-process/src/migrate.rs:112) rightly keeps from the resync. Read against this tree: the five folds that retired those spellings (the lens router D0273, the render fold, D0449 gating, D0450 channel, D0451 authoring) each shipped a committed Python transform over THIS repository's call sites and made cli-reference (issue528) stricter; none carried the fold into a downstream project's own text, and CLAUDE.md is outside migrate's scope altogether (restore at migrate.rs:1055 covers .engine .tracking .claude). The guard then fails the adopter inside the run on words the engine itself wrote at 0.4.1, and the run reverts with no action the adopter can take but hand-editing what the guard names. Their direction stands (st167, st168): migrate is blocked in many projects; migration should be smooth; make downstream projects whole.";
        :>> decision = "The spelling this binary dispatches for a retired top-level verb is ONE authored fact with two readers. A lens (`orient` -> `show orient`) and a verb one router declares under the same name (`validate` -> `gate validate`) are computed from the CLI facts as today; a verb a fold RENAMED (`add-task` -> `record task`, `github-decider` -> `github decider`, `report` -> `render report`) is a row of the engine-shipped contract `.engine/contracts/verb-renames.toml`, read from the binary's embedded copy so a tree's older copy never answers for it. Reader one: guard cli-reference's `today it is` clause names that spelling for every retired verb it can, renamed ones included. Reader two: `keel migrate` gains a `verb-respell` step, planned after the resync, that rewrites in every living doc the guard reads and the resync does not write in this plan - CLAUDE.md, the project-owned contracts, a project-added file under .engine/ - exactly the references the guard would fail and a spelling exists for, one reported edit per file; a reference with no spelling stays as written and the guard still names it. CLAUDE.md joins the run's scope for what the run may now write: the door's cleanliness check and the rollback's restore, the latter only when the pre-run commit holds the file. Reader two writes locked paths - a project-owned contract is under .engine/contracts/ - so the process-change lock treats a locked file whose text is exactly the respell of its own HEAD text as the engine arriving, the D0441 resync exemption one step on: decided by content, one edited byte beyond the fold puts it back under the lock.";
        :>> rationale = "Discounting the pre-existing red instead (the D0522 shape) would let the run land and leave the adopter's own `keel gate guard` red on cli-reference until they hand-edit, which is honest state but not whole; rewriting makes the docs true and the guard green in one run, and it is the same class of transform migrate already performs on the project's `.tracking` records (retype, order drop). Rewriting exactly the guard's population - code spans and command-shaped phrases - keeps the step and the guard congruent: the step is green precisely where the guard would be, and prose that merely mentions a verb is left alone as the guard leaves it. A shipped contract rather than a Rust table because a retired verb's current spelling is a CLI-surface fact (D0271) a reader may inspect and the resync may update; embedded rather than read from the tree because the tree being migrated is by definition the older vintage. Idempotent by construction: a rewritten reference names a verb the binary dispatches, so it is never a defect again.";
        :>> consequences = "Backlog task dcVerbFoldsTravelWithMigrate delivers this in sprint 746 and resolves issue622; the guard message change rides this Decision under the process-change lock (D0209 cl.2). Every future fold that renames a verb adds its row to verb-renames.toml in the same commit, and the fold's own transform over this repository stays as it is. The released 0.5.0 carries the defect, so a 0.5.1 follows for adopters to receive the step; GH#86-90 are answered naming it. Stated residual: a retired verb the table does not name is still a red the adopter must edit by hand, and the guard names the line. HELD proposed under D0337 for the human's word; applied under the marker in the same commit as D0519 and D0522 were.";
    }
    #DerivedFrom dependency from d0523 to st167;
    #DerivedFrom dependency from d0523 to st168;

    // acceptance event (D0121 review-queue sign-off; D0066/D0106 — human-judged, not fabricated)
    verification d0523Accept : Test { :>> id = "14d64f76-9929-4fb8-8201-601aeae98c8c"; :>> method = VerificationMethod::confirmation; :>> procedureText = "recorded from chat - their words, verbatim: “Accept: the spelling a retired verb has today is one shipped contract read from the binary's embedded copy; guard cli-reference names it and keel migrate's verb-respell step rewrites the adopter's own living docs, CLAUDE.md joining the run's scope and the lock treating an exact respell of HEAD as the engine arriving (recommended)”"; }
    part d0523AcceptR1 : TestResult { :>> id = "e7eea14d-a0d4-4b65-a093-443a3b3d9b65"; :>> outcome = VerdictKind::pass; :>> judgedAgainst = "ba665ec0"; :>> judgedAt = "2026-09-19"; :>> judgedBy = "wweatherholtz"; :>> createdBy = "claudeFable5"; }
}
