// D0507 (status: the `status` field below is the truth) — The governance processes are a member above the guards and the tooling, and the validate authority descends to the read model
// Recorded via `keel record decision` (D0105 RMWX axis; issue054). Acceptance is a separate explicit
// human gate (method=confirmation, D0106): flip status + add the d0507Accept event on sign-off.
package Decision0507 {
    private import EngineElement::*;
    private import EngineWork::*;
    private import EngineVerification::*;
    private import EngineRelationships::*;

    part d0507 : Decision {
        :>> id = "878d4ecf-f2ab-4840-9d31-21e13f3d6192";
        :>> title = "The governance processes are a member above the guards and the tooling, and the validate authority descends to the read model";
        :>> createdAt = "2026-09-17";
        :>> createdBy = "claudeFable5";
        :>> status = DecisionStatus::accepted;
        :>> context = "Sprint 736 (dcProcessIsAMember, chartered by D0479) moves process_cmd, library, adoption_check, migrate, workspace, sync, status and currency out of keel-cli into members/keel-process. The DoD's prose places the member on keel-view and below and names activation and onboard among its modules; its own probe says an edit to serve.rs leaves keel-process Fresh and advance, activate and show status behave identically. Three facts of the tree bear on that prose. workspace.rs runs the guards (keel_guards::run_all_timed, staged_marked_decision, is_locked_path) and reads the guard receipt; status.rs runs them too and reads the hook binary's describe; sync.rs runs the touched set before a land (keel_suite::touched::before_gate). activation and onboard have been keel-model's since sprint 718 because the guards, the views and the write API read them. And workspace.rs calls validate_root, which lived in keel-cli/src/lib.rs beside the orient API, so a member cannot reach it. currency.rs called crate::github_ingest::pull_cmd, and D0480 makes the intake keel-issues', never keel-process's.";
        :>> decision = "The member sits above what it runs. keel-process depends on keel-guards, keel-suite, keel-view, keel-write, keel-model and the leaves (cargo tree -p keel-process --depth 1), because the workspace gate, status and land ARE the processes that run the gates and the touched set - a process crate below the guards would have to be handed every gate it runs as a parameter, which restates the dependency without removing it. activation and onboard stay in keel-model, where their readers below the process layer are. The validate authority - Report, check_files, validate_root, validate_engine_instances and their tests - descends from keel-cli/src/lib.rs to members/keel-model/src/validate.rs, moved whole by scripts/extract_process.py in three anchored slices, and keel-cli re-exports the four at their old paths; the orient API and walk_longest stay. currency::cmd takes its GitHub pull as a parameter (&dyn Fn(&[String], &Path) -> i32) and main.rs hands it keel_cli::github_ingest::pull_cmd, so the process member depends on neither the intake nor the server. Every one of the eight modules keeps its crate:: path through keel-cli's lib.rs re-exports; keel --help is byte-identical and keel version's guard line unchanged.";
        :>> rationale = "D0479's rule is that a fact lives where its readers are, and the readers of the gate runner include the processes that gate a workspace and report a status - the layering the DoD's prose wanted (process below guards) would invert that for the sake of a dependency count, and the sprint's own probe never asked for it: an edit to serve.rs leaves keel-process Fresh whichever side of the guards it sits on, because serve.rs is keel-cli's. When a DoD's prose and its probe disagree, the probe is the contract (sprints 734 and 735 read the same rule). The validate descent is the smaller move that makes the larger one compile - the workspace gate cannot call into the binary crate above it - and it lands the authority beside the corpus walk it reads, which is the read model's already. The pull parameter is the one inversion that keeps D0480's boundary honest: the intake will be keel-issues', and a process crate that imported it today would have to be edited again when it moves.";
        :>> consequences = "keel-cli/src loses eight modules (5,889 lines) and the validate authority; members/keel-process is the sixth member above the leaves, keel-model gains validate.rs. Two integration tests that read adoption_check.rs by include_str! follow the file. cargo clippy --release --workspace --all-targets -- -D warnings is clean; keel --help byte-identical (cmp, 15089 bytes); keel version guards 75 (66 hard-blocking, 9 warning-only); modgraph --check and module_home --probe hold. Known-positive, chosen before the tree is read: touching keel-cli/src/serve.rs leaves keel-process Fresh under cargo build --release --verbose while keel-cli recompiles, and advance's unit tests, the activation and status integration tests and the member's own tests pass (pos736.py). Known-negative: a pub use keel_cli::serve planted in the member's lib.rs fails cargo check naming the undeclared crate keel_cli, restored bytes and mtime on every path (neg736.py). Wrong if a later extraction needs the validate authority below keel-model: it depends on keel-parser and the corpus walk only, so it can descend again without a caller moving. NOT A FORK: the alternative, a process crate below the guards, fails to compile against the gates it runs and the DoD's probe does not ask for it. NOT A PROCESS CHANGE: no gate, guard, workflow or locked path is edited; every path in the diff is source under keel-cli/src, members/keel-model, members/keel-process, two tests and the manifests.";
    }

    // acceptance event (D0121 review-queue sign-off; D0066/D0106 — human-judged, not fabricated)
    verification d0507Accept : Test { :>> id = "fdeed412-bbb4-4709-99b5-e3a69b6b2350"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0507AcceptR1 : TestResult { :>> id = "505f6e2c-a448-4279-8039-dc7208ffafc8"; :>> outcome = VerdictKind::pass; :>> judgedAgainst = "01f7ad00"; :>> judgedAt = "2026-09-17"; :>> judgedBy = "wweatherholtz"; :>> createdBy = "claudeFable5"; }
}
