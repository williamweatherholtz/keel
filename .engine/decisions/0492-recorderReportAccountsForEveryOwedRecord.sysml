// D0492 (status: the `status` field below is the truth) — The recorder's report is refused when it accounts for fewer records than the dispatch owed, or for none
// Recorded via `keel record decision` (D0105 RMWX axis; issue054). Acceptance is a separate explicit
// human gate (method=confirmation, D0106): flip status + add the d0492Accept event on sign-off.
package Decision0492 {
    private import EngineElement::*;
    private import EngineWork::*;
    private import EngineVerification::*;
    private import EngineRelationships::*;

    // #ProspectiveChange (D0070) - this Decision governs a process/schema change; the co-committed
    // change rides the process-change guard's hard lock.
    #ProspectiveChange part d0492 : Decision {
        :>> id = "abc138b8-df63-42e7-8513-e7fb025c8301";
        :>> title = "The recorder's report is refused when it accounts for fewer records than the dispatch owed, or for none";
        :>> createdAt = "2026-09-15";
        :>> createdBy = "claudeFable5";
        :>> status = DecisionStatus::accepted;
        :>> context = "Sprint 723's first RECORDER (D0425: haiku, no Write or Edit tool) was dispatched with seven owed records - one record result and six record gate-result - and the verifier's receipt reading DISCREPANCIES: NONE. Its first act, a heredoc composing its report, was denied by the pre-bash hook for a backslash in the receipt path (D0309); it then composed a three-line report with printf - the header, DISCREPANCIES: NONE, the gate line - ran no keel record command, and check_report.py passed it: no typed or undeclared marker, every write a keel record sub-verb written once, report ends with the gate's last line. The sprint file held no TestResult (grep -c verdict = 0). The five refusals of D0473 each read the WROTE: lines that ARE there; none reads what is absent, so a report accounting for nothing was indistinguishable from a report over nothing owed, and every write a keel record sub-verb was vacuously true. The brief's list of owed records was text the checker never saw - a reminder, which D0047 says is not a control. issue568 (High) is the finding; a second recorder, dispatched with the count stated, wrote all seven.";
        :>> decision = "check_report.py takes --owed N, the count of records the dispatch named, and refuses a recorder report whose WROTE: lines plus REFUSED: lines number fewer than N, naming the shortfall (owed 7, accounted 6). With or without --owed it refuses a report with zero WROTE: lines and no REFUSED: line: a recorder dispatched with nothing to write does not exist, so such a report is a recorder that did nothing and said NONE. The recorder brief in the delegated-ceremony skill passes --owed <count> and the process step dcyRecorderReport says so.";
        :>> rationale = "The report is the one surface a control reads after the recorder's writes, and D0473 made it refuse what the report admits; sprint 723 showed it must also refuse what the report omits. The count of owed records is a fact the primary states at dispatch and the recorder cannot lose - each record is one WROTE line or one REFUSED line - so the shortfall is decidable from the text the recorder already returns, at no cost to a recorder that did its work. Refusing at the report keeps the D0425 shape: the recorder writes the record it missed or reports it under REFUSED, and the primary triages. MEASURED on this Windows 11 host: the checker before the change passed sprint 723's first report as returned (exit 0); after the change it refuses it naming zero WROTE: lines and no REFUSED: line (exit 1); under --owed 7 the second recorder's seven-line report passes and the same report with one gate line removed is refused naming owed 7, accounted 6; the five D0473 pairs hold unchanged, so eight pairs hold. NOT A FORK: the alternative is a guard over the sprint file for a ceremony gate with no result at the commit, which fires after the primary has already trusted the report and commits a sprint with no results one step before the sprint-closure gate catches it; the report is where the omission is visible first, and the count is already in the primary's hands.";
        :>> consequences = ".engine/skills/delegated-ceremony/references/check_report.py carries seven refusals and a probe over eight fixtures, three of them sprint 723's own reports and cuts of them; PAIRS rows carry the owed count the fixture is checked under. The recorder brief in SKILL.md passes --owed <count> and states the rule in its own words; .claude is regenerated by sync-claude. A dispatch that states no count still gets refusal 6; a report short of the stated count is returned to the recorder, never to the primary. Resolves issue568 through dcRecorderReportAccountsForEveryOwedRecord.";
    }

    // acceptance event (D0121 review-queue sign-off; D0066/D0106 — human-judged, not fabricated)
    verification d0492Accept : Test { :>> id = "e4aca008-4c9b-4d5c-93d1-36ca690b5f01"; :>> method = VerificationMethod::confirmation; :>> procedureText = "recorded from chat - their words, verbatim: “Accept the owed-count check on the recorder's report. [x] Accept: check_report.py takes --owed N and refuses a recorder report whose WROTE plus REFUSED lines number fewer than N, and with or without --owed refuses a report with zero WROTE lines and no REFUSED line; the recorder brief passes the count (recommended)”"; }
    part d0492AcceptR1 : TestResult { :>> id = "0e495742-91f6-40ee-84b2-bff7ce00d4eb"; :>> outcome = VerdictKind::pass; :>> judgedAgainst = "444333d"; :>> judgedAt = "2026-09-15"; :>> judgedBy = "wweatherholtz"; :>> createdBy = "claudeFable5"; }

    // grounded (D0098 rootedness): this Decision serves the Need that a pass is never AI testimony alone -
    // st065, the human's words behind the D0425 ceremony line (verifier, recorder, ladder, rendered receipt)
    #DerivedFrom dependency from d0492 to nVerificationByAuthorityAndMethod;
}
