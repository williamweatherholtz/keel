// D0500 (status: the `status` field below is the truth) — The probe pair travels in a file - keel verify --probe-from FILE reads the known-positive then the known-negative from two lines the primary wrote, and any other shape is refused before a rung runs
// Recorded via `keel record decision` (D0105 RMWX axis; issue054). Acceptance is a separate explicit
// human gate (method=confirmation, D0106): flip status + add the d0500Accept event on sign-off.
package Decision0500 {
    private import EngineElement::*;
    private import EngineWork::*;
    private import EngineVerification::*;
    private import EngineRelationships::*;

    // #ProspectiveChange (D0070) - this Decision governs a process/schema change; the co-committed
    // change rides the process-change guard's hard lock.
    #ProspectiveChange part d0500 : Decision {
        :>> id = "b275cc6e-245e-4d22-a2a7-60c53059c552";
        :>> title = "The probe pair travels in a file - keel verify --probe-from FILE reads the known-positive then the known-negative from two lines the primary wrote, and any other shape is refused before a rung runs";
        :>> createdAt = "2026-09-16";
        :>> createdBy = "claudeFable5";
        :>> status = DecisionStatus::accepted;
        :>> context = "The D0388 pair reaches the pre-commit ladder through the VERIFIER's transcription of its dispatch into `keel verify --probe POSITIVE,NEGATIVE`, and twice in two sprints the transcription was wrong (issue571): sprint 724's first dispatch named the bare checker runs, whose positive side exits 1 by design, and sprint 725's first verifier passed the two test NAMES as the two sides instead of the two `cargo test ... -- <name>` command lines the dispatch spelled out. Sprint 729's first dispatch did it a third time (its retro names it). Each time the ladder refused at the probe rung after an 80-second climb, the verifier reported a red no check produced, and the sprint paid a full re-dispatch. The pair is chosen by the PRIMARY before the tree is read (D0388); the verifier is only meant to NAME it. A comma-separated shell argument is the wrong carrier for two command lines: it is retyped by a second actor, it cannot hold a comma, and the receipt cannot say where it came from. D0224 already moved every other prose argument into a file for the same reason.";
        :>> decision = "keel verify takes --probe-from FILE beside --probe POSITIVE,NEGATIVE. The file holds exactly two non-empty lines: the known-positive command line, then the known-negative. It is written by the primary - the actor who chose the check and both cases before reading the tree - and the verifier's dispatch names its path; the verifier never transcribes the pair. A file with any other line count, a blank line, or --probe given beside --probe-from is refused at parse, before any rung runs, the way --probe a, is refused today; the receipt's probe rung row names the file and both lines. The verifier brief's pair slot becomes the file's path and the test-verify skill's launch line, probe section and receipt shape say so. --probe POSITIVE,NEGATIVE stays for a human at a terminal.";
        :>> rationale = "The defect was never the pair - every named pair was correct in the primary's dispatch - it was a second actor retyping two command lines into a comma-separated argument. Removing the transcription removes the failure class instead of asking a haiku verifier to be more careful, which is the reminder D0047 refuses. A file is the carrier every other prose argument already uses (D0224), it can be diffed against the dispatch, and it survives a comma inside a command line. Refusing at parse rather than at the rung is what turns a wrong file into a two-second refusal that names its shape instead of an eighty-second climb that names `program not found`. The refusal of both flags together is deliberate: two sources for one pair is the ambiguity the file exists to remove. This is a process change - the verifier brief and the test-verify skill change - so the record is held for the human under D0337.";
        :>> consequences = "verify.rs gains the file read and a parsed pair that carries its source; own_args skips the flag's value so the path is never taken for a root; --wait refuses --probe-from beside it as it refuses --probe. The CLI fact for keel verify names the flag. The delegated-ceremony verifier brief's pair slot reads `the pair file at <ABS PATH> (two lines, positive then negative, written by the primary)` and test-verify's step 1 launches `keel verify . --probe-from <PATH>`. Known-positive, chosen before the tree is read: a file whose two lines are the cargo test command lines for two touched::tests filters climbs the probe rung green and the rung row names the file and both lines. Known-negative: a one-line file, a three-line file, a file whose second line is blank, and --probe beside --probe-from are each refused at parse with exit 2 and no receipt written. Wrong if a verifier needs to choose its own pair - it never does; the pair is the primary's under D0388. Resolves issue571; delivered by dcProbePairTravelsInAFile.";
    }

    // acceptance event (D0121 review-queue sign-off; D0066/D0106 — human-judged, not fabricated)
    verification d0500Accept : Test { :>> id = "7aed0509-dab9-49b1-be4b-0d66f3a751d7"; :>> method = VerificationMethod::confirmation; :>> procedureText = "recorded from chat - their words, verbatim: “Accept all decisions as recommended. Proceed to release and fix downstream” WARN: read-back - the quoted words do not name d0500 (D0201 B); recorded as given (D0423)."; }
    part d0500AcceptR1 : TestResult { :>> id = "5eeb5394-600b-45fb-94f1-996400a526b9"; :>> outcome = VerdictKind::pass; :>> judgedAgainst = "4d00c1bc"; :>> judgedAt = "2026-09-18"; :>> judgedBy = "wweatherholtz"; :>> createdBy = "claudeFable5"; }

    // grounded (D0098 rootedness): this Decision serves the Need that a pass is never AI testimony alone -
    // st065, the human's words behind the D0425 ceremony line (verifier, recorder, ladder, rendered receipt)
    #DerivedFrom dependency from d0500 to nVerificationByAuthorityAndMethod;
}
