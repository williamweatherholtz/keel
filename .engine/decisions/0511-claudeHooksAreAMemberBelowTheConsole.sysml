// D0511 (status: the `status` field below is the truth) — The Claude hooks are member keel-hooks, below the console and the item member and above everything they read; project discovery from the current directory is the process layer's
// Recorded via `keel record decision` (D0105 RMWX axis; issue054). Acceptance is a separate explicit
// human gate (method=confirmation, D0106): flip status + add the d0511Accept event on sign-off.
package Decision0511 {
    private import EngineElement::*;
    private import EngineWork::*;
    private import EngineVerification::*;
    private import EngineRelationships::*;

    part d0511 : Decision {
        :>> id = "5abb3447-a3f0-4db4-9c6c-fb6bf15e3947";
        :>> title = "The Claude hooks are member keel-hooks, below the console and the item member and above everything they read; project discovery from the current directory is the process layer's";
        :>> createdAt = "2026-09-17";
        :>> createdBy = "claudeFable5";
        :>> status = DecisionStatus::accepted;
        :>> context = "Sprint 739 (dcHooksAreAMember, chartered by D0479) is the ninth D0479 extraction and the first to slice main.rs itself rather than move whole files: the keel hook body (stop, post-edit, pre-bash, pre-write, config-change, subagent-stop, prompt), its override and ledger helpers, the two recall constants the prompt hook shares with keel recall, and the two hook test modules leave keel-cli/src/main.rs for members/keel-hooks/src/lib.rs, and shellcheck.rs and proactive.rs move beside them. The block was 1246 of main.rs's 6187 lines and read fifteen keel_cli module paths across the write, view, guards, actor, perf, model, suite and git members. Two helpers the block calls, find_repo_root (the cwd walk to .engine, issue281) and engine_version_skew (the D0190 pin warning), were defined in main.rs as dispatch-level helpers and are called by hooks and by the binary alike; a member cannot call into the binary crate, so they needed a home below both. dcKeelCliIsThinDispatch's DoD asks for main.rs under 800 lines with every cmd_ body in the member owning its verb; the hooks are the one body whose verb has no owning member, so the split creates it. The hook dispatch line in main.rs (Some('hook') => cmd_hook(rest)) is unchanged, keel-cli/src/main.rs is outside the enforcement-surface lock (is_enforcement_surface, members/keel-guards/src/lib.rs, asserts main.rs is NOT locked), and no guard, hook script, CI workflow or rule changes.";
        :>> decision = "Member keel-hooks holds the keel hook body, the override and ledger helpers, the recall constants, the two hook test modules, shellcheck and proactive; it depends on keel-perf, keel-git, keel-actor, keel-model, keel-write, keel-view, keel-guards, keel-suite and keel-process and is depended on by keel-cli alone - it sits below keel-serve and keel-issues in the root manifest and neither names it. find_repo_root and engine_version_skew are keel_process::workspace pub fns beside require_project: project discovery from the current directory is the process layer's, and every member that resolves a project from cwd reads it there. keel-cli's lib.rs re-exports keel_hooks as hooks and shellcheck and proactive at their old paths; main.rs imports the eight names it still calls (cmd_hook, ledger_gate, ledger_refused, refused_injected_prose, override_path, override_target, OVERRIDE_TTL_SECS, RECALL_BUDGET) and the two workspace helpers, so no other caller moved and keel --help is byte-identical. The transform is scripts/extract_hooks.py, dry-run by default, idempotent, printing its reconciliation (files moved, slices conserved out of main.rs, fns and consts published, anchored edits) before it writes.";
        :>> rationale = "D0479's rule is that a fact lives where its readers are. The hooks are read by nothing in the engine - Claude Code invokes them through the binary and they read every layer below - so their home is a member just under the console, and the console does not read them either, so neither depends on the other and both are leaves the binary alone gathers. Slicing main.rs instead of moving a file is forced by the block's shape: cmd_hook was never its own module, and the thin-dispatch DoD counts main.rs lines, so the body has to leave the file, not be renamed within it. The two discovery helpers go to keel-process rather than keel-hooks because the binary's own root_arg path and the process member's require_project already walk the same directories; a copy in keel-hooks would be the two-vocabularies class, and a home in keel-hooks would make the binary read discovery from the hooks. NOT A PROCESS CHANGE: code structure only - the hook dispatch path, the guard set, the hook scripts under .githooks and .claude, the CI workflows and the rules are byte-for-byte what they were, and the one locked path this extraction approaches (keel-cli/src/adherence.rs, GUARD_SOURCE_FILES) stays where it is for the thin-dispatch sprint to move under its own marked Decision. NOT A FORK: the alternatives - the hook body renamed into a keel-cli module and left in the binary, the discovery helpers duplicated into keel-hooks, or the hooks folded into keel-serve - each fail the thin-dispatch line count, the one-home rule or the console-reads-nothing-of-the-hooks fact, and nothing here is left for a later choice.";
        :>> consequences = "members/keel-hooks holds lib.rs (1455 lines), shellcheck.rs and proactive.rs under the member lint preamble, with build = ../../keel-cli/build.rs for the KEEL_BUILD_COMMIT the console-liveness probe embeds; main.rs is 4726 lines (from 6187); members/keel-process/src/workspace.rs gains the two pub must_use helpers. cargo tree -p keel-hooks names no keel-cli, keel-serve or keel-issues; touching members/keel-hooks/src/lib.rs recompiles keel-hooks and keel-cli with sixteen members Fresh; twenty keel-hooks unit tests pass; scripts/modgraph.py --check and scripts/module_home.py --probe hold. dcKeelCliIsThinDispatch now depends on dcHooksAreAMember and is the next extraction: cursor, history and enroll to keel-process, adherence to the guards member under a process-change Decision because GUARD_SOURCE_FILES names it, and every remaining cmd_ body to the member owning its verb.";
    }

    // acceptance event (D0121 review-queue sign-off; D0066/D0106 — human-judged, not fabricated)
    verification d0511Accept : Test { :>> id = "4f866c7e-5852-4053-bb9b-47a2e2610973"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0511AcceptR1 : TestResult { :>> id = "093ef8b9-9711-46db-b482-031b6747c4ee"; :>> outcome = VerdictKind::pass; :>> judgedAgainst = "2ffa64b4"; :>> judgedAt = "2026-09-17"; :>> judgedBy = "wweatherholtz"; :>> createdBy = "claudeFable5"; }
    #DependsOn dependency from d0511 to d0479;
}
