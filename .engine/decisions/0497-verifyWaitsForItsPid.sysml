// D0497 (status: the `status` field below is the truth) — The wait for a launched ladder is a command, keel verify --wait - it blocks while the receipt's writer pid is alive, prints the finished table, and reports a dead writer as KILLED during <rung>, never as a verdict
// Recorded via `keel record decision` (D0105 RMWX axis; issue054). Acceptance is a separate explicit
// human gate (method=confirmation, D0106): flip status + add the d0497Accept event on sign-off.
package Decision0497 {
    private import EngineElement::*;
    private import EngineWork::*;
    private import EngineVerification::*;
    private import EngineRelationships::*;

    // #ProspectiveChange (D0070) - this Decision governs a process/schema change; the co-committed
    // change rides the process-change guard's hard lock.
    #ProspectiveChange part d0497 : Decision {
        :>> id = "a39854bd-5ad8-4a79-b41f-de80866972b4";
        :>> title = "The wait for a launched ladder is a command, keel verify --wait - it blocks while the receipt's writer pid is alive, prints the finished table, and reports a dead writer as KILLED during <rung>, never as a verdict";
        :>> createdAt = "2026-09-16";
        :>> createdBy = "claudeFable5";
        :>> status = DecisionStatus::accepted;
        :>> context = "The sprint 726 VERIFIER launched the D0476 ladder detached, read .keel/metrics/verify-receipt.toml 17 seconds later, found the outcome = 'running' stub the launch writes (D0387), and reported a green 718-second ladder as killed (issue575). The test-verify skill's step 4 was headed 'ONLY after the process exits' and step 5 opened with a sentence telling the reader to wait until tasklist showed no cargo and the output file ended with the summary line. That sentence was the whole control, and a subagent skipped it; a control that is a sentence has no way to refuse a reader who does not wait (D0047). The receipt already carries what a wait needs: since D0493 the running stub names its writer's pid, and touched::pid_alive answers whether that pid lives on this host. What was missing was one command that turns those two facts into blocking, so that reading early is not possible rather than not advised.";
        :>> decision = "keel verify --wait [ROOT] launches nothing. It reads .keel/metrics/verify-receipt.toml; while the receipt says running and its pid is alive it blocks, printing one line per rung change (in flight: <rung>, pid N alive, N s); when the writer exits it prints the finished rung table and exits as the ladder did (0 green, the red rung's own code otherwise). A running receipt whose pid is gone is KILLED during <rung>, exit 2 - a verdict on neither side; no receipt at all is exit 2 naming that nothing was launched. --probe or --no-receipt beside --wait is refused: they belong to the launch. The test-verify skill's steps 4 and 5 each open with that one command in place of the prose wait, and the CliCommand fact for verify names the flag (D0271).";
        :>> rationale = "The verifier's failure was not a wrong reading of the receipt - the stub really did say running - it was reading at a time the skill's prose forbade. Moving the wait into the binary makes the early read impossible instead of forbidden: --wait returns only a finished ladder or a named death, so the one output a hasty reader can copy into a receipt is a true one. The three states are separated by liveness rather than by time because time is what sprint 726 misjudged: a stub with a live writer is in flight however old it is, and a stub with a dead writer is a killed ladder however fresh. The wait is pure over the receipt text and a liveness answer (wait_state in keel-cli/src/verify.rs), so its D0388 pair runs without launching anything - a running stub with a dead child pid is KILLED, a finished green receipt is the table with exit 0, this process's own pid is in flight - and lives in the verify module's unit tests. This is a process-change: the test-verify skill is the VERIFIER's procedure under D0425/D0438 and its steps change, so the edit is co-committed with this Decision under the CR: prefix and the Decision is held for the human under D0337.";
        :>> consequences = "keel-cli/src/verify.rs gains WaitState, wait_state, report and wait; keel verify's own run prints through the same report, so the two surfaces cannot show different tables. The verify fact in .engine/cli/commands.sysml and its mirror in members/keel-schema/src/cli_facts.rs name the flag; CLAUDE.md section 5 lists the command; the test-verify skill's steps 4 and 5 open with it, and keel sync-claude carries the copy. The recorder's receipt reading is unchanged: it still copies the table the verifier writes. Delivered by dcVerifyWaitsForItsPid, which resolves issue575. Nothing changes for a keel verify run without the flag.";
    }

    // acceptance event (D0121 review-queue sign-off; D0066/D0106 — human-judged, not fabricated)
    verification d0497Accept : Test { :>> id = "5cb3c55d-1d48-4b57-8d4c-bd38ecf4c0a5"; :>> method = VerificationMethod::confirmation; :>> procedureText = "recorded from chat - their words, verbatim: “Accept all decisions as recommended. Proceed to release and fix downstream” WARN: read-back - the quoted words do not name d0497 (D0201 B); recorded as given (D0423)."; }
    part d0497AcceptR1 : TestResult { :>> id = "4158ad75-3ead-4ce4-8ab0-e9821a033e41"; :>> outcome = VerdictKind::pass; :>> judgedAgainst = "4d00c1bc"; :>> judgedAt = "2026-09-18"; :>> judgedBy = "wweatherholtz"; :>> createdBy = "claudeFable5"; }
}
