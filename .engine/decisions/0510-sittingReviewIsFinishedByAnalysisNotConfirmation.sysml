// D0510 (status: the `status` field below is the truth) — sittingReviewIsFinishedByAnalysisNotConfirmation: a sitting review is finished by the AI as method=analysis, like the retro; the human's word is recorded only where it is irreducible - keel accept on a Decision, keel judge-set on a proposed result, a disposition on a finding - never as 'the review is done'
// Recorded via `keel record decision` (D0105 RMWX axis; issue054). Acceptance is a separate explicit
// human gate (method=confirmation, D0106): flip status + add the d0510Accept event on sign-off.
package Decision0510 {
    private import EngineElement::*;
    private import EngineWork::*;
    private import EngineVerification::*;
    private import EngineRelationships::*;

    // #ProspectiveChange (D0070) - this Decision governs a process/schema change; the co-committed
    // change rides the process-change guard's hard lock.
    #ProspectiveChange part d0510 : Decision {
        :>> id = "06bd477d-284b-40df-85dc-f21451dc31b3";
        :>> title = "sittingReviewIsFinishedByAnalysisNotConfirmation: a sitting review is finished by the AI as method=analysis, like the retro; the human's word is recorded only where it is irreducible - keel accept on a Decision, keel judge-set on a proposed result, a disposition on a finding - never as 'the review is done'";
        :>> createdAt = "2026-09-17";
        :>> createdBy = "claudeFable5";
        :>> status = DecisionStatus::accepted;
        :>> context = "The human asked, 2026-09-17: 'change the method for finishing a review to not be confirmation. what should there be to confirm? on a sprint review'. The per-sitting review (D0049 clause 3, sharpened by D0051) is the one ceremony record whose method is confirmation: the sprint-review skill records `verification sittingRev<id> : Test { method = confirmation }` judged by the human, with #Covers edges to the sprint Stories it attests. D0204 already retired the framing of that review as a mandatory human gate and removed sitting coverage from the authority queue, but it left the method: the skill still says the human 'accepts the sitting's content (the one gate)', sittingReviewVP still sits on the act surface with the concern 'which sittings have not yet had their per-sitting human review (D0049's single gate)', and keel show sitting-coverage reads 309 sprints due such a review out of 738 (116 covered, 313 grandfathered under D0155). Reading what a review presents against who already judges each part: tested work is self-evidencing (D0051); an AI-examined pass lands proposed and the human judges it per item with keel judge-set (D0312 B); a Decision is accepted per Decision with keel accept --words or the published brief (D0192, D0337); a >= Medium critique finding is dispositioned per finding through keel record review (D0092); and 'I have seen this sprint' is a receipt, not testimony (D0232; D0200: acknowledgment is not examination). Every judgment a review bundles therefore already has an atomic home, and the residue - that the review itself is finished - is not a judgment a human can add anything to. Eighty sitting reviews on the tree carry the old method; they are history and are not rewritten.";
        :>> decision = "A sitting review is finished by the AI: its record is a Test with method = analysis, judged by the AI actor that ran it, carrying the #Covers edges to the sprint Stories it presented, and its procedure text names what the sitting shipped, its metrics, and what waits on a human's word under the three per-item verbs - keel accept for a proposed Decision, keel judge-set for a proposed result, a disposition for a finding. Nothing about the review itself is confirmed: no Test with method = confirmation is recorded for a sitting, a sprint, or a review from this Decision on, and no surface counts a sitting without a review as something a human owes. sittingReviewVP leaves the act surface for the assurance surface with its concern rewritten to 'which sprints has a sitting review presented' - keel show sitting-coverage keeps computing the same numbers as a coverage view, never an obligation. The sprint-review skill's phase 4 records the analysis review and lists the outstanding per-item asks by their verbs; it never asks the human to confirm the sitting.";
        :>> rationale = "method = confirmation records a human's word on a specific claim (D0016, D0051), and the claim 'this review is finished' has no content a human's word settles: the tested work carries its own evidence, and each judgment-only item a review can surface - a Decision, a proposed result, a finding - has a per-item verb whose record binds to that item's text, which a sitting-level confirmation cannot. A confirmation over a sitting is therefore either a duplicate of three atomic records or a reading receipt, and D0232 says a receipt is not testimony. D0204 made oversight pull, not push, and named the human's only inherent gates as the direction decisions that block work and the confirmations they choose to give; a review method that still reads confirmation contradicts that by making a review the human has not given an absence the coverage view counts and the console shows on the act tab. The retro is the precedent: D0049 clause 2 and D0123 made it AI-judged analysis that generates tracked items, and the sitting review is the same shape - a presentation whose outputs are items and asks, not a verdict. The human judges this Decision under D0337 because it changes a ceremony method.";
        :>> consequences = "NOT A FORK: the human's instruction named the change and the question it answers; the one alternative read - that a sitting review should confirm the direction of the work - is already the Decision path (a direction Decision, keel accept), so no option is weighed here. Supersedes D0049 clause 3 ('the single HUMAN touchpoint is a per-SITTING sprint review (method=confirmation, batchable across the sitting's sprints)') and D0051's clause that 'the per-sitting review requires human confirmation ONLY for non-test-verifiable items'; D0049 clauses 1-2 and D0051's rule that test-backed items self-evidence stay in force. Depends on D0204 (pull, not push) and D0312 (proposed results are the human's to judge). Applying it: the sprint-review skill's SKILL.md phase 4 and record shape, sittingReviewVP's surface and concernText in .engine/views/viewpoint-registry.sysml, the console's act tab (which reads the viewpoint registry, so it stops counting sitting reviews once the surface changes), and the sitting-coverage renderer's 'due' wording, which stays a count of sprints no review has presented and stops implying anyone owes one. The eighty existing confirmation-method sitting reviews stay as recorded: their judgedBy is a human's actual word and is not rewritten. A guard follows in the resolving sprint: no Test with method = confirmation whose title or name contains 'sitting' or 'Rev' is added after this Decision's commit - the D0388 pair is one planted sittingRev with method = confirmation (red) and one with method = analysis (green).";
    }
    #SupersedeClause dependency from d0510 to d0049;
    #SupersedeClause dependency from d0510 to d0051;
    #DependsOn dependency from d0510 to d0204;
    #DependsOn dependency from d0510 to d0312;

    // acceptance event (D0121 review-queue sign-off; D0066/D0106 — human-judged, not fabricated)
    verification d0510Accept : Test { :>> id = "2f782de1-a8ad-4c6c-a83d-f9e5f5969a8d"; :>> method = VerificationMethod::confirmation; :>> procedureText = "recorded from chat - their words, verbatim: “Accept all decisions as recommended. Proceed to release and fix downstream” WARN: read-back - the quoted words do not name d0510 (D0201 B); recorded as given (D0423)."; }
    part d0510AcceptR1 : TestResult { :>> id = "bd85f4b9-e8dc-49fa-b6fc-c312425d949f"; :>> outcome = VerdictKind::pass; :>> judgedAgainst = "4d00c1bc"; :>> judgedAt = "2026-09-18"; :>> judgedBy = "wweatherholtz"; :>> createdBy = "claudeFable5"; }
}
