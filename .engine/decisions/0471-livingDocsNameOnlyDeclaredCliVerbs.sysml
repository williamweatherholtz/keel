// D0471 (status: the `status` field below is the truth) — A living doc names only verbs this binary dispatches
// Recorded via `keel record decision` (D0105 RMWX axis; issue054). Acceptance is a separate explicit
// human gate (method=confirmation, D0106): flip status + add the d0471Accept event on sign-off.
package Decision0471 {
    private import EngineElement::*;
    private import EngineWork::*;
    private import EngineVerification::*;
    private import EngineRelationships::*;

    // #ProspectiveChange (D0070) - this Decision governs a process/schema change; the co-committed
    // change rides the process-change guard's hard lock.
    #ProspectiveChange part d0471 : Decision {
        :>> id = "b137b2b9-b308-4757-89a2-c0fd2c166385";
        :>> title = "A living doc names only verbs this binary dispatches";
        :>> createdAt = "2026-09-13";
        :>> createdBy = "claudeFable5";
        :>> status = DecisionStatus::accepted;
        :>> context = "Sprint 701's VERIFIER followed the test-verify skill verbatim, as D0425 requires of it. The skill's three gate lines said validate, check-engine and guard as top-level verbs - the spellings D0452 folded under gate - so each exited 2 with a usage dump, the receipt came back with no gate lines, and its DISCREPANCIES line read NONE (issue528, High). cli-surface-declared (D0271) holds facts = help = dispatch, and tool-reference (issue196) holds every tool path a doc names to a file that exists; nothing held a doc's command lines to the dispatch. The living surface - processes, skills, docs, contracts, workflows, rules, CLAUDE.md, the output style - is the procedure a delegated agent runs from, and a retired verb there is an enforcement point that has silently stopped firing (hazard EHZ5). A survey of that surface at 32d9424 found eight such lines: six in test-verify, two in knowledge-graph-memory; every other keel-verb token on it dispatched.";
        :>> decision = "Every command reference on the living doc surface names a verb this binary dispatches, and after a router or show a declared sub-verb or lens. A command reference is keel, KEEL, keel.exe or a copy of the binary followed by a verb: inside code (a fenced block or a backtick span) every such token, in prose only one carrying a flag or a root argument, because keel is also the project's name. The verb must be in COMMAND_NAMES; a verb-shaped token after a router that declares sub-verbs (gate, record, audit, process, library, github, hook) must be one of them, after show a lens. Guard cli-reference (74) holds it as a hard forward guard over tool-reference's scope plus .claude/output-styles; its violation names file:line, the token, and the spelling that exists today when the retired verb survives as a sub-verb or a lens. Decisions and .tracking are history and stay out of scope.";
        :>> rationale = "A doc a subagent follows verbatim is a control's procedure, and D0425 made the verifier deliberately unable to correct it - a verifier that fixes the brief it was given has inherited the primary's belief. So the procedure has to be right by construction, which means a check that runs on every edit, not a reader noticing a usage dump. The code-context rule is what makes the check honest on a surface where the word keel appears four hundred times as a name: a doc that says the keel engine is not naming a command, a doc that says run keel gate --fast . is. The scan at 32d9424 was chosen before the guard was written and the guard's first run named exactly its eight sites, plus three in the guard's own catalogue row that quoted the defect in backticks and two wordings the rule is right to refuse. The suggestion text exists because the follower of a violation should not need to know D0452 to fix it. NOT A FORK: the alternative - a reader remembering the fold - is the state issue528 records. MEASURED: keel gate guard cli-reference --no-receipt . on this Windows 11 host, three runs 0.09-0.12 s over 438 command references (the whole 74-guard set runs on every edit already; this guard adds about a tenth of a second to it).";
        :>> consequences = "keel-cli/src/guards.rs gains cli_reference beside tool_reference, sharing living_doc_files so the two guards mean the same surface; GUARD_NAMES is 74. The test-verify skill's six lines read KEEL gate validate ., KEEL gate check-engine ., KEEL gate guard --no-receipt .; knowledge-graph-memory names keel show why and keel show knowledge question-coverage; the recorder brief says a sub-verb of keel record. A doc that must quote a retired command verbatim writes it outside a code span with no flag or root, or the guard names it - that is the intended friction. A copy of the binary is recognised only with its .exe suffix (keel-serve.exe), so keel-cli and .keel/ paths are never read as commands. The guard reads the dispatch through cli_surface and cli_facts, so a verb added to commands.sysml is accepted by the docs the same commit it is declared, and a verb removed fails every doc that still names it.";
    }

    // acceptance event (D0121 review-queue sign-off; D0066/D0106 — human-judged, not fabricated)
    verification d0471Accept : Test { :>> id = "d3860236-2d20-4401-afac-62c75c750931"; :>> method = VerificationMethod::confirmation; :>> procedureText = "Said in chat 2026-09-14 over the twenty-eighth publish of the decision brief, which carried fifteen held asks; one instruction covers the fourteen non-forks, d0471 among them. The fork d0466 is not covered - it needs an option letter and stays held. - their words, verbatim: “Accept all proposals. Proceed to design with needs, etc.” WARN: read-back - the quoted words do not name d0471 (D0201 B); recorded as given (D0423)."; }
    part d0471AcceptR1 : TestResult { :>> id = "24a8ff2f-082e-4a96-b335-31a7aca3cc1b"; :>> outcome = VerdictKind::pass; :>> judgedAgainst = "d110d0a"; :>> judgedAt = "2026-09-14"; :>> judgedBy = "wweatherholtz"; :>> createdBy = "claudeFable5"; }
}
