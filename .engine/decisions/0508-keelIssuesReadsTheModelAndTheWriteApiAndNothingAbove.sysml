// D0508 (status: the `status` field below is the truth) — keelIssuesReadsTheModelAndTheWriteApiAndNothingAbove: the item member depends on keel-model, keel-write, keel-schema and keel-json only; the resolver predicate descends to keel-model so the write and the guard read one function; a name reachable through keel-issues may live in the crate its other readers share; the module home is computed, not a synopsis clause
// Recorded via `keel record decision` (D0105 RMWX axis; issue054). Acceptance is a separate explicit
// human gate (method=confirmation, D0106): flip status + add the d0508Accept event on sign-off.
package Decision0508 {
    private import EngineElement::*;
    private import EngineWork::*;
    private import EngineVerification::*;
    private import EngineRelationships::*;

    // #ProspectiveChange (D0070) - this Decision governs a process/schema change; the co-committed
    // change rides the process-change guard's hard lock.
    #ProspectiveChange part d0508 : Decision {
        :>> id = "211819d8-c8a6-4afa-b6e4-915a93818469";
        :>> title = "keelIssuesReadsTheModelAndTheWriteApiAndNothingAbove: the item member depends on keel-model, keel-write, keel-schema and keel-json only; the resolver predicate descends to keel-model so the write and the guard read one function; a name reachable through keel-issues may live in the crate its other readers share; the module home is computed, not a synopsis clause";
        :>> createdAt = "2026-09-17";
        :>> createdBy = "claudeFable5";
        :>> status = DecisionStatus::accepted;
        :>> context = "Sprint 737 (dcKeelIssuesIsAMember) is the seventh D0479 extraction: github_ingest leaves keel-cli, intake_write leaves keel-write, the issue write leaves write.rs and the open-issues, dispositions and intake views leave keel-view for members/keel-issues. D0480 drew the member's boundary in words - items and their state on one side, the engine's own governance on the other - and its DoD's probe made the boundary a build fact: an edit to a governance or serving module must leave keel-issues Fresh. Three things the DoD did not say had to be settled for the probe to hold. First, `record issue` checks its resolver through the resolver-kind guard's own predicate (issue558), which sat in members/keel-guards, and a member that depends on keel-guards depends on every guard and on the read model's whole enforcement layer. Second, `record task` is an item verb D0480 names for the member, but add_task reads eight private insertion helpers in write.rs that append_result and the other result writes share; moving it moves the helpers or copies them. Third, D0480's consequences say the record verbs' CLI facts name the member in their synopsis when it lands - and every synopsis renders into `keel --help`, which every extraction has held byte-identical, while the same repository already computes each module's crate from the manifests (scripts/module_home.py, D0105 one home per fact). The predicate's move edits members/keel-guards/src, a locked path, so this Decision carries the process-change marker and is held for the human.";
        :>> decision = "Member keel-issues depends on keel-model, keel-write, keel-schema and keel-json and on no crate above them: not keel-guards, not keel-view, not keel-suite, not keel-process. The resolver predicate - declared_task_names and resolver_kind_holds, the functions the resolver-kind guard applies at commit and record issue applies before it writes - lives in keel_model::resolvers; keel-guards re-exports both at their old paths and applies the same function, so the write and the gate cannot disagree. at_least_medium lives in keel_model::queries beside issue_disposition, which reads the same tier. add_task stays keel-write's and keel-issues re-exports it: a name the member's users reach through keel-issues may live in the crate its other readers share, and the member is the path, not the home. The severity and resolver checks that sat inline in main.rs are issue_write::triage_holds, the member's, with the refusal text unchanged. The clause of D0480 that has the record verbs' CLI facts name the member in their synopsis is reversed: `keel --help` is the human's surface and stays byte-identical across extractions; the crate a verb's implementation lives in is computed from the manifests by scripts/module_home.py and is never restated in a synopsis. The rest of D0480 stands.";
        :>> rationale = "D0479's rule is that a fact lives where its readers are. The resolver predicate has two readers - the guard and the write - in two crates that must not know each other, so it lives below both, in the read model they share; a copy in each would be the issue119/issue120 class (two vocabularies, nothing holding them equal) applied to a predicate, and the first triage of issue556 already showed what a write that disagrees with its gate does. add_task's readers are the eight helpers in write.rs, which append_result reads too: moving the function moves or duplicates the helpers, so it stays and the member re-exports it, which gives a keel-issues user the verb without giving the member the write file. The synopsis clause was a good intention that fails two standing facts: one home per fact (D0105) - the module home is already computed and a synopsis restating it is a second home that drifts - and the byte-identical help every extraction has held as its proof that the human's surface did not move (sprints 731-736). Reversing one clause with #SupersedeClause leaves D0480's boundary and its ownership list in force (D0398). The marker: members/keel-guards/src is under the keystone lock (is_locked_path), and the two slices this sprint takes from it - each replaced by a re-export - are an enforcement change by path even though the guard's behaviour is byte-for-byte the same function; D0209 clause 2 asks for the marked Decision beside every such edit, and the human judges it, not the tree.";
        :>> consequences = "members/keel-issues holds github_ingest.rs, intake_write.rs, issue_write.rs (NewIssue, record_issue, TriageRefusal, triage_holds) and views.rs (open_issues, dispositions, intake); its Cargo.toml names four members and serde_json; cargo tree -p keel-issues names no keel-process, keel-view, keel-guards or keel-suite, and touching members/keel-process/src/process_cmd.rs leaves it Fresh. members/keel-model/src/resolvers.rs holds the predicate; keel-guards' lib.rs and issues.rs re-export it. keel-cli's lib.rs re-exports every moved name at its old path, view and write becoming wrapper modules that glob the member's module and add the sliced names, so no caller in main.rs, serve.rs, deck.rs or the tests moved. keel --help is byte-identical to the pre-move render and keel version's guard line is unchanged at 75. The transform is scripts/extract_issues.py (idempotent, dry-run default). The next extraction that needs a guard's predicate below the guards follows this descent, not a dependency on keel-guards. NOT A FORK: the alternatives (a member depending on keel-guards; a copied predicate; add_task moved with its helpers; a synopsis naming the crate) each break a standing fact named above, and the DoD's own probe rules them out; nothing here is left for a later choice.";
    }
    #SupersedeClause dependency from d0508 to d0480;
    #DependsOn dependency from d0508 to d0479;
    #DependsOn dependency from d0508 to d0506;

    // acceptance event (D0121 review-queue sign-off; D0066/D0106 — human-judged, not fabricated)
    verification d0508Accept : Test { :>> id = "097c622c-16f2-4840-950e-8b20614f34c9"; :>> method = VerificationMethod::confirmation; :>> procedureText = "recorded from chat - their words, verbatim: “Accept all decisions as recommended. Proceed to release and fix downstream” WARN: read-back - the quoted words do not name d0508 (D0201 B); recorded as given (D0423)."; }
    part d0508AcceptR1 : TestResult { :>> id = "db49e4ef-8b63-446d-ba76-5e7279950d25"; :>> outcome = VerdictKind::pass; :>> judgedAgainst = "4d00c1bc"; :>> judgedAt = "2026-09-18"; :>> judgedBy = "wweatherholtz"; :>> createdBy = "claudeFable5"; }
}
