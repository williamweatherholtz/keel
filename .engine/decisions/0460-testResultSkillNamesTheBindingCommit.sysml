// D0460 (status: the `status` field below is the truth) — testResultSkillNamesTheBindingCommit: the test-result and sprint-standup skills state the D0308 binding rule - a pass binds to the commit that lands it, and a suspect is a change since that commit, never judgedAgainst != HEAD
// Recorded via `keel record decision` (D0105 RMWX axis; issue054). Acceptance is a separate explicit
// human gate (method=confirmation, D0106): flip status + add the d0460Accept event on sign-off.
package Decision0460 {
    private import EngineElement::*;
    private import EngineWork::*;
    private import EngineVerification::*;
    private import EngineRelationships::*;

    // #ProspectiveChange (D0070) - this Decision governs a process/schema change; the co-committed
    // change rides the process-change guard's hard lock.
    #ProspectiveChange part d0460 : Decision {
        :>> id = "821776e1-7ede-454e-826b-cf1719542417";
        :>> title = "testResultSkillNamesTheBindingCommit: the test-result and sprint-standup skills state the D0308 binding rule - a pass binds to the commit that lands it, and a suspect is a change since that commit, never judgedAgainst != HEAD";
        :>> createdAt = "2026-09-12";
        :>> createdBy = "claudeFable5";
        :>> status = DecisionStatus::accepted;
        :>> context = "Two skills under the D0070 hard lock still describe a TestResult's validity by HEAD-equality. .engine/skills/test-result/SKILL.md anti-pattern 2 says judgedAgainst must be the actual HEAD at test time, and anti-pattern 4 says commit ancestry is the validity signal without saying whose ancestry; .engine/skills/sprint-standup/SKILL.md lists as suspect any item whose judgedAgainst commit differs from the current HEAD. dcResultBindsToItsLandingCommit (sprint 624, chartered by D0308) changed the engine: a pass recorded on a dirty tree names the HEAD before its work and BINDS to the commit that introduces it once that HEAD is the commit's ancestor - the write path says so at every record (the note this session read six times: this pass names 51410ba but binds to the commit that lands it). A suspect is computed by keel show suspect as a dependency or own-DoD change since the BINDING commit, never as judgedAgainst != HEAD, which would make every result suspect one commit later. At sprint 624 the wording was corrected in the same commit as the code and the process-change guard refused it: a two-sentence skill edit is a process change outside standing consent (D0337), so the code landed with usage.md carrying the note and the skills unchanged. This is the Decision that wording waits on; dcTestResultSkillNamesTheBinding is the item.";
        :>> decision = "NOT A FORK: the rule is D0308's, already landed in code at sprint 624; this clause is its skill wording. The consequence of this Decision is exactly three edits, applied verbatim on acceptance and nothing else. test-result/SKILL.md anti-pattern 2 becomes: Missing or borrowed commit SHA - judgedAgainst is the HEAD the tree stood at when the judgment was made, never a placeholder or a commit that does not exist yet; a pass recorded on a dirty tree names that HEAD and BINDS to the commit that lands the work once judgedAgainst is that commit's ancestor (dcResultBindsToItsLandingCommit, D0308). Anti-pattern 4 becomes: Wall-clock or HEAD-equality as the validity signal - judgedAt is display; the validity signal is the BINDING commit's ancestry, and a result is suspect when a dependency or its own DoD changed since that commit (keel show suspect . --explain), not when judgedAgainst differs from HEAD, which every result does one commit later. sprint-standup/SKILL.md's suspect line becomes: Any suspect items - a dependency or own-DoD change since the result's binding commit (keel show suspect . --explain), not judgedAgainst != HEAD. Then keel sync-claude regenerates .claude/.";
        :>> rationale = "A skill that tells the agent to treat judgedAgainst != HEAD as suspicion contradicts the engine it drives: the lens computes suspicion from ancestry, the write path binds to the landing commit, and an agent following the skill's words would either re-record every result each commit or mistrust the lens. Two homes for one rule with different texts is the D0105 defect; the skill is the home the agent reads first, so it must carry the rule the engine enforces. The wording is fixed in this Decision rather than left to the edit so that the human accepts the exact sentences (D0308/D0329: acceptance binds to text), which is what the process-change guard's refusal at sprint 624 asked for.";
        :>> consequences = "Process-change (D0337): held proposed for the human's word; nothing is edited before acceptance. On acceptance: the three edits above, keel sync-claude, and the VERIFY of dcTestResultSkillNamesTheBinding - grep judgedAgainst over .engine/skills finds no claim that HEAD-equality alone is the validity or suspect signal; sync-claude --check clean. Behavioural instruction 4 of test-result (judgedAgainst = current HEAD short SHA) stays as written: it is the recording instruction, and the binding rule says what that SHA then means. STATED: this changes no code, guard or lens; a skill that names the binding does not make the binding correct - dcResultBindsToItsLandingCommit's tests do.";
    }
    #DependsOn dependency from d0460 to d0308;

    // acceptance event (D0121 review-queue sign-off; D0066/D0106 — human-judged, not fabricated)
    verification d0460Accept : Test { :>> id = "4d93af51-1a96-4332-ae08-467dd4a3da3f"; :>> method = VerificationMethod::confirmation; :>> procedureText = "Selected on the decision brief copy-out (nineteenth publish), pasted into chat 2026-09-13; d0460 accepted, the recommended course. The sheet's one note was written for the retro item, they said, and is recorded there. - their words, verbatim: “Accept: the test-result and sprint-standup skills state the binding rule - a pass binds to the commit that lands it, a suspect is a change since that commit, never judgedAgainst differing from HEAD (recommended)”"; }
    part d0460AcceptR1 : TestResult { :>> id = "8bcf5ad4-23c8-44e5-a694-62ddc69b844d"; :>> outcome = VerdictKind::pass; :>> judgedAgainst = "8469f80"; :>> judgedAt = "2026-09-13"; :>> judgedBy = "wweatherholtz"; :>> createdBy = "claudeFable5"; }
}
