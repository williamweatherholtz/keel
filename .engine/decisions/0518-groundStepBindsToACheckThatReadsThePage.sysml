// D0518 (status: the `status` field below is the truth) — groundStepBindsToACheckThatReadsThePage: the decision-surfacing step dsGround is checked by a check that reads the rendered decision page for the shapes the step forbids, or it declares that no check does
// Recorded via `keel record decision` (D0105 RMWX axis; issue054). Acceptance is a separate explicit
// human gate (method=confirmation, D0106): flip status + add the d0518Accept event on sign-off.
package Decision0518 {
    private import EngineElement::*;
    private import EngineWork::*;
    private import EngineVerification::*;
    private import EngineRelationships::*;

    // #ProspectiveChange (D0070) - this Decision governs a process/schema change; the co-committed
    // change rides the process-change guard's hard lock.
    #ProspectiveChange part d0518 : Decision {
        :>> id = "5c74b50f-7d01-46af-9d77-48e4a9882f9e";
        :>> title = "groundStepBindsToACheckThatReadsThePage: the decision-surfacing step dsGround is checked by a check that reads the rendered decision page for the shapes the step forbids, or it declares that no check does";
        :>> createdAt = "2026-09-18";
        :>> createdBy = "claudeFable5";
        :>> status = DecisionStatus::accepted;
        :>> context = "GH#84 (st161; untrusted source, D0264 - the Penumbra project's agent session, after that project's owner could not see the bifurcation on a six-tab page and a five-critic panel read the tabs against the rules that govern them). Verified in this tree: .engine/processes/decision-surfacing.sysml:49 binds dsGround (`Give them what an INDEPENDENT judgment needs, not a request to bless my pick` - the item inline, what accepting binds, the specific fork, the evidence, what I do with each answer) to `checkedBy = 'judgment-request-quality'`; .engine/docs/guards.md:38 says that guard reads a PROPOSED fork Decision's title, rationale, RESEARCH statement and per-OPTION cost in the decisions directory. It never opens a rendered page; no guard names scripts/check_templates.py, and check_brief (check_templates.py:264) holds word budgets, field presence and chain order only. What got through the reporting project's page: two tabs whose options differed only by a verdict verb (`Judge ... as PASS` / `Fail ... with a direction`), a cost reading literally `None.`, before/after rows whose both cells were record states (`PROPOSED` -> `judged`), and a computed classification preamble before every tab - three of the four forbidden by the skill text, none read by anything. So a D0321 binding resolves (the guard exists) and checks a different artefact from the one the step is about. The page is machine-local (.keel/decision-page.toml records its URL; the HTML lives in the session's scratchpad), so no tree guard can open it; the build script (scripts/exec_brief/build_*.py) is the one actor that holds the page, and it already refuses on fit_check overrun and on facts read from a tree not at HEAD.";
        :>> decision = "RESEARCH: read before asking. D0321 OPTION A gave ProcessStep `checkedBy` naming a guard or a declared rule, held by guard step-check-resolves; the same Decision left the four judgment steps and obligationReview on their contract declaration, unenforced and said so. OPTION A (recommended): check_templates.py --brief gains four content refusals over the rendered page - a `data-d='cost'` whose text is none, n/a or a dash; a choice label that begins with a verdict verb (accept, reject, approve, confirm, pass, fail, judge); a before/after row whose two cells are both drawn from the record-state vocabulary (proposed, accepted, judged, pass, fail, done, ready, blocked); and a required `data-d='premise'` rendered before the choices and budgeted like `stake` - and the build script runs that check and refuses to write the page on any of them, as it does today for fit_check. dsGround's checkedBy is retargeted to a declared rule `brief-page-quality` in rules.sysml whose mechanism is that check, so step-check-resolves keeps resolving and hardening reports the step as checked by the thing that reads the page. COST: four shapes in check_templates.py with a self-test holding the reporting project's two offending tabs as the shapes that must refuse and a premise-led tab as the shape that must pass (the D0388 pair); one rule row; the 35 build scripts that already import the checker are unchanged because each calls it before publish (MEASURED 2026-09-18: 45 build scripts under scripts/exec_brief, 35 import check_templates, 36 call assert_fits; the ten that do not are the 2026-09-08/09 pages that predate the checker and are history, not writers), and the forty-eighth page is re-checked against the four shapes before the rule lands. OPTION B: dsGround drops checkedBy and carries the D0321 contract declaration - `unenforced: the page is machine-local and no tree check opens it` - so the process stops claiming a control it does not have. COST: one line; the four shapes stay caught only by the human who reads the page, which is the failure the report describes.";
        :>> rationale = "A step whose checkedBy names a check of a different artefact is worse than an unenforced step, because hardening counts it as checked (D0321) and the reader trusts the count. Both courses end that; only A adds a control. A is cheap because the enforcement point already exists: the build script is the sole writer of the page and already refuses on two contracts, so a third refusal is a function call, not a new gate, and the four shapes are structural enough for a regex over the markup the builders already emit (the courses table and the options list of logic_exhibits.py; D0402's fit_check reads the same markup). The honest residual is that the check runs where the page is built, not at the tree's gate - a page built by another script, or edited by hand after the build, is not read - and rules.sysml's mechanism field is where that residual is stated. B is the fallback if the human judges the four shapes too narrow to be worth a rule; it is not the recommendation, because the reporting project already wrote the equivalent floor (tools/tab_quality.py) and its self-test held.";
        :>> consequences = "Under A: check_templates.py --brief refuses four content shapes; every build script refuses to publish a page that carries one; rules.sysml gains brief-page-quality; dsGround.checkedBy names it; guards.md and the decision-surfacing skill say so in the same commit (doc-sync); the current forty-eighth page is re-checked and re-published if any of its nineteen tabs carries a shape. GH#84 is answered on GitHub with the tracked ids once this record's status is known. HELD proposed under D0337 for the human's word: a process step's binding is a process change (D0209 cl.2) and the source is untrusted (D0264); the delivering item is dcGroundStepBindsToACheckThatReadsThePage and issue606's resolution is computed from its #Resolves edge.";
    }

    // acceptance event (D0121 review-queue sign-off; D0066/D0106 — human-judged, not fabricated)
    verification d0518Accept : Test { :>> id = "27d2d6db-a78d-4300-bd93-91224efa65a3"; :>> method = VerificationMethod::confirmation; :>> procedureText = "OPTION A chosen (the recommended option; the brief's verdict was A on both forks) - their words, verbatim: “Accept all decisions as recommended. Proceed to release and fix downstream” WARN: read-back - the quoted words do not name d0518 (D0201 B); recorded as given (D0423)."; }
    part d0518AcceptR1 : TestResult { :>> id = "5e3d21d4-a2da-4ac4-b697-1c06d6f118da"; :>> outcome = VerdictKind::pass; :>> judgedAgainst = "4d00c1bc"; :>> judgedAt = "2026-09-18"; :>> judgedBy = "wweatherholtz"; :>> createdBy = "claudeFable5"; }
}
