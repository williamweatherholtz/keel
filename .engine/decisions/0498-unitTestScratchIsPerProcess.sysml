// D0498 (status: the `status` field below is the truth) — A test's scratch directory carries the process id - one helper, keel_fs::scratch, names it, and a lib census fails any temp_dir().join whose argument two processes could share
// Recorded via `keel record decision` (D0105 RMWX axis; issue054). Acceptance is a separate explicit
// human gate (method=confirmation, D0106): flip status + add the d0498Accept event on sign-off.
package Decision0498 {
    private import EngineElement::*;
    private import EngineWork::*;
    private import EngineVerification::*;
    private import EngineRelationships::*;

    part d0498 : Decision {
        :>> id = "a2e8ff97-35d5-4a9a-864b-e6cfb4e00cf0";
        :>> title = "A test's scratch directory carries the process id - one helper, keel_fs::scratch, names it, and a lib census fails any temp_dir().join whose argument two processes could share";
        :>> createdAt = "2026-09-16";
        :>> createdBy = "claudeFable5";
        :>> status = DecisionStatus::accepted;
        :>> context = "Unit tests across keel-cli/src and members/*/src build their scratch trees under std::env::temp_dir() at fixed names - keel-judge-set, keel-atomic-write-test, keel-k6-{tag}, and some thirty more in guards.rs, deck.rs, pm.rs, attestation.rs, onboard.rs, main.rs, actor.rs among them - so two lib runs on one host share every one of them. During sprint 724's ceremony two runs overlapped (issue569) and produced two different failing sets, 5 tests and 3, from one source: one process deleted or rewrote a tree the other was reading, which is why the receipt named NotFound errors and a result no single run produces (issue570). Every named test passes alone. Most sites already interpolate std::process::id() by hand, which is exactly why the fixed ones survived: the convention was known and applied by memory, and memory is not a control (D0047). The same class sits under keel-cli/tests, where the three cucumber runners name write_bdd_{n}, keel_cli_bdd and orient_bdd_{n}.";
        :>> decision = "A unit or integration test that writes under the system temp directory names its tree through keel_fs::scratch(tag), which returns temp_dir()/<tag>-<process id>; keel-fs is the home because it is the leaf every writing member already depends on. A census test in the keel-cli lib reads every .rs under keel-cli/src, keel-cli/tests and members/*/src and fails on any temp_dir().join( in test code whose argument carries no per-process token - no process::id(), no gen_uuid() - naming the file and line. Test code is the region from a file's first bare #[cfg(test)] attribute to its end, and all of keel-cli/tests; a production site that names a stable scratch path (audit history's keel-audit, the trend and baseline worktrees) is outside the census and outside this Decision.";
        :>> rationale = "The defect is not any one fixed name; it is that the rule lived in the author's head and was applied thirty-odd times by hand with a dozen misses. One helper makes the correct call the shortest one to write, and the census makes the incorrect call fail the lib test set that keel land and the D0476 ladder already run, so a new fixed name cannot land. The census is a text scan rather than a type because the hazard is textual - a literal in a join call - and a text scan can name the offending line for the reader. gen_uuid() is admitted beside process::id() because a per-call uuid is stricter than a per-process id, not weaker. The production worktree sites are excluded on purpose: they are reused by design across runs of one command and changing them is a different question, tracked if it is worth asking. This is a rule about how test code is written, held by a lib test; it changes no gate, hook, workflow step or skill.";
        :>> consequences = "Thirty-odd test sites change from a fixed join to keel_fs::scratch; keel-actor gains keel-fs as a dev-dependency (a leaf depending on a leaf, downward). The census's D0388 pair is stated before the tree is read: known-positive, a synthetic source with a #[cfg(test)] line followed by temp_dir().join('keel-x') is named at its line; known-negative, scratch('keel-x') and temp_dir().join(format!('keel-x-{}', std::process::id())) pass, as does the same fixed join above the #[cfg(test)] line. Wrong if a test needs a path two processes share on purpose - a lock-contention test, say - which would then need its own stated exemption rather than a fixed name. Resolves issue570; delivered by dcUnitTestScratchIsPerProcess.";
    }

    // acceptance event (D0121 review-queue sign-off; D0066/D0106 — human-judged, not fabricated)
    verification d0498Accept : Test { :>> id = "88ab9f40-6aff-40ba-aaea-a17b974354b9"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0498AcceptR1 : TestResult { :>> id = "e8d490f9-000d-419f-ae94-5717c4d3235b"; :>> outcome = VerdictKind::pass; :>> judgedAgainst = "1ecbef0"; :>> judgedAt = "2026-09-16"; :>> judgedBy = "wweatherholtz"; :>> createdBy = "claudeFable5"; }
}
