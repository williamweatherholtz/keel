// D0546 (status: the `status` field below is the truth) — sliceOneAgentCredentialIsASeatCopyOrAPooledKey: the agent in a slice-one run holds either a copy of the human's seat login, deleted at reap and never revoked, or an organisation API key from a Console-minted pool, inactivated at reap and billed per token, which reverses the accepted auth clause of the agent bridge
// Recorded via `keel record decision` (D0105 RMWX axis; issue054). Acceptance is a separate explicit
// human gate (method=confirmation, D0106): flip status + add the d0546Accept event on sign-off.
package Decision0546 {
    private import EngineElement::*;
    private import EngineWork::*;
    private import EngineVerification::*;
    private import EngineRelationships::*;

    part d0546 : Decision {
        :>> id = "ad98807f-cc60-483e-8a12-66f7748599d4";
        // RESEARCH: three rounds of a nine-persona adversarial panel over four revisions of the direction artifact, every finding verified against the repository at f365cb7a; the two landscape spikes D0540 (94 rows) and D0541 (122 user threads); docs/reviews/runner-direction-panel-2026-09-22.md holds the reports and the finding-to-resolution maps.
        :>> title = "sliceOneCredential: the agent in a slice-one run holds either a copy of the human's seat login, deleted at reap and never revoked, or an organisation API key from a Console-minted pool, inactivated at reap and billed per token, which reverses the accepted auth clause of the agent bridge";
        :>> createdAt = "2026-09-22";
        :>> createdBy = "claudeFable5";
        :>> status = DecisionStatus::accepted;
        :>> context = "Slice one has no proxy, so whatever credential the agent uses to reach the model provider is readable inside the run. The credential on this host is the seat's OAuth login under the profile; the agent bridge's accepted Decision D0094 says in its auth clause that it 'MUST NOT set ANTHROPIC_API_KEY (setting it overrides the subscription and forces pricier per-token API-rate billing)', enforced in the server code. The runner landscape (D0541) marks a runner holding a person's setup token as a terms violation that dies when they leave, and says keel must hold organisation keys or federated identity. The provider's Admin API can list and update keys but cannot create them; keys are minted in the Console, so a per-run key comes from a pool and its inactivation needs an admin-capable credential that must live outside the run profile. Revision 4 of the direction (D0542) carries this as invariant I-5's slice-one cell, which is VOID under the seat copy and ENFORCED under the pooled key. Three panelists named it as the residue only the human can decide.";
        :>> decision = "OPTION A: keel copies the human's seat credential into the seeded per-run config directory; it is deleted at reap and cannot be revoked, the agent holds the human's whole seat for the run, and the terms exposure the landscape names is accepted in the human's words; D0094's auth clause stands. OPTION B (recommended): a pool of organisation API keys minted in the Console, one leased per run and set inactive at reap through the Admin API by a credential kept outside the run profile; runs bill per token; a #SupersedeClause on D0094's auth clause is authored with this word, scoped to runs.";
        :>> rationale = "A is what the machine can do today with no new secret and no billing change, and it is what every run of the console launcher already does implicitly - but it is not run-scoped, and calling it so was the error the panel caught twice. B is the only form in which 'no credential the agent can read outlives the step' can be true before the proxy exists, at the price of per-token billing for runs and an admin credential to guard. The recommendation is B because slice one exists to make the boundary real, and a credential that cannot be revoked is not a boundary.";
        :>> consequences = "Under A: I-5 is void in slice one and V1 says the agent holds the seat; nothing else changes. Under B: the CR names the pool, its size (the concurrency bound), the inactivation call at reap, where the admin credential lives, and the superseding clause on D0094; slice two's enrolment rule (organisation key or federated identity, never a subscription token) follows without further change. COST under A: the agent holds the human's whole seat for the run, deletion is not revocation, and the terms exposure is accepted. COST under B: per-token billing for runs, a Console-minted key pool, an admin-capable credential to guard outside the run profile, and a superseding clause on D0094.";
    }

    // acceptance event (D0121 review-queue sign-off; D0066/D0106 — human-judged, not fabricated)
    verification d0546Accept : Test { :>> id = "53488cae-bce2-4ae3-8555-44e1c2683e9f"; :>> method = VerificationMethod::confirmation; :>> procedureText = "OPTION B ticked on the published brief 2026-09-23; their words beside it: a custom internal gate holding the one key rather than a pool - their words, verbatim: “add a custom gate interface that requires a separate key to access - we won't have multiple e.g. anthropic API keys to leverage. But a custom internal gate is proper, yes?” WARN: read-back - the quoted words do not name d0546 (D0201 B); recorded as given (D0423)."; }
    part d0546AcceptR1 : TestResult { :>> id = "f9ce77d1-3fc1-4943-b7bb-2f91f63ba861"; :>> outcome = VerdictKind::pass; :>> judgedAgainst = "996db40d"; :>> judgedAt = "2026-09-23"; :>> judgedBy = "wweatherholtz"; :>> createdBy = "claudeFable5"; }
}
