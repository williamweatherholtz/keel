// D0545 (status: the `status` field below is the truth) — sliceOneBoundaryIsAScrubbedProfileOrASecondUser: the wall around the slice-one agent is either a redirected and seeded profile on the human's own account, with every repository on disk reachable by path as the accepted residual, or a low-privilege operating-system user with the parent repository read-only
// Recorded via `keel record decision` (D0105 RMWX axis; issue054). Acceptance is a separate explicit
// human gate (method=confirmation, D0106): flip status + add the d0545Accept event on sign-off.
package Decision0545 {
    private import EngineElement::*;
    private import EngineWork::*;
    private import EngineVerification::*;
    private import EngineRelationships::*;

    part d0545 : Decision {
        :>> id = "9643a8e4-d082-40ec-bf10-7024fef6fd63";
        // RESEARCH: three rounds of a nine-persona adversarial panel over four revisions of the direction artifact, every finding verified against the repository at f365cb7a; the two landscape spikes D0540 (94 rows) and D0541 (122 user threads); docs/reviews/runner-direction-panel-2026-09-22.md holds the reports and the finding-to-resolution maps.
        :>> title = "sliceOneBoundary: the wall around the slice-one agent is either a redirected and seeded profile on the human's own account, with every repository on disk reachable by path as the accepted residual, or a low-privilege operating-system user with the parent repository read-only";
        :>> createdAt = "2026-09-22";
        :>> createdBy = "claudeFable5";
        :>> status = DecisionStatus::accepted;
        :>> context = "Slice one of the panelled direction (D0542, revision 4) runs the agent in a full clone with no remote. On this Windows host the agent is the same operating-system user as the human; Node and keel resolve the home from USERPROFILE, so a home-only scrub is a no-op, and a redirected profile changes what the agent reads but cannot stop a write by path to the parent repository or any other on disk. A linked worktree once rewrote the parent's git config and disarmed the commit gate (issue249); the clone closes that shared-git class. The panel split: the reducer holds that no recorded defect names an agent writing the parent by path - the five sandbox and scratch leaks in the ledger are one user's concurrent processes, closed by the per-run profile - and that a second user answers no counted defect while costing a per-user toolchain (.cargo, .rustup, miniforge3, claude) reinstalled or ACL-opened, an elevation step the developer does not have, and docker-users membership; the steelman and the mechanisms pedant hold that only a permission the operating system enforces makes 'a working copy the agent cannot write past' true. Both positions are on the record in the review.";
        :>> decision = "OPTION A (recommended for slice one): the agent runs as the human's own user with USERPROFILE, HOMEDRIVE and HOMEPATH, APPDATA, LOCALAPPDATA, TEMP and TMP, GH_CONFIG_DIR, GIT_CONFIG_GLOBAL and GIT_CONFIG_NOSYSTEM redirected into a per-run folder and CLAUDE_CONFIG_DIR seeded by keel; the human accepts, in their own words, that the agent can reach the whole profile and every repository on disk by path, and the out-of-tree profile diff is recorded as an indicator. OPTION B: the run executes as a separate low-privilege operating-system user with the parent repository denied by ACL and that user's profile as the diff baseline; the one-time cost - toolchain, elevation, docker group - is measured in the CR before approval.";
        :>> rationale = "The harvest, not the operating-system boundary, is what closes the counted defect class: any change outside the declared outputs fails the step whoever made it. A gets slice one to its first measured run without an administrator; B is the boundary the direction's own sentence promises and belongs at the latest at slice three's trigger, when a hostile-agent threat is stated. Recommending A for slice one is a judgment about payback order, not about which wall is stronger.";
        :>> consequences = "Under A: revision 4's profile variable set and seeding are the slice-one CR's materialise step; the residual is quoted in the human's words on the acceptance; B is revisited at slice three's trigger. Under B: the CR adds the user, the ACL and a spawn-as-user path, and the measured floor includes them. COST under A: the residual accepted in the human's words - every repository on disk reachable by path - and the profile diff as an indicator only. COST under B: a second user with its own toolchain, an elevation step the developer does not have today, and docker group membership, all measured before approval.";
    }

    // acceptance event (D0121 review-queue sign-off; D0066/D0106 — human-judged, not fabricated)
    verification d0545Accept : Test { :>> id = "c395ca42-e70b-4b40-9589-81b4a830d589"; :>> method = VerificationMethod::confirmation; :>> procedureText = "Their words: 'OPTION B: run as a second OS user; parent repository denied by ACL' (pasted copy-for-AI digest with this option ticked, chat, 2026-09-22) - their words, verbatim: “OPTION B: run as a second OS user; parent repository denied by ACL”"; }
    part d0545AcceptR1 : TestResult { :>> id = "08ec4556-3de7-4bb2-b125-6c5fe2ca12e9"; :>> outcome = VerdictKind::pass; :>> judgedAgainst = "b65a13e4"; :>> judgedAt = "2026-09-22"; :>> judgedBy = "wweatherholtz"; :>> createdBy = "claudeFable5"; }
}
