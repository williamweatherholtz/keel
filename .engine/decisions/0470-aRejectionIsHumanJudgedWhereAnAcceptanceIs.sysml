// D0470 (status: the `status` field below is the truth) — A rejection is human-judged at every layer an acceptance is
// Recorded via `keel record decision` (D0105 RMWX axis; issue054). Acceptance is a separate explicit
// human gate (method=confirmation, D0106): flip status + add the d0470Accept event on sign-off.
package Decision0470 {
    private import EngineElement::*;
    private import EngineWork::*;
    private import EngineVerification::*;
    private import EngineRelationships::*;

    // #SafetyChange (D0070) - this Decision governs a process/schema change; the co-committed
    // change rides the process-change guard's hard lock.
    #SafetyChange part d0470 : Decision {
        :>> id = "d5705583-0d1b-4c8a-983f-77edbf7bf725";
        :>> title = "A rejection is human-judged at every layer an acceptance is";
        :>> createdAt = "2026-09-13";
        :>> createdBy = "claudeFable5";
        :>> status = DecisionStatus::accepted;
        :>> context = "D0121/D0122 gave the review loop two verdicts: `keel accept` and `keel reject`, and the reject command's own synopsis (`.engine/cli/commands.sysml`, cliReject) says 'the same channel rules as accept'. They were not the same. accept_decision_locked calls refuse_ai_judgment (write.rs:1977) so an AI-kind or unregistered judgedBy is refused inside the lock; reject_decision_locked (write.rs:2233) read the file and wrote the Reject event with whatever judgedBy it was handed. HUMAN_ONLY_WRITE_COMMANDS and HUMAN_AUTHORITY_COMMANDS listed accept and judge-set only, so the computed control structure showed reject as the agent's action, and the control_structure test that holds the two lists equal could not see a command left out of both. confirmationAuthenticityRule reads resultJudgedByHuman(Accept) under whereStatus(accepted) only (rules.sysml:110-120), so a rejected Decision with an AI-judged RejectR1 would pass the guard. Only the command layer (verdict_channel_refusal in cmd_reject) stood between an AI actor and a recorded human rejection; the write API, the serve endpoint and any future caller bypass it. Found while writing the write-path registry (sprint 701); tracked as issue526 (High). Two Decisions in the tree are rejected (d0376, d0463; grep DecisionStatus::rejected over .engine/decisions), each with a RejectR1 event judged by the human, so the rule evaluates over two subjects and names zero violators - nothing to backfill.";
        :>> decision = "A rejection carries the same human-judgment guarantee as an acceptance, at every layer accept has it - reject_decision_locked, the human-authority command lists and the authenticity rule mirror accept_decision_locked, HUMAN_ONLY_WRITE_COMMANDS / HUMAN_AUTHORITY_COMMANDS and confirmationAuthenticityRule exactly, so an AI-kind or unregistered judgedBy is refused under the lock, the computed control structure shows reject as the human's action, and the recorded tree is held to the same claim. NOT A FORK: the alternative - leave reject at the command layer only - is what issue526 records as the defect; the synopsis already claimed accept's rules, so this Decision makes the claim true rather than choosing between claims.";
        :>> rationale = "A rejection is a human verdict on a proposal exactly as an acceptance is (D0106: sign-off is never AI-fabricated; D0178/K6: the write layer, not the caller, refuses). An AI actor that can record a human's rejection can retire a proposal the human never saw, which is the mirror of fabricating an acceptance and the same loss. The fix is placed where accept's is - inside the lock - because that is the layer no caller, hook or transport routes around; the lists and the rule follow so that the control structure and the recorded tree state the same fact the code enforces. One rule per verdict rather than widening the accepted rule: appliesWhen is a status scope and the predicate names the event suffix, so each branch is a separate ElementRule and the guard sums them.";
        :>> consequences = "Write layer: reject_decision_locked calls refuse_ai_judgment before it reads the file, so a refused rejection leaves the file unchanged byte-for-byte and `keel reject` and POST /api/decision/reject refuse an AI-kind or unregistered --by at the write. Command lists: reject joins HUMAN_ONLY_WRITE_COMMANDS (write.rs) and HUMAN_AUTHORITY_COMMANDS (control_structure.rs), so the control census and control structure list reject under the human's authority and the existing test holds the two lists equal. Rule: rejectionAuthenticityRule (subject Decision, predicate resultJudgedByHuman(Reject), appliesWhen whereStatus(rejected), blocking) sits beside confirmationAuthenticityRule; keel gate rules and the confirmation-authenticity guard read both, and its scanned count is the rejected Decisions (two today, d0376 and d0463, both human-judged). A refused rejection under the write ledgers nothing new: the channel refusals (reject:no-quote etc.) already ledger at the command layer, and the write-layer refusal returns WriteError::Parse as accept's does - the same shape the census registry (sprint 701) records for accept. The change touches write.rs, control_structure.rs, guards.rs and .engine/rules/rules.sysml and rides the process-change guard under this Decision's marker. Resolves issue526 through dcRejectIsHumanJudgedAtTheWriteAndTheRule.";
    }

    // acceptance event (D0121 review-queue sign-off; D0066/D0106 — human-judged, not fabricated)
    verification d0470Accept : Test { :>> id = "e0533e9f-a50e-4aa4-8110-d26d55df8ad2"; :>> method = VerificationMethod::confirmation; :>> procedureText = "Said in chat 2026-09-14 over the twenty-eighth publish of the decision brief, which carried fifteen held asks; one instruction covers the fourteen non-forks, d0470 among them. The fork d0466 is not covered - it needs an option letter and stays held. - their words, verbatim: “Accept all proposals. Proceed to design with needs, etc.” WARN: read-back - the quoted words do not name d0470 (D0201 B); recorded as given (D0423)."; }
    part d0470AcceptR1 : TestResult { :>> id = "4f0835f4-eb4c-404e-93af-07f52102f610"; :>> outcome = VerdictKind::pass; :>> judgedAgainst = "d110d0a"; :>> judgedAt = "2026-09-14"; :>> judgedBy = "wweatherholtz"; :>> createdBy = "claudeFable5"; }
}
