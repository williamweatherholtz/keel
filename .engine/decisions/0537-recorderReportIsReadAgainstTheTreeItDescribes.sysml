// D0537 (PROPOSED — NOT YET ACCEPTED) — check_report.py counts the TestResult parts the working tree gained since HEAD under .tracking and refuses a report with fewer WROTE lines than that, naming each gained result no WROTE key claims
// Recorded via `keel record decision` (D0105 RMWX axis; issue054). Acceptance is a separate explicit
// human gate (method=confirmation, D0106): flip status + add the d0537Accept event on sign-off.
package Decision0537 {
    private import EngineElement::*;
    private import EngineWork::*;
    private import EngineVerification::*;
    private import EngineRelationships::*;

    // #ProspectiveChange (D0070) - this Decision governs a process/schema change; the co-committed
    // change rides the process-change guard's hard lock.
    #ProspectiveChange part d0537 : Decision {
        :>> id = "f3d372e9-b816-441d-948b-75f89d58e898";
        :>> title = "check_report.py counts the TestResult parts the working tree gained since HEAD under .tracking and refuses a report with fewer WROTE lines than that, naming each gained result no WROTE key claims";
        :>> createdAt = "2026-09-20";
        :>> createdBy = "claudeFable5";
        :>> status = DecisionStatus::proposed;
        :>> context = "The D0425 recorder's report is checked by the delegated-ceremony skill's check_report.py before it returns (D0473, D0492, D0516). Every one of its eight refusals reads the report alone. Sprint 741 (issue602): the dispatch named the eighth owed record as --task dcTouchedSetDescendsTheWorkspaceDoD, the Test's name where the write API takes the action's; the write API refused that attempt, the recorder retried with --task dcTouchedSetDescendsTheWorkspace, the result dcTouchedSetDescendsTheWorkspaceDoDR1 landed in .tracking/backlog.sysml with its RAN receipt, and the report filed it as REFUSED: task not found. Seven WROTE lines plus one REFUSED line accounted for eight; check_report.py --owed 8 passed it. The tree held eight new TestResult parts and the report said seven were written. The primary found it by reading git diff after the report - no control read the report against the tree it describes. It is issue568's class (wrote nothing, reported NONE) with the sign reversed.";
        :>> decision = "check_report.py, given --root, reads the TestResult parts the working tree gained since HEAD under .tracking - the added `part <name> : TestResult` lines of `git diff HEAD -U0 -- .tracking` plus every such line of an untracked .tracking file - and REFUSES a report whose WROTE lines number fewer than that count. The refusal names each gained result no WROTE line claims: a WROTE line's --gate G claims results named G R<n>, its --task T claims T R<n> and T DoDR<n>. Refusal nine, beside the eight. The recorder brief gains one rule: a write that lands after a refused attempt is a WROTE line naming the command that landed, never a REFUSED line for the attempt that did not. The pure refusals() takes the gained list as an argument so the D0388 pair pins it without a tree; the fixtures are sprint 741's report as returned and its corrected form, both judged over the same eight-result list.";
        :>> rationale = "D0047: a defect that recurs becomes a control, and the recorder misfiling a landed write is a defect two agents can repeat - the API's refusal message is what the recorder sees last, and the report is written from what it saw last. Reading the report against the tree is the one check that cannot be satisfied by wording: the results either exist in the diff or they do not. The count is the refusal (D0492's shape, which the recorder already meets) and the names are the diagnosis, so a passing report and a red one each say exactly which part is unaccounted. The claim-by-prefix rule follows the write API's own naming: gate-result writes <gate>R<n>, result writes <task>DoDR<n> or <task>R<n>; a key that prefixes a gained name is the write that produced it.";
        :>> consequences = "A result the primary itself recorded onto the same dirty tree before the dispatch shows as gained and unclaimed, and the recorder's report is refused for a write it did not make; the primary commits its own results first, or the ceremony carries them as owed records. That is the intended edge: the recorder's report accounts for every TestResult the tree gained, whoever wrote it, or it does not return. check_report.py's --probe rows carry the sprint 741 pair; the delegated-ceremony skill's refusal list, the recorder brief and .engine/docs/guards.md's account of the skill say what the code does. No guard, hook or CI workflow changes; the guard count stays 76. The .claude copy is regenerated by keel sync-claude in the same commit.";
    }
}
