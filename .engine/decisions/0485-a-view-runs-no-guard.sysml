// D0485 (status: the `status` field below is the truth) — aViewRunsNoGuard: the readiness composition that runs the guard suite for the assured verdict lives in guards, the report compositions that read orient live above both, and the module graph is the check
// Recorded via `keel record decision` (D0105 RMWX axis; issue054). Acceptance is a separate explicit
// human gate (method=confirmation, D0106): flip status + add the d0485Accept event on sign-off.
package Decision0485 {
    private import EngineElement::*;
    private import EngineWork::*;
    private import EngineVerification::*;
    private import EngineRelationships::*;

    // #ProspectiveChange (D0070) - this Decision governs a process/schema change; the co-committed
    // change rides the process-change guard's hard lock.
    #ProspectiveChange part d0485 : Decision {
        :>> id = "a05f047c-c1e9-4ce1-a159-ed29cf2fd488";
        :>> title = "aViewRunsNoGuard: the readiness composition that runs the guard suite for the assured verdict lives in guards, the report compositions that read orient live above both, and the module graph is the check";
        :>> createdAt = "2026-09-14";
        :>> createdBy = "claudeFable5";
        :>> status = DecisionStatus::accepted;
        :>> context = "D0479 orders the decomposition of keel-cli leaves first, with every cycle broken before the boundary it crosses is drawn. scripts/modgraph.py, written for dcGuardsViewOrientCycleIsBroken, read 32 references across five back-edges at 6a22002: view -> guards (10), orient -> guards, write -> guards, scaffold -> guards, view -> orient. Three of them were one shape. view::compute_readiness ran the whole guard suite (GUARD_NAMES filtered of assured and critique, each through run_one) to fill the invariant_violations category of the assured verdict; view::report_cards and orient_html read orient::compute for the frontier; view::priority_signals read orient::ready. A view that runs the guards, and a guard (assured, priority-inversion) that reads that view, is a cycle Cargo will refuse at the member boundary, and it is also why keel gate assured cost keel gate guard plus every composed view (the term D0311 named). The remaining references were helpers that had grown in the wrong file: the marker and retro text scanners, the UUID shapes, the gate-outcome predicates, the done-set, the git blob readers, the CLI-fact parser and the step-check bindings were read by view, orient, write, cursor and scaffold but defined in guards or orient. Two tests sat in the module of their fixture rather than the module of the function they exercise, and one guard function existed only so a test in view could reach it.";
        :>> decision = "A view runs no guard. view::readiness(root, task_suspect, invariant_violations) computes the categories a view can compute alone - coverage, critique, findings, population - and takes the suspect walk and the guard suite's violations as inputs; guards::compute_readiness composes them by running the suite, and assured_blockers and assured_report move to guards beside it. The report compositions - report_cards, report, report_html, orient_html and the six card builders - move to crate::reports above view, orient and guards, and the priority lens moves to crate::priority above view and orient; view keeps the pure vocabulary they use (pct, card, cov_tone, trend_series, the coverage rows) and makes it crate-visible. The shared helpers move DOWN into leaf modules of their own: textscan (string-literal stripping, engine markers, retro texts, the gate_passed / gate_recorded / gate_has_result predicates), ident (gen_uuid and the three UUID shapes), done (the done-set), evidence (step 1 of an orient run), suspect (steps 3-5 and suspect(root), which coverage and readiness read instead of a whole orient::compute), plus gitfacts (valid_commits, batch_cat_blobs, git_sha_valid), binding (step_check_bindings) and keel-schema's cli_facts (parse_cli_facts). Each test moves to the module whose function it exercises; retro_backlog_violations_for_test is deleted and the test reads retro_backlog_violations directly. No trait object hides an edge, no guard predicate changes, and scripts/modgraph.py --check, with the five forbidden pairs listed in it, is the instrument that says the layering holds.";
        :>> rationale = "The alternative each back-edge offered was a trait object or a callback handed down into view so that view could run the guards without naming them; D0479 forbids that because it keeps the dependency and hides it from the graph, and a hidden dependency is exactly what a member boundary would then expose as a compile failure. Moving the composition UP to where the guards already are, and the helpers DOWN to a leaf, is the only shape in which every module reads only what sits below it, which is the property the next extractions (dcModelAndWriteAreMembers onward) need to be mechanical. The guard source changes because compute_readiness and two test modules move into it and one function leaves it; that is the enforcement surface under D0209 clause 2 and this Decision is the co-committed marker for it - the predicates of all 75 guards are untouched, keel --help is byte-identical, and the guard count is the same before and after. MEASURED: keel verify . --probe --no-receipt on the working tree at 6a22002 plus this change, host 0F3DGVX25193H7, 2026-09-14, one run of the ladder: keel gate guard rung 2 s (75 guards, ALL PASS), clippy 76 s, keel suite --touched 570 s over 74 binaries plus the lib (878 passed), every rung green in 650 s; the guard rung read 2 s before the change as well (sprint 717 evidence) - the composition moved, its cost did not.";
        :>> consequences = "Readiness costs what it did (the suite still runs once for the assured verdict) but now from guards, so a view can be built into a member that does not depend on the guards. keel show coverage, the reports' coverage rows and readiness read suspect::suspect(root) - the walk alone - instead of a full orient run. Callers move: keel_cli::view::priority -> keel_cli::priority::priority, view::report / report_html / orient_html -> reports::, view::assured -> guards::assured_report. The view submodules critique, reports and staleness become pub so their crate-visible items are not redundant under the crate's nursery lints. Left standing: view still owns the Model, ViewError and the pure vocabulary the reports use through a wildcard import; the next sprint (dcWorkspaceLayeringIsGuarded, D0483) turns modgraph --check into a guard so a back-edge fails at the gate rather than in a DoD. NOT A FORK: this Decision records the one course D0479 already chose for cycles; the trait-object route is named only as what it forbids.";
    }
    #DerivedFrom dependency from d0485 to st126;

    // acceptance event (D0121 review-queue sign-off; D0066/D0106 — human-judged, not fabricated)
    verification d0485Accept : Test { :>> id = "971649f7-2730-4cd0-a505-ca8034892b60"; :>> method = VerificationMethod::confirmation; :>> procedureText = "Said in chat 2026-09-14 over the twenty-eighth publish of the decision brief, which carried fifteen held asks; one instruction covers the fourteen non-forks, d0485 among them. The fork d0466 is not covered - it needs an option letter and stays held. - their words, verbatim: “Accept all proposals. Proceed to design with needs, etc.” WARN: read-back - the quoted words do not name d0485 (D0201 B); recorded as given (D0423)."; }
    part d0485AcceptR1 : TestResult { :>> id = "ac179968-0cd8-422b-bfe5-c36dbf71ee62"; :>> outcome = VerdictKind::pass; :>> judgedAgainst = "d110d0a"; :>> judgedAt = "2026-09-14"; :>> judgedBy = "wweatherholtz"; :>> createdBy = "claudeFable5"; }
}
