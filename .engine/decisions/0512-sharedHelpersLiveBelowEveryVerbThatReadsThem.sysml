// D0512 (status: the `status` field below is the truth) — sharedHelpersLiveBelowEveryVerbThatReadsThem: a helper every verb shares lives in the lowest member that reaches what it needs - project discovery in keel-git, the hook ledger writers in keel-write, fork detection in keel-model, the init path walk in keel-fs, the argument helpers in member keel-args
// Recorded via `keel record decision` (D0105 RMWX axis; issue054). Acceptance is a separate explicit
// human gate (method=confirmation, D0106): flip status + add the d0512Accept event on sign-off.
package Decision0512 {
    private import EngineElement::*;
    private import EngineWork::*;
    private import EngineVerification::*;
    private import EngineRelationships::*;

    part d0512 : Decision {
        :>> id = "0bf09b52-defa-4a9a-8310-88f61df5d974";
        :>> title = "sharedHelpersLiveBelowEveryVerbThatReadsThem: a helper every verb shares lives in the lowest member that reaches what it needs - project discovery in keel-git, the hook ledger writers in keel-write, fork detection in keel-model, the init path walk in keel-fs, the argument helpers in member keel-args";
        :>> createdAt = "2026-09-17";
        :>> createdBy = "claudeFable5";
        :>> status = DecisionStatus::accepted;
        :>> context = "D0479 split keel-cli into members and D0511 placed the Claude hooks as member keel-hooks with project discovery (find_repo_root, engine_version_skew) as keel_process::workspace pub fns, the process layer's. dcKeelCliIsThinDispatch then stalled: scripts/verb_homes.py, written for sprint 740, computes for every top-level item of keel-cli/src/main.rs the least member that could hold it, and before the move no cmd_ body could leave the binary - each reached root_arg (keel-process, so every verb sat above the process layer), the ledger writers (keel-hooks, above everything), fork detection (keel-serve, the console), walk_longest (a pub fn of keel-cli's lib.rs, no member at all) or the nine private argument helpers of main.rs. The pre-move tree gave cmd_accept, cmd_judge_set and cmd_record only keel-serve(+keel-hooks) as a home, and three items no home but the binary.";
        :>> decision = "A helper that every verb shares lives in the lowest member that reaches everything the helper needs, so that a verb's body can move to the member that owns its substance without pulling the console, the hooks or the process layer under it. Concretely, by scripts/extract_seams.py (dry-run default, idempotent, its slices conserved and its rewrites counted): project discovery - Workspace, is_project, missing_project_dirs, require_project, canon, discover, find_repo_root, engine_version_skew - is keel_git::projects (keel-git spawns git and reaches nothing above keel-perf; the workspace GATE stays in keel_process::workspace and re-exports the names, so every keel_process::workspace:: and keel_cli::workspace:: path resolves); the hook ledger writers ledger_gate, ledger_refused, refused_injected_prose and the line writer ledger_line are keel_write::ledger, with the slow-fire threshold SLOW_FIRE_MS and slow_fire_phases from keel_view::pm beside them so the writer and the reader share one constant (keel-hooks re-exports the three the binary calls, keeps ledger_fire beside the emitted-verdict cell it reads, and no longer depends on keel-process; pm re-exports the threshold); fork_options, NOT_A_FORK, fork_signals and disguised_fork are keel_model::textscan, re-exported by keel_serve::deck; walk_longest is keel_fs's, re-exported by keel-cli's lib.rs; and the nine argument helpers - without_flag_values, root_arg, refuse_flag_as_path, flag, prose_flag, prose_args, provenance_date, positional_arg, repo_arg - with root_arg's test are member keel-args, which depends on keel-git alone, is re-exported as keel_cli::args and imported by name in main.rs. The two doc comments earlier moves stranded (root_arg's in workspace.rs, cmd_init's above positional_arg) are reattached to their fns. This reverses D0511's clause that project discovery from the current directory is the process layer's and that the ledger helpers are keel-hooks'; the rest of D0511 stands.";
        :>> rationale = "verb_homes.py measures the claim: on the applied tree its --check names exactly the three items that reach keel-cli's own modules (audit_subverb, cmd_audit, cmd_enroll - history, adherence and enroll, dcTheFourStayingModulesAreMembers' seam), and every cmd_ body has a member home that adds at most keel-args - cmd_accept and cmd_judge_set keel-write(+keel-args), the show verbs keel-view(+keel-args), cmd_serve and cmd_record keel-serve(+keel-args). keel-args is a leaf that reaches only keel-git and keel-perf, so any member that reaches git can take it without widening its build; the least-member rule was refined in the same sprint to say so (a member holds a crate it could depend on without widening its reach), with the acyclicity test the first draft lacked. keel --help is byte-identical, keel version's guard line unchanged, the release build and cargo clippy --workspace --all-targets -D warnings clean, the moved unit tests pass in their new crates, modgraph and module_home hold, and no path under GUARD_SOURCE_FILES or GUARD_SOURCE_DIRS changes. NOT A PROCESS CHANGE: this is code placement inside the binary's workspace - no workflow, gate, schema, guard or hook changes meaning; the hooks fire the same bodies through re-exports. NOT A FORK: the placement of each helper is computed by the tool from the manifests, and the one alternative - leaving the helpers where they were and moving each cmd_ body with a copy of what it reaches - forks truth (D0105) and was rejected by dcKeelCliIsThinDispatch's own DoD.";
        :>> consequences = "dcKeelCliIsThinDispatch can move any cmd_ body to the member verb_homes.py --by-member names, adding keel-args to that member's manifest as it goes; dcTheFourStayingModulesAreMembers moves history, adherence, cursor and enroll first so the three remaining --check lines clear. scripts/verb_homes.py --check is the control behind both (a `# ci-probe: --probe` script; its probe fixture carries a known-negative for two members that each hold a dependency the other lacks). A helper added to main.rs that a verb shares is a defect the table shows as a keel-cli-only row. Sprint 740 delivers this under D0479's charter.";
    }
    #SupersedeClause dependency from d0512 to d0511;

    // acceptance event (D0121 review-queue sign-off; D0066/D0106 — human-judged, not fabricated)
    verification d0512Accept : Test { :>> id = "53a991f8-2268-4cf8-90ac-e2ab455b8367"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0512AcceptR1 : TestResult { :>> id = "067b65eb-7e5c-4c20-afa3-379661cc53d3"; :>> outcome = VerdictKind::pass; :>> judgedAgainst = "b93cb8de"; :>> judgedAt = "2026-09-17"; :>> judgedBy = "wweatherholtz"; :>> createdBy = "claudeFable5"; }
    #DependsOn dependency from d0512 to d0479;
}
