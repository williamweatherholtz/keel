// D0543 (status: the `status` field below is the truth) — runOrchestratorClauseSupersededWhole: clause 5 of the adhere-not-invert direction - the deferred, opt-in, expensive-to-unwind, library-mode-only run orchestrator - is superseded whole so slice one may be chartered, with its keystone condition re-adopted as the run code joining the process-change lock, and the human confirms the sequence harvest first, container third
// Recorded via `keel record decision` (D0105 RMWX axis; issue054). Acceptance is a separate explicit
// human gate (method=confirmation, D0106): flip status + add the d0543Accept event on sign-off.
package Decision0543 {
    private import EngineElement::*;
    private import EngineWork::*;
    private import EngineVerification::*;
    private import EngineRelationships::*;

    part d0543 : Decision {
        :>> id = "84c4b968-e260-4067-8eb7-c321e4472c20";
        // RESEARCH: three rounds of a nine-persona adversarial panel over four revisions of the direction artifact, every finding verified against the repository at f365cb7a; the two landscape spikes D0540 (94 rows) and D0541 (122 user threads); docs/reviews/runner-direction-panel-2026-09-22.md holds the reports and the finding-to-resolution maps.
        :>> title = "runClause: clause 5 of the adhere-not-invert direction - the deferred, opt-in, expensive-to-unwind, library-mode-only run orchestrator - is superseded whole so slice one may be chartered, with its keystone condition re-adopted as the run code joining the process-change lock, and the human confirms the sequence harvest first, container third";
        :>> createdAt = "2026-09-22";
        :>> createdBy = "claudeFable5";
        :>> status = DecisionStatus::accepted;
        :>> context = "D0209 (accepted 2026-08-24 under standing consent) says do NOT invert the topology and, in its clause 5 verbatim: 'An opt-in keel run <process> orchestrator is DEFERRED to last, adopted only for transitions where a landed-then-detected bad state is expensive to unwind, only alongside library mode, and only with its own code inside the signed keystone.' Its rationale reserves the clause for the inversion and says the human may override any clause. The panel record (this sprint's review, D0542) reached revision 4 of a direction whose slice one is exactly that orchestrator in its smallest form: keel run <process>.<step> in keel's own process, one bounded step class, a clone with no remote, a harvest of declared outputs, governance writes replayed through the write API with standing consent suspended, and the gate computed by keel on the merge candidate in a checkout the agent holds no handle to. Three of the clause's four conditions cannot hold for that slice: it runs any runnable step, not only expensive-to-unwind transitions; 'library mode' is used in D0209 and its dossier and defined in neither; and 'deferred to last' is the clause being exercised. The fourth condition can hold as a mechanism: the run's materialise, harvest, replay and gate code lives under a path the process-change guard's lock set lists, so a change to the code that computes done needs a human-held marked Decision. The human also asked in st183 for both a constrained container option and an unconstrained agent option; the direction builds the harvest first and the container third, and that order is theirs to confirm.";
        :>> decision = "OPTION A (recommended): supersede clause 5 of D0209 whole under D0398 - one clause, reversed whole - dropping 'deferred to last', 'only for expensive-to-unwind transitions' and 'only alongside library mode', and re-adopting 'its own code inside the signed keystone' as a mechanism: the run module's path is added to the process-change guard's lock set in the D0504 shape. Slice one may then be chartered in a Change Request whose first deliverable is the schema CR revision 4 names. The human confirms the sequence - harvest first (slice one), daemon protocol on a recorded trigger (slice two), container and proxy third (slice three) - as part of this word. OPTION B: keep clause 5 whole; the direction stays a brainstorm and no run verb is chartered. The rest of D0209 - the acceptance audit, the frozen enforcement surface, the process cursor - stands under either option.";
        :>> rationale = "Under A the three findings of the 2026-08-24 panel still shape the design: the achievable win is deterministic acceptance, so slice one is a harvest-and-gate and not a behaviour controller; the turn-boundary gate stays for interactive work; and the monitor-modifiable-by-monitored gap is closed by the keystone lock the re-adopted condition now makes real for the run's own code. Under B the accepted direction is honoured as written and the counted class of defects the harvest would remove - 129 of 667 issues, 19 percent, where the agent recorded its own result, edited its monitor, or lost a record to the shell - keeps its current controls, which are prose rules and after-the-fact hooks. A is recommended because the alternative D0209 preferred, the process cursor, was built and is reported rather than required, and because the direction's first slice costs one verb and one schema change before anything about a daemon is decided.";
        :>> consequences = "Under A: a #SupersedeClause edge from this Decision to D0209 names clause 5; the CR for slice one lists the run module's path among the process-change lock prefixes, the schema change to ProcessStep, the safety-change for the hook-free spawn, and the measured floor of one run on this host before approval; slices two and three wait on their recorded triggers. Under B: nothing moves and the brainstorm closes with the direction recorded and unapproved. Either way the panel record stands. COST under A: one schema change on the frozen core, one CliCommand, a safety-change for the hook-free spawn, the run module joining the process-change lock, and one measured run before approval. COST under B: the counted 129-issue class keeps its prose controls and the brainstorm closes unapproved.";
    }
    #SupersedeClause dependency from d0543 to d0209;

    // acceptance event (D0121 review-queue sign-off; D0066/D0106 — human-judged, not fabricated)
    verification d0543Accept : Test { :>> id = "f977e972-1a71-4e98-9a7d-6ccc36cfb5c6"; :>> method = VerificationMethod::confirmation; :>> procedureText = "Their words: 'SUPERSEDE clause 5 whole; keel run in-process, one bounded class, schema CR first, floor measured before approval; sequence confirmed' (pasted copy-for-AI digest with this option ticked, chat, 2026-09-22) - their words, verbatim: “SUPERSEDE clause 5 whole; keel run in-process, one bounded class, schema CR first, floor measured before approval; sequence confirmed”"; }
    part d0543AcceptR1 : TestResult { :>> id = "d5becb68-aa88-4e94-9d70-a36bc69a1717"; :>> outcome = VerdictKind::pass; :>> judgedAgainst = "b65a13e4"; :>> judgedAt = "2026-09-22"; :>> judgedBy = "wweatherholtz"; :>> createdBy = "claudeFable5"; }
}
