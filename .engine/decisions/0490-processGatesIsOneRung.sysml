// D0490 (status: the `status` field below is the truth) — processGatesIsOneRung: one gate rung, process-gates, fails a step recorded past a red earlier step in any adopted process, and the editor hook, the commit gate and CI print its verdict lines unchanged
// Recorded via `keel record decision` (D0105 RMWX axis; issue054). Acceptance is a separate explicit
// human gate (method=confirmation, D0106): flip status + add the d0490Accept event on sign-off.
package Decision0490 {
    private import EngineElement::*;
    private import EngineWork::*;
    private import EngineVerification::*;
    private import EngineRelationships::*;

    // RESEARCH: Read 2026-09-15. The process cursor is computed, never stored (cursor.rs:1-22): keel advance answers 'may the next step be taken?' and refuses while an earlier bound step is red (D0435/D0436), but nothing re-asks that question when the record is written - the pre-commit hook runs keel gate validate and keel gate guard (.githooks/pre-commit:88,98), CI runs keel gate validate (.github/workflows/ci.yml:49), and no guard reads a process's step order (grep cursor keel-cli/src/guards.rs: 0 hits). So a passing result on a later step can be recorded and committed while an earlier step's check is red, and the only thing that ever said no was an advisory command the writer may not have run. The Need nCustomProcessRefusesEverywhere (accepted 2026-09-14) asks for the same refusal in the hook, at commit and in CI with the same verdict text.
    // #ProspectiveChange (D0070) - this Decision governs a process/schema change; the co-committed
    // change rides the process-change guard's hard lock.
    #ProspectiveChange part d0490 : Decision {
        :>> id = "a24c44ae-3e49-4d71-9491-6e1156eb3e11";
        :>> title = "processGatesIsOneRung: one gate rung, process-gates, fails a step recorded past a red earlier step in any adopted process, and the editor hook, the commit gate and CI print its verdict lines unchanged";
        :>> createdAt = "2026-09-15";
        :>> createdBy = "claudeFable5";
        :>> status = DecisionStatus::accepted;
        :>> context = "Given the two Decisions before it - a project's process is found, and its steps bind to its Tests - the remaining gap is that the refusal lives only in keel advance. A step's order is enforced at the moment someone asks and nowhere else; the record can still hold a later step's pass beside an earlier step's red check, and the three surfaces that gate the record (the stop hook's fast tier, the pre-commit commit tier, the CI gate job) do not look. This is the third one-clause Decision for the process hook (D0303). What it means for the reader: 'absolute discipline' becomes a fact about what can be COMMITTED, not about which command the writer remembered to run, and the sentence they read is the same on their screen, at commit and in the CI log.";
        :>> decision = "A forward guard named process-gates, one function in the guards member, lists every process adopted in .engine/contracts/activation.toml (engine or project), and for each run computes the step positions with the same resolver keel advance uses; every later step that holds a passing result (or the record its step produces) at a commit where an earlier step's bound check is red is one violation, emitted as one fixed-format line `process-gates: <process> step <later> recorded while <earlier> is red (<check>)`. The fast tier keel gate --fast (the editor hook), keel gate --workspace (the commit tier) and the CI gate job all call that function and print its lines unchanged.";
        :>> rationale = "Refusal at the moment of asking cannot be discipline when the record is written by a different command; a guard over the record is what the engine already uses for every other honest-state rule (D0098), so the process hook is made of the same material as keel's own controls rather than a special case. Parity between three surfaces is by a single implementation, so the requirement's byte comparison is a probe of the construction rather than a test that has to be kept passing by hand. Emitting the violation as a fixed-format line keeps the verdict the same object in the hook ledger, the commit output and the CI log, which is the only form in which three environments can be shown to agree. MEASURED: the resolver the rung would run per adopted process is keel advance <process>; on this host (keel 0.4.1 from keel-serve.exe, tree e344950, 2026-09-15) the seven process files with a bound step cost 115-828 ms each (the intake process the slowest, the four ceremony and analysis ones 140-420 ms), 2.3 s summed serially - the rung's upper bound before it shares one tree read across processes; the fast tier's own budget is the D0389 latency distribution, and the rung is measured against it again on the live set before the pair is recorded.";
        :>> consequences = "Held proposed for the human (a process change: a new rung joins the gate at all three tiers and the activation contract gains it). On acceptance: process-gates is added to the guard set and to .engine/contracts/activation.toml; guards.md gains its row and the count from keel version moves by one; the D0388 pair is the fixture of projectProcessesResolveFromTheProjectTree with a pass recorded on step two while step one is red (red) and the same tree after step one passes (green); the three captures of the fixture violation are compared byte-for-byte in a test. Chartered work: srCustomGateRefusesIdenticallyInThreeSurfaces and ssrProcessGatesIsOneRung (modular-members-requirements.sysml) derive from this Decision. Depends on aStepBindsToAProjectTest.";
    }
    #DerivedFrom dependency from d0490 to st126;
    #DependsOn dependency from d0490 to d0489;

    // acceptance event (D0121 review-queue sign-off; D0066/D0106 — human-judged, not fabricated)
    verification d0490Accept : Test { :>> id = "f4b738e4-107f-4313-b5a1-3e3127aa70b4"; :>> method = VerificationMethod::confirmation; :>> procedureText = "recorded from chat - their words, verbatim: “Accept the three process-hook clauses in order - Read, Bind, Rung. [x] Accept: one forward guard process-gates over every adopted process, one fixed-format violation line, called unchanged by gate --fast, gate --workspace and CI (recommended)”"; }
    part d0490AcceptR1 : TestResult { :>> id = "40945e49-2b4d-40e8-ae7b-a4b71a0466fa"; :>> outcome = VerdictKind::pass; :>> judgedAgainst = "85613c8"; :>> judgedAt = "2026-09-15"; :>> judgedBy = "wweatherholtz"; :>> createdBy = "claudeFable5"; }
}
