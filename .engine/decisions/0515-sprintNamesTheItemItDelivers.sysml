// D0515 (status: the `status` field below is the truth) — sprintNamesTheItemItDelivers: the sprint Story names the backlog item it delivers with a #Delivers edge authored at prep, and the sprint-closure guard holds each delivered item to a DoD TestResult once a later sprint exists
// Recorded via `keel record decision` (D0105 RMWX axis; issue054). Acceptance is a separate explicit
// human gate (method=confirmation, D0106): flip status + add the d0515Accept event on sign-off.
package Decision0515 {
    private import EngineElement::*;
    private import EngineWork::*;
    private import EngineVerification::*;
    private import EngineRelationships::*;

    // #ProspectiveChange (D0070) - this Decision governs a process/schema change; the co-committed
    // change rides the process-change guard's hard lock.
    #ProspectiveChange part d0515 : Decision {
        :>> id = "97ec25a2-85cb-469f-97a3-19229e2700a2";
        :>> title = "sprintNamesTheItemItDelivers: the sprint Story names the backlog item it delivers with a #Delivers edge authored at prep, and the sprint-closure guard holds each delivered item to a DoD TestResult once a later sprint exists";
        :>> createdAt = "2026-09-18";
        :>> createdBy = "claudeFable5";
        :>> status = DecisionStatus::accepted;
        :>> context = "A sprint exists to deliver a backlog item, and nothing in the model says which one. The Story's #CharteredBy edge points at what chartered the work - 755 edges across 705 delivery files: 681 to Decisions, 32 to Needs and Requirements, 42 to backlog items, all of those on sprints 158 to 170 and none since - and a charter is an origin, not a delivery, so nothing reads it as saying which item the sprint finished; the only link between a sprint and the item it delivers is the slug the two share in the story name and the fill's DELIVERED BACKLOG ITEMS line in the DoD prose, and no guard reads either. Twice that gap let a delivered item stand as READY work: sprint 720 closed with its story DoD passing at ecc393e and dcInstrumentAnswersCarryTheirSourceHash had no DoD result, so keel show whats-next ranked it first at 63221a8 (issue563, 2026-09-14); sprint 735 closed at 249dac2 the same way and dcSuiteIsAMember ranked first as ready while two items sat blocked on it as not done (issue589, 2026-09-17). In the second case the recorder wrote exactly the results its dispatch named and check_report.py --owed 7 passed: the primary typed the story and not the item, and the relationship it had to remember was not written anywhere a control could read. The sprint-closure guard (members/keel-guards/src/sprints.rs, sprint_closure) already holds every task of a sprint that has a later sprint to a TestResult; it does not know which backlog item the sprint delivered because the model does not say. The backlog item dcSprintNamesTheItemItDelivers resolves issue589; its DoD names this Decision as step one, a CR with human sign-off because schema/core is frozen and the guard change rides the enforcement lock (D0209 cl.2).";
        :>> decision = "schema/core relationships.sysml gains metadata def Delivers: a work-item Story to the backlog action it delivers, authored as a marked dependency beside #CharteredBy in the sprint delivery file, one edge per delivered item. record sprint --fill authors the edges at prep from a delivers key in the fill file naming the backlog actions, comma-separated, and the sprint-planning skill's DoR names the edge beside the charter edge. The sprint-closure guard gains a clause and keeps its name and count: for each sprint that has a later sprint, every #Delivers target whose DoD Test has no TestResult is a violation naming the sprint and the item, and a sprint recorded on or after this Decision's acceptance date whose Story carries no #Delivers edge is a violation too, because an unnamed delivery is not a delivery. Sprints recorded before that date carry no edge and are history: nothing backfills by guessing from a shared slug. The guard unit test carries the D0388 pair: a fixture with sprint N delivering item X with no DoD result and sprint N+1 present is red naming X; the same fixture with X's result is green.";
        :>> rationale = "The two occurrences are one defect: a relationship that governs whether an item is done existed only in a name and in prose the primary types into a dispatch, so the control that would have caught it had nothing to read. A typed edge is the shape every other governing relationship in this model already takes - the charter, the resolver, the prioritiser - and the sprint-closure guard is the control that already answers the question this edge completes, which is why the clause joins it rather than founding a seventy-seventh guard. The edge is authored at prep because that is when the sprint knows what it is for and when the sprint-planning skill already writes the charter; a closing-time edge would be the same remembered fact moved later. The missing-edge clause is dated to acceptance and not applied to history because a guessed backfill would author the relationship this Decision exists to make explicit, and a guard that reads guessed facts holds nothing.";
        :>> consequences = "A sprint recorded after acceptance that leaves its delivered item without a DoD result is red before commit at the item's name, at the moment a later sprint opens, and the recorder's dispatch can be checked against the edge rather than against the primary's memory. Every sprint from that date carries at least one #Delivers edge or is red; a research spike or ceremony-only sprint that delivers no backlog item is the case this clause does not yet fit, and the first such sprint is the occasion for the clause that names it, not for a silent exemption. The fill file gains a key, the scaffold writes a second edge, the skill's DoR gains a line, and sprints.rs changes under the enforcement lock this Decision's marker authorises. The guard count from keel version stays at 76; guards.md, guard-constraints.sysml and control-map.sysml carry the widened clause on the existing row. The 743 sprints before this date remain readable exactly as recorded, with the slug as their only link to the item, and this Decision states that as the accepted residual.";
    }
    #DependsOn dependency from d0515 to d0068;
    #DependsOn dependency from d0515 to d0260;
    #DependsOn dependency from d0515 to d0209;

    // acceptance event (D0121 review-queue sign-off; D0066/D0106 — human-judged, not fabricated)
    verification d0515Accept : Test { :>> id = "7174559a-0a31-4eaa-9657-f45d77e44dce"; :>> method = VerificationMethod::confirmation; :>> procedureText = "recorded from chat - their words, verbatim: “Accept all decisions as recommended. Proceed to release and fix downstream” WARN: read-back - the quoted words do not name d0515 (D0201 B); recorded as given (D0423)."; }
    part d0515AcceptR1 : TestResult { :>> id = "08c927d1-3886-4bc8-b6c9-d3d1116e2f13"; :>> outcome = VerdictKind::pass; :>> judgedAgainst = "4d00c1bc"; :>> judgedAt = "2026-09-18"; :>> judgedBy = "wweatherholtz"; :>> createdBy = "claudeFable5"; }
}
