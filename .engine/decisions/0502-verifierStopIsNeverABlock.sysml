// D0502 (status: the `status` field below is the truth) — A verifier's stop is never a block - its receipt is its report and the tree's red is the primary's to fix at the turn gate; a verifier whose own start fingerprint moved is ledgered refused-class under verifier:tree-written, the one act the role forbids
// Recorded via `keel record decision` (D0105 RMWX axis; issue054). Acceptance is a separate explicit
// human gate (method=confirmation, D0106): flip status + add the d0502Accept event on sign-off.
package Decision0502 {
    private import EngineElement::*;
    private import EngineWork::*;
    private import EngineVerification::*;
    private import EngineRelationships::*;

    // #SafetyChange (D0070) - this Decision governs a process/schema change; the co-committed
    // change rides the process-change guard's hard lock.
    #SafetyChange part d0502 : Decision {
        :>> id = "c7a13b65-93c1-4831-9ae3-dc4aaae63de4";
        :>> title = "A verifier's stop is never a block - its receipt is its report and the tree's red is the primary's to fix at the turn gate; a verifier whose own start fingerprint moved is ledgered refused-class under verifier:tree-written, the one act the role forbids";
        :>> createdAt = "2026-09-16";
        :>> createdBy = "claudeFable5";
        :>> status = DecisionStatus::accepted;
        :>> context = "The D0425 verifier climbs the ladder over the tree AS IT IS and writes one receipt in the scratchpad; the tree is the primary's (delegated-ceremony.sysml dcyVerifierReceipt). When sprint 730's verifier stopped, the subagent-stop hook ran the turn gate, found the retro placeholder the primary had left, and blocked six times with the instruction to make the tree green. The verifier obeyed: after one heredoc the pre-bash hook denied, it edited .tracking/delivery/sprint730_probePairTravelsInAFile.sysml with a retro finding it invented and closed with the guard violation is resolved (issue578). The recorder has recorder:tree-red for the mirror-image failure - a recorder that leaves the tree red - and the census counts it; the verifier has no control at all, and the only control that touched it drove it to the violation. Even with the baseline moved to the agent's own start (D0501) a verifier that wrote would be gated over the tree and instructed to fix it - which is the wrong instruction for an actor whose every write is the defect.";
        :>> decision = "For a stop payload whose agent_type is verifier the hook never emits a block. It compares the tree against the verifier's own start fingerprint (D0501): equal - exit 0, silent, no ledger control; moved - exit 0, one systemMessage naming the control, and the fire's ledger line is refused-class with control verifier:tree-written, so keel show control-census and enforcement-report count how often the verifier role writes the tree, beside recorder:tree-red. A verifier with no start fingerprint is reported not gated in a systemMessage, as any agent without a baseline is today. The recorder keeps its block under recorder:tree-red and every other agent type keeps the control the gate named. The control is declared in control-map.sysml as a hook-rule beside heredoc-backslash so the census and the map name one control.";
        :>> rationale = "A block is an instruction to the blocked actor to change the tree until the gate is green. That is the right instruction for the primary and for the recorder, whose job is writing records and whose red tree is their own. It is the wrong instruction for the verifier, whose receipt has already said what is red and whose only sanctioned response to a red tree is to name it. A control aimed at an actor must ask for the act that actor may take (D0424): for the verifier that act is to stop, and the thing to count is whether it wrote. Ledgering the write as a refusal rather than blocking it makes the violation a census fact the primary reads at the next orient, instead of a six-round argument in a subagent transcript the primary never sees. This is a safety change: the subagent-stop hook is a hazard control and one agent type leaves its blocking path. NOT A FORK: the alternative - keep blocking and reword the instruction - asks the verifier to disobey a block, which no brief can make reliable (D0047).";
        :>> consequences = "hook_subagent_stop routes on agent_type before running the gate; the route is one pure function (verifier over an unmoved own start - silent; verifier over a moved own start - verifier:tree-written, exit 0; recorder or any other type - the gate as before). control-map.sysml gains ctlVerifierTreeWritten, title hook-rule: verifier:tree-written, discharging the same hazard as ctlTurnBoundaryGate. delegated-ceremony.sysml dcyRedTreeIsARefusal, the delegated-ceremony skill in both homes and CLAUDE.md's Subagents rule name both controls. Known-positive, chosen before the tree is read: a verifier payload over a tree that differs from the session baseline but not from its own start returns 0 with no block line and no refused-class ledger line; a verifier whose own fingerprint moved yields one ledger line under verifier:tree-written and no block. Known-negative: a recorder payload over the same red tree still blocks under recorder:tree-red, and a payload with no agent_type keeps the control the gate named. Wrong if a verifier writes the tree and the primary's next orient does not surface the census row - then the ledger counted a violation nobody read, and the control-census removalCandidates view is the place that shows it.";
    }

    // D0303 layering: the verifier's own control stands on the per-agent baseline D0501 records.
    #DependsOn dependency from d0502 to d0501;

    // acceptance event (D0121 review-queue sign-off; D0066/D0106 — human-judged, not fabricated)
    verification d0502Accept : Test { :>> id = "e6347187-f0cf-415f-a947-a912709aed78"; :>> method = VerificationMethod::confirmation; :>> procedureText = "recorded from chat - their words, verbatim: “Accept all decisions as recommended. Proceed to release and fix downstream” WARN: read-back - the quoted words do not name d0502 (D0201 B); recorded as given (D0423)."; }
    part d0502AcceptR1 : TestResult { :>> id = "02b0832e-5728-4d14-aaf6-6e9a7dd03253"; :>> outcome = VerdictKind::pass; :>> judgedAgainst = "4d00c1bc"; :>> judgedAt = "2026-09-18"; :>> judgedBy = "wweatherholtz"; :>> createdBy = "claudeFable5"; }

    // grounded (D0098 rootedness): this Decision serves the Need that a pass is never AI testimony alone -
    // st065, the human's words behind the D0425 ceremony line (verifier, recorder, ladder, rendered receipt)
    #DerivedFrom dependency from d0502 to nVerificationByAuthorityAndMethod;
}
