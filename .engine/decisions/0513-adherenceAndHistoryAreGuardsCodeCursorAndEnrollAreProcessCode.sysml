// D0513 (status: the `status` field below is the truth) — adherenceAndHistoryAreGuardsCodeCursorAndEnrollAreProcessCode: the four modules still beside main.rs move to the members that own them - the two audits that re-derive the gate verdict into keel-guards, under its directory lock; the process cursor and actor enrollment into keel-process - so the enforcement surface names one locked directory and one locked file
// Recorded via `keel record decision` (D0105 RMWX axis; issue054). Acceptance is a separate explicit
// human gate (method=confirmation, D0106): flip status + add the d0513Accept event on sign-off.
package Decision0513 {
    private import EngineElement::*;
    private import EngineWork::*;
    private import EngineVerification::*;
    private import EngineRelationships::*;

    // #ProspectiveChange (D0070) - this Decision governs a process/schema change; the co-committed
    // change rides the process-change guard's hard lock.
    #ProspectiveChange part d0513 : Decision {
        :>> id = "ecc3ebfb-7b84-4f90-b30d-329935fa75f9";
        :>> title = "adherenceAndHistoryAreGuardsCodeCursorAndEnrollAreProcessCode: the four modules still beside main.rs move to the members that own them - the two audits that re-derive the gate verdict into keel-guards, under its directory lock; the process cursor and actor enrollment into keel-process - so the enforcement surface names one locked directory and one locked file";
        :>> createdAt = "2026-09-17";
        :>> createdBy = "claudeFable5";
        :>> status = DecisionStatus::accepted;
        :>> context = "After sprint 740 (D0512) keel-cli/src holds main.rs, lib.rs and four modules: adherence.rs (445 lines, keel audit adherence - re-runs every guard over each commit of the git tree and refuses a weakened guard set), history.rs (172 lines, keel audit history - the same re-derivation over the commit range), cursor.rs (568 lines, keel advance - the process cursor) and enroll.rs (297 lines, keel enroll - the actor-enrollment process). scripts/verb_homes.py --check names exactly the three main.rs items that reach them (audit_subverb, cmd_audit, cmd_enroll) as having no home but the binary; dcTheFourStayingModulesAreMembers is the frontier item and dcKeelCliIsThinDispatch depends on it. adherence.rs is on the enforcement surface: GUARD_SOURCE_FILES in members/keel-guards/src/enforcement.rs (line 71) names keel-cli/src/adherence.rs beside members/keel-schema/src/guard_names.rs, and GUARD_SOURCE_DIRS (line 78) locks members/keel-guards/src/ by prefix. Moving adherence.rs therefore changes what the process-change guard locks, which D0209 clause 2 says needs a marked Decision held for the human before it lands; D0511 and D0512 carried no marker because no locked path moved.";
        :>> decision = "adherence.rs and history.rs become members/keel-guards/src/adherence.rs and history.rs: they are the audits that re-derive the guard verdict from the git tree, so they are guards code and belong under the directory the enforcement surface already locks by prefix. The keel-cli/src/adherence.rs entry is retired from GUARD_SOURCE_FILES (its file is under GUARD_SOURCE_DIRS by construction, so the logic stays locked and nothing is unlocked by the retirement), history.rs enters the lock by the directory it enters, and the is_enforcement_surface test asserts members/keel-guards/src/adherence.rs and members/keel-guards/src/history.rs locked and keel-cli/src/adherence.rs not. cursor.rs and enroll.rs become members/keel-process/src/cursor.rs and enroll.rs: the process cursor and actor enrollment are the process layer's and neither is on the enforcement surface. keel-cli's lib.rs re-exports the four at their old paths (keel_cli::adherence, history, cursor, enroll) so every caller resolves unchanged; keel --help is byte-identical and the guard count from keel version is unchanged. One transform (dry-run default, --apply, idempotent, reconciliation line) makes the moves, and its plan asserts no slice starts below a doc line or attribute (issue601). After the move keel-cli/src holds main.rs and lib.rs only and scripts/verb_homes.py --check exits 0.";
        :>> rationale = "The enforcement surface is defined by two constants whose purpose is that a guard's logic cannot be edited without a marked Decision (D0209 clause 2, issue236). The move keeps that invariant at every commit: before, adherence.rs is locked by name; after, it is locked by the directory prefix, and the enforcement_surface_covers_every_guard_source test - which fails CI when a guard-defining file appears outside the lock - runs on both trees. history.rs is today unlocked although it re-derives the same verdict (a weakening planted there would not be a locked-path edit); the move closes that by putting it under the prefix, which is why the change is a strengthening and not a relaxation of the lock, and the known-negative of the item's DoD (a weakened guard set in a scratch clone is still refused by keel audit adherence from its new crate) is the check. cursor and enroll go to keel-process because keel advance and keel enroll are the process layer's verbs (D0435/D0436 for the cursor; skill actor-enrollment for enroll), and verb_homes.py names keel-process as the least member for cmd_enroll once enroll.rs is there. The marker is process-change because GUARD_SOURCE_FILES changes: retiring the file entry is an edit to the locked set even though the file it named stays locked by another rule.";
        :>> consequences = "Held proposed for the human (D0337): the sprint that applies it (dcTheFourStayingModulesAreMembers) does not land until this Decision is accepted, because the commit edits enforcement.rs's locked constants. On acceptance: the four files move, GUARD_SOURCE_FILES reads members/keel-schema/src/guard_names.rs alone, the locked set gains history.rs, keel-cli/src is main.rs and lib.rs, verb_homes.py --check exits 0, and dcKeelCliIsThinDispatch can begin moving the cmd_ bodies to the members verb_homes.py --by-member names. Rejected: the modules stay in the binary and dcKeelCliIsThinDispatch is re-scoped to leave audit_subverb, cmd_audit and cmd_enroll in main.rs, or the process-change guard gains a stays-in-binary reason for keel-cli/src/adherence.rs. Depends on D0479 (the member split) and D0209 (the enforcement surface and its clause 2).";
    }
    #DependsOn dependency from d0513 to d0479;
    #DependsOn dependency from d0513 to d0209;

    // acceptance event (D0121 review-queue sign-off; D0066/D0106 — human-judged, not fabricated)
    verification d0513Accept : Test { :>> id = "a96398ea-e82a-4c12-920c-6d00b5c208bf"; :>> method = VerificationMethod::confirmation; :>> procedureText = "recorded from chat - their words, verbatim: “Accept all decisions as recommended. Proceed to release and fix downstream” WARN: read-back - the quoted words do not name d0513 (D0201 B); recorded as given (D0423)."; }
    part d0513AcceptR1 : TestResult { :>> id = "f35aeb2a-9a4b-4ce7-b1f8-bc3c6865eb6a"; :>> outcome = VerdictKind::pass; :>> judgedAgainst = "4d00c1bc"; :>> judgedAt = "2026-09-18"; :>> judgedBy = "wweatherholtz"; :>> createdBy = "claudeFable5"; }
}
