// D0533 (PROPOSED — NOT YET ACCEPTED) — The verifier's receipt is rendered from the receipt files by scripts/verify_receipt.py - every verdict line below the header is a field read, DISCREPANCIES is the computed list, and the verifier supplies only its noted writes
// Recorded via `keel record decision` (D0105 RMWX axis; issue054). Acceptance is a separate explicit
// human gate (method=confirmation, D0106): flip status + add the d0533Accept event on sign-off.
package Decision0533 {
    private import EngineElement::*;
    private import EngineWork::*;
    private import EngineVerification::*;
    private import EngineRelationships::*;

    // #ProspectiveChange (D0070) - this Decision governs a process/schema change; the co-committed
    // change rides the process-change guard's hard lock.
    #ProspectiveChange part d0533 : Decision {
        :>> id = "20c01a25-f1b5-499f-bb7b-7db190731159";
        :>> title = "The verifier's receipt is rendered from the receipt files by scripts/verify_receipt.py - every verdict line below the header is a field read, DISCREPANCIES is the computed list, and the verifier supplies only its noted writes";
        :>> createdAt = "2026-09-19";
        :>> createdBy = "claudeFable5";
        :>> status = DecisionStatus::proposed;
        :>> context = "The D0425 verifier ends its dispatch by writing a receipt whose last verdict line, DISCREPANCIES, is the one the recorder acts on. Three times in six sprints (676, 745, 750; issue490) that line read NONE over the receipt's own LADDER row saying outcome=fail touched=fail failed=2: a haiku agent read the toml, summarised it, and typed the summary wrong, and the recorder read the summary. Once (sprint 726; issue567) a verifier read the running stub seventeen seconds after launch and typed killed while five cargo processes were alive. D0497 made the wait a command (keel verify --wait) and the sprint 750 retro still names the typed summary as the open resolver dcVerifierReceiptOutcomeIsRenderedNotTyped. The receipt's inputs are all files the ladder wrote - verify-receipt.toml, touched-receipt.toml, verify-launch.epoch, verify-touched.out - plus git and two outside checks; nothing in it is the verifier's judgment except the writes it noticed on the way.";
        :>> decision = "The verifier's receipt is the stdout of scripts/verify_receipt.py, written to the path the dispatch names with --out. The script reads the four receipt files, runs gate check-engine and sync-claude --check under --keel, reads HEAD, the dirty-path count and the changed paths' stems by the rule members/keel-suite/src/touched.rs uses, and renders the receipt shape the test-verify skill's step 6 has carried since D0438. DISCREPANCIES is computed: one line per rung that is not pass, per failing test name, per receipt dated before the launch, per touched receipt dated after the ladder, per stems mismatch, per head mismatch, per non-zero outside check; NONE is printed when that list is empty and is never typed. A receipt whose ladder says running exits 2 with one WAIT line naming the rung and the seconds while the writer pid (D0493) or any keel or cargo process is alive, and exits 3 with KILLED at the rung naming verify-launch.epoch and the receipt's at when none is; neither writes a RESULT block. The test-verify skill's steps 4 to 6 run the script in a bounded wait loop until it exits 0 or 3 and forbid editing the rendered file; the only line the verifier supplies is VERIFIER-NOTED WRITES, through --noted, because that line is its own noticing and nobody's verdict (D0516).";
        :>> rationale = "The defect was never the evidence - every receipt file said the truth - it was an agent restating the evidence in its own words and the next agent reading the words. Removing the restatement removes the class, which is the D0047 shape; asking the verifier to read more carefully is the reminder D0047 refuses, and it was asked three times. A rendering is checkable by anyone who re-runs the script over the same files, so a receipt can be re-derived after the fact where a typed one could only be believed. Liveness is a process, not a field: a stub that says running is in flight or dead, and the observable that separates them is whether its writer is alive (D0493 named the pid for exactly this); a verifier at second seventeen cannot know which by reading, so the script asks the process table and the skill loops on its answer. Running the two outside checks inside the script rather than beside it means their exit codes are copied, not transcribed. This is a process change - the verifier's procedure (D0438) changes - so the record is held for the human under D0337.";
        :>> consequences = "scripts/verify_receipt.py exists with ci-probe --probe on line 2, so scripts/script_probes.py runs its known cases at every pre-commit and in CI. Its probe carries: a fixture whose touched receipt says fail with two failing names renders a red block naming both and no NONE; a pass fixture renders passed=N failed=0 and DISCREPANCIES: NONE; running with an alive writer is one WAIT line and exit 2 with no block; running with no writer is KILLED at the rung naming the epoch and at, exit 3; a receipt dated before the launch is STALE and a discrepancy; a touched receipt dated after the ladder is a rewritten-by-a-later-run discrepancy, the case keel land produced on 2026-09-19 when it overwrote the ladder's 963-passed receipt with its own 736; no receipt is NO RECEIPT exit 3; and the stem rule (view/mod.rs to view, main.rs and lib.rs to none, any .engine/ path to init). The test-verify skill is 0.4.0: step 2's hand-run checks move into the script, step 4 is the wait loop, step 5 is the table of what the script computes, step 6 forbids editing the file. Known-negative, stated: the script cannot see a receipt the ladder never wrote, and a dispatch that names the wrong pair file still produces a truthful red at the probe rung - the rendering is only as honest as the files, which is the point. Wrong if a verifier ever needs to add a verdict line by hand - it never does; a line the script cannot render is a script defect, tracked as an Issue. Resolves issue490 and issue567; delivered by dcVerifierReceiptOutcomeIsRenderedNotTyped, sprint 751.";
    }

    // grounded (D0098 rootedness): this Decision serves the Need that a pass is never AI testimony alone -
    // st065, the human's words behind the D0425 ceremony line (verifier, recorder, ladder, rendered receipt)
    #DerivedFrom dependency from d0533 to nVerificationByAuthorityAndMethod;
}
