// D0493 (status: the `status` field below is the truth) — One touched run at a time per tree - the running stub names its writer and a second launch is refused while that process is alive
// Recorded via `keel record decision` (D0105 RMWX axis; issue054). Acceptance is a separate explicit
// human gate (method=confirmation, D0106): flip status + add the d0493Accept event on sign-off.
package Decision0493 {
    private import EngineElement::*;
    private import EngineWork::*;
    private import EngineVerification::*;
    private import EngineRelationships::*;

    part d0493 : Decision {
        :>> id = "2b7df149-efa2-4fda-a48c-7a97512b5ed0";
        :>> title = "One touched run at a time per tree - the running stub names its writer and a second launch is refused while that process is alive";
        :>> createdAt = "2026-09-15";
        :>> createdBy = "claudeFable5";
        :>> status = DecisionStatus::accepted;
        :>> context = "Sprint 724's second VERIFIER (D0425) launched `keel verify . --probe POS,NEG` twice, two seconds apart, and nothing refused the second launch. Both ladders reached the touched rung; the two touched runs raced on the receipt rename (verify-touched.out line 536, `touched: receipt could not be written`) and on the lib tests' fixed scratch directories (`std::env::temp_dir().join('<literal>')`, some twenty sites), and the receipt reported five red lib tests of which none holds alone - 58/58 keel-write and keel-actor lib tests pass in one run. The D0387 running stub written before cargo starts said `running` but named no writer: a second launcher reading it could not tell a live run from a killed one, and the only thing D0387 asked of a stub was that it not read as a verdict. Tracked as issue569 (High); its sibling issue570 (the shared scratch directories) is the next item. The verifier that launched twice was told, on re-dispatch, to launch exactly once - a reminder, which D0047 says is not a control.";
        :>> decision = "The `running` stub of `.keel/metrics/touched-receipt.toml` and of `.keel/metrics/verify-receipt.toml` carries `pid`, the process writing it. `keel suite --touched` (and so `keel land`'s touched run) and `keel verify` READ the receipt on disk before writing their own stub and REFUSE with exit 2 - nothing written, no cargo started - while it says `running` and that pid is a live process on the host, the refusal line naming the pid, the stub's `at` and (for the touched run) its log. A stub whose pid is gone, a stub from before the pid rode it, and a finished receipt refuse nothing: a killed run's stub is replaced as D0387 intended. Liveness is read from the host (`tasklist` for exactly that pid on Windows; `/proc/<pid>` or `kill -0` elsewhere), never inferred from the stub's age.";
        :>> rationale = "The launch is the one place the collision is visible before it costs anything: the second process has the first's stub in hand and has written nothing yet. Refusing there keeps the receipt single-writer, keeps the scratch directories single-tenant for as long as issue570 stands, and turns a double-launching verifier's red into a receipt line naming the process it should have waited for. The pid is the smallest fact that distinguishes a live run from a killed one; an age threshold would either refuse a slow legitimate run or admit a fast second one. MEASURED on this Windows 11 host: a stub naming this process's own pid refuses the launch and names the pid and `at` (the D0388 known-positive, in the lib test and live against the built binary - exit 2, the stub unchanged, zero cargo processes started); a stub naming a spawned-and-exited child's pid, a stub with no pid, and a finished receipt each proceed (the known-negative). NOT A FORK: a lock file beside the receipt was the alternative and is the same fact with a second home - a lock outlives a killed process exactly as a stub does, and would still need the pid to tell the two apart. NOT A PROCESS CHANGE: the ceremony's steps, actors and gates are as D0425 left them; a CLI launch refuses a concurrent duplicate of itself.";
        :>> consequences = "touched.rs: `Phase::Running` carries `pid`; `live_run_in` reads a stub back; `exclusive_refusal(text, alive)` is the pure control and `pid_alive` the host read; `run()` returns `Err` with the refusal before its first write, so `keel suite --touched` exits 2 and `keel land` refuses to push naming the live run. verify.rs: `Ladder` carries `pid`, rendered and parsed (0 on an older receipt); `cmd` refuses before its first stub. Both help texts say so. A verifier that double-launches now gets `REFUSING to launch a second` in its output instead of a red no test caused. Resolves issue569 through dcTouchedRunIsExclusive; issue570 (per-process scratch directories) remains the second half of the race and is the next item on the frontier.";
    }

    // acceptance event (D0121 review-queue sign-off; D0066/D0106 — human-judged, not fabricated)
    verification d0493Accept : Test { :>> id = "0e4ba131-ebc1-4da8-ad8e-c1b29f3bed74"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0493AcceptR1 : TestResult { :>> id = "c878b7fd-5405-4561-923d-70c4f4bd2adc"; :>> outcome = VerdictKind::pass; :>> judgedAgainst = "ea02af5"; :>> judgedAt = "2026-09-15"; :>> judgedBy = "wweatherholtz"; :>> createdBy = "claudeFable5"; }
}
