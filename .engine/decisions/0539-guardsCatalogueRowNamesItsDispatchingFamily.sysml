// D0539 (PROPOSED — NOT YET ACCEPTED) — every row of .engine/docs/guards.md carries a Family cell, and doc-guard-count holds that cell equal to the family whose table dispatches the guard - a guard moved between family files without its row is a red gate
// Recorded via `keel record decision` (D0105 RMWX axis; issue054). Acceptance is a separate explicit
// human gate (method=confirmation, D0106): flip status + add the d0539Accept event on sign-off.
package Decision0539 {
    private import EngineElement::*;
    private import EngineWork::*;
    private import EngineVerification::*;
    private import EngineRelationships::*;

    // #ProspectiveChange (D0070) - this Decision governs a process/schema change; the co-committed
    // change rides the process-change guard's hard lock.
    #ProspectiveChange part d0539 : Decision {
        :>> id = "513a94c6-d6ac-4206-8103-25374e445204";
        :>> title = "every row of .engine/docs/guards.md carries a Family cell, and doc-guard-count holds that cell equal to the family whose table dispatches the guard - a guard moved between family files without its row is a red gate";
        :>> createdAt = "2026-09-20";
        :>> createdBy = "claudeFable5";
        :>> status = DecisionStatus::proposed;
        :>> context = "Sprint 733 split keel-cli/src/guards.rs into nine family modules, members/keel-guards/src/<family>.rs, each carrying a FAMILY table of the guards it dispatches, and lib.rs's FAMILIES holds the nine in family order. The catalogue, .engine/docs/guards.md, groups its rows by TIER - Hard-blocking, Warning-only, the non-blocking burndown - and said nothing about family, so a reader who found a guard in the catalogue could not find its code without a grep; issue584 recorded that the backlog DoD of dcGuardsAreMembersPerFamily had assumed the catalogue grouped by family when it did not. The one control on the catalogue's rows was every_guard_has_a_catalogue_row (lib.rs), a substring match for the row's first cell; nothing held any other cell to the code, and doc-guard-count, the hard guard that already reads CLAUDE.md and every .engine/docs/*.md, policed only the total-count literal (issue246).";
        :>> decision = "Both catalogue tables gain a Family column - the header reads | Guard | Family | What it enforces | (or What it flags) - and every guard row's second cell names the family whose FAMILY table dispatches the guard. doc-guard-count gains a second clause: for a catalogue file whose table header declares the column, every row of the shape | `guard` | family | is read, and a row whose cell is empty, is not a family name, or names a family other than the one dispatching the guard is a VIOLATION naming the file and line, the row, the cell and the dispatching family with its module path. The clause reads a file only where the header declares the column, so a downstream copy of guards.md shipped before the column existed claims nothing and stays green. The unit test the_shipped_catalogue_names_every_guards_family holds the reverse direction - every GUARD_NAMES member has a row carrying its dispatching family - and every_catalogue_row_sits_inside_a_table holds that each row renders inside a table (a header above it, no blank line or heading between).";
        :>> rationale = "The family is the guard's code home, and a pointer that nothing checks drifts the first time a guard moves; guards.md had already drifted in a way no reader could see - twenty of its 77 rows rendered outside any table, a blank line splitting the Hard-blocking table and five rows sitting under the Warning-only heading above that table's header (issue667). Holding the column in doc-guard-count rather than doc-sync is deliberate: doc-sync is warning-only by construction (a diff guard, violations always empty), and the DoD asks for a red gate; doc-guard-count is hard, already reads the same files, and its existing clause is the same shape - a fact typed into the catalogue that the code can compute. The header scope is the D0419 lesson (issue433): cli-surface-declared read the engine's Decision citations on a keel init scaffold and turned CI red for six pushes; a clause on a shipped doc must be silent on a copy that predates it. MEASURED: keel gate guard doc-guard-count . --no-receipt on this tree at 957b2888 with the column in place - PASS, 4 scanned, 0 violations, 164 ms wall-clock; the added cost is one pass over guards.md's 77 rows. D0388 pair: a fixture row naming doc-guard-count under identity fails naming the row, identity and enforcement (and a row with an empty cell fails naming sprints for charter); the shipped catalogue passes; a header without the column claims nothing, so the cursor.rs fixture stays a count-only red.";
        :>> consequences = "guards.md's two tables carry three columns; the twenty rows that rendered as prose render as table rows, in their tiers (the tier grouping is unchanged). A guard moved between family modules without its catalogue row fails the commit gate naming both families; a new guard's row must carry its family or the gate is red. Downstream projects see no change until their guards.md carries the column. The tier the catalogue states and the tier keel version reports are still two homes held together by nothing - issue668 tracks that with its own resolver; this Decision does not touch WARNING_ONLY_GUARDS.";
    }
}
