// D0540 (status: the `status` field below is the truth) — agentHarnessLandscapeSpikeSaved: the ninety-four-row landscape of sandboxes, task-owning harnesses, workflow engines, hermetic build and CI, and verification tools is saved as a spike; no tool is adopted and the sixteen mechanisms feed the unapproved tool-owns-the-task design, not the backlog
// Recorded via `keel record decision` (D0105 RMWX axis; issue054). Acceptance is a separate explicit
// human gate (method=confirmation, D0106): flip status + add the d0540Accept event on sign-off.
package Decision0540 {
    private import EngineElement::*;
    private import EngineWork::*;
    private import EngineVerification::*;
    private import EngineRelationships::*;

    part d0540 : Decision {
        :>> id = "583faf38-e071-4c02-83d1-cc82aa19908c";
        :>> title = "agentHarnessLandscapeSpikeSaved: the ninety-four-row landscape of sandboxes, task-owning harnesses, workflow engines, hermetic build and CI, and verification tools is saved as a spike; no tool is adopted and the sixteen mechanisms feed the unapproved tool-owns-the-task design, not the backlog";
        :>> createdAt = "2026-09-20";
        :>> createdBy = "claudeFable5";
        :>> status = DecisionStatus::accepted;
        :>> context = "The human, 2026-09-20 (st184): 'Research alternative harnesses like this. We're talking bazel and GitHub actions, but surely there are sandbox container setups for AI agents. Any strongly considering custom processes and verification workflows? Other strengths we should integrate? Investigate 50 alternative tools, noting what has gained some following recently'. The 'this' is the design in progress from st181-st183: a keel where the tool owns the AI task, processes are chains of typed steps with declared inputs and outputs, two step classes (constrained sandbox, unconstrained proposal), gates are tests bound to steps, the server never executes, runner daemons claim leased steps, browser UI. That design is not approved; the brainstorm's HARD-GATE holds. The spike ran as an adversarial-panel-review (D0187) on the sprint 517 shape: five parallel read-only web-enabled lenses with one shared brief, one round, every number dated and URL-cited, ninety-four table rows (two tools in two lenses, several rows bundling a family, so above a hundred distinct tools). Every lens claim about keel's own state was re-checked against source before use: authoring friction as the #1 risk is CLAUDE.md section 4 (D0054); the verbatim-words acceptance the lenses found no precedent for is keel accept --words (D0192/D0289). The external facts are lens-reported and were not re-fetched by the synthesiser; the review says so in its header and keeps every 'not found' the lenses wrote.";
        :>> decision = "The spike is saved: docs/reviews/agent-harness-landscape-2026-09-20.md is the record - the answer in the order the human asked, a sixteen-row table of mechanisms to integrate each naming the tool it runs in, a following-recently table with numbers and dates, the cross-lens convergences, the adversarial case against the design with a disposition per critique, and the five lens reports appended verbatim with their sources - and this Decision is its charter; the knowledge record .tracking/knowledge/agent-harness-landscape-2026-09-20.sysml holds the D0196 replication text. No tool is adopted, trialled or integrated. No backlog item is raised against the design, because the design is not approved and an item against an unapproved design would author state ahead of the decision; the sixteen mechanisms are inputs to the next design section, where each enters the draft or is declined with a reason. The one backlog item this spike touches is its own, dcAgentHarnessLandscapeIsRecorded, which sprint 758 delivers. NOT A FORK: the human asked for research, not a choice; this records the finding and that nothing changes. NOT A PROCESS CHANGE: no workflow, gate, schema or rule moves; the phrase 'custom processes' above quotes the human's question about other tools.";
        :>> rationale = "The finding worth a record is the empty quadrant: across ninety-four rows every process-defining tool (Spec Kit 138.1k stars, OpenSpec 69.7k, BMAD 53.3k, Kiro, Symphony, Camunda, Kestra, Argo, Temporal) lets the agent or a returned function say when a step is done, and every tool that computes done outside the agent (Harbor, SWE-bench, Runloop Scenario, Inspect, claude plugin eval, Dagster asset checks, in-toto, Lean-kernel provers) ends its process when the eval ends and owns no persistent work item. Nobody harvests declared outputs from an agent sandbox (only build systems do: Bazel, REAPI, Pants, Argo), nobody detects a write with no run behind it, nobody nests processes, and nobody records the human's words as the acceptance. That is where the design sits, and it is why the spike is saved rather than folded into a tool choice. The second finding is that the pieces the design still lacked exist and converge: one run credential held by an egress proxy (six sandbox vendors, GitHub, GitLab, Buildkite), a reserve-acquire-heartbeat lease (Buildkite JAT 2026-08-31, Temporal, Conductor, Symphony, Linear, Paperclip, K8s SandboxClaim), in-toto MATCH as the drift guard, Harbor's task directory as the step shape, Codex cloud's online-setup-then-offline-agent lifecycle, version pinning of in-flight runs (Restate, Vercel, DBOS, Camunda). Saving it as a record rather than re-deriving later is D0040; the numbers are dated because they will be stale within months.";
        :>> consequences = "docs/reviews/agent-harness-landscape-2026-09-20.md exists and names its check date, its epistemic status and its sources; sprint 758 is chartered by this Decision and delivers dcAgentHarnessLandscapeIsRecorded; the knowledge record carries the replication text with a passing result at HEAD. Three critiques change the design draft before it is next presented: 'network off' becomes 'egress only to declared providers through the proxy with the run token'; the repository at a declared ref is itself a declared input, so the constraint is on outputs and credentials and not on reading; the sandbox image is digested into the step as an input. Two are held for the human: whether the browser-only surface applies to the runner protocol as well as to the human (the evidence says every runner-owning system has a scriptable surface, and a runner daemon is one by construction), and whether the verbatim-words acceptance stays as the attestation shape (no precedent in any lens; kept as the one shape that survives a status field being edited). The open runner question - server spawns agents, or daemons claim leased steps - reads against the evidence as the second: every system that is not a vendor owning the compute chose it. Nothing in the engine, the process set or the tracking model changes.";
    }

    // acceptance event (D0121 review-queue sign-off; D0066/D0106 — human-judged, not fabricated)
    verification d0540Accept : Test { :>> id = "aaf25ff7-e535-4adf-b4ea-aa21c9c96e27"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0540AcceptR1 : TestResult { :>> id = "6cc16a55-6ac0-473a-b6d2-b518f1ee4c10"; :>> outcome = VerdictKind::pass; :>> judgedAgainst = "68fb803b"; :>> judgedAt = "2026-09-20"; :>> judgedBy = "wweatherholtz"; :>> createdBy = "claudeFable5"; }
}
