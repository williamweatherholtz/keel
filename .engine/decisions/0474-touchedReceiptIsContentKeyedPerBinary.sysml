// D0474 (status: the `status` field below is the truth) — touchedReceiptIsContentKeyedPerBinary: the touched receipt records, per test binary, the content its outcome depends on, and keel land runs only the binaries that lack a green observation at the pushed content
// Recorded via `keel record decision` (D0105 RMWX axis; issue054). Acceptance is a separate explicit
// human gate (method=confirmation, D0106): flip status + add the d0474Accept event on sign-off.
package Decision0474 {
    private import EngineElement::*;
    private import EngineWork::*;
    private import EngineVerification::*;
    private import EngineRelationships::*;

    // #ProspectiveChange (D0070) - this Decision governs a process/schema change; the co-committed
    // change rides the process-change guard's hard lock.
    #ProspectiveChange part d0474 : Decision {
        :>> id = "b60976d0-7617-4776-9ae3-b915c4e98855";
        :>> title = "touchedReceiptIsContentKeyedPerBinary: the touched receipt records, per test binary, the content its outcome depends on, and keel land runs only the binaries that lack a green observation at the pushed content";
        :>> createdAt = "2026-09-14";
        :>> createdBy = "claudeFable5";
        :>> status = DecisionStatus::accepted;
        :>> context = "D0421 makes keel land run the touched set before the first push, and it is right to: issue416 was a green commit gate and a red CI because nothing ran the integration tests. Measured on this host (touched_breakdown.py over .keel/metrics/touched-*.log, 2026-09-14): one touched run costs 936 s; the same one-line fix (sprint705) ran three times, and the third run (touched-1789357116.log) was build 1.08 s, tests 736 s - cargo already knew nothing had changed, only the test RUN had no memo. The receipt key in receipt.rs hash_path (lines 153-158) is (len, mtime), which is why it needs a two-second RACY window and why the sprint705 test raced the clock. Eighteen test files read the repository's own tree through CARGO_MANIFEST_DIR (control_census_names_friction.rs:10, federation.rs:38, batched_governance_agrees.rs:17 among them), so a .tracking write can legitimately change their outcome and no key that ignores .tracking is sound for them. The adversarial panel of 2026-09-13 (knowledge record KnowledgePerfOptionsPanel20260913) ranked this first of eight options.";
        :>> decision = "NOT A FORK: one key scheme, one skip rule, one control. The invariant, implementation-free: no commit is pushed unless every binary in its touched set was observed green against the same content its outcome depends on; land's obligation is that the observation EXISTS, not that land produced it. The touched receipt is content-keyed: file bytes are hashed, not (len, mtime), so the RACY window is removed. It records two keys per binary: K_code, the content of keel-cli/**, .engine/**, Cargo.toml, Cargo.lock and .githooks/**; and K_tree, the content of every tracked and untracked path outside .keel/. A binary whose test text names CARGO_MANIFEST_DIR is self-reading. keel land skips a binary whose receipt entry is green under an equal K_code and, when self-reading, an equal K_tree; it runs every other binary in the touched set and writes the merged receipt. It prints the skipped set and the run set. The receipt files - .keel/metrics/*-receipt.toml and touched-*.log - join the pre-write protected surfaces (claude_surface.rs PROTECTED_PATHS), so only keel writes them. This reverses one clause of D0421 - runs exactly those before the first push - and leaves D0421 in force: the set is still computed the same way and a red still refuses. It depends on D0371, whose clause - keyed on every input a guard can read - content satisfies more exactly than stat does. NOT a reversal of D0356: the obligation to run the suite before a push stays withdrawn; a receipt here removes a run, it never demands one.";
        :>> rationale = "Cargo memoises compilation by content fingerprint and saved 4-6 minutes on the third run; nothing memoised the 736 s of tests. A whole-tree key alone would not pay: the normal flow is code, touched run, ceremony writes to .tracking, commit, land, and the ceremony changes the tree. The two-tier key makes the ceremony case rerun exactly the self-reading binaries (18 of 71) and the unchanged-tree case rerun none. Detection of self-reading binaries is the text scan touched.rs already performs for module names and is conservative: a false positive reruns, a miss cannot skip a binary that reads code, because code is in K_code. Trusting a local file is an honour system unless the file is protected: a receipt the AI can Write with a tool is not evidence, so the protection is the control (D0047), CI stays the authority (D0420) and runs the full suite regardless, and the trust class equals today's RAN receipts (D0232). git write-tree was considered and not needed: key() already enumerates ls-files plus status -z -uall; hashing bytes of an 11.6 MB corpus is 0.4 s warm (KnowledgePerfSpike20260907).";
        :>> consequences = "receipt.rs hashes content and loses RACY and the settledness test; a per-binary table joins the touched receipt; touched.rs gains the self-reading scan, the skip computation and the printed skipped/run sets; claude_surface.rs PROTECTED_PATHS gains the receipt globs and its unit tests gain the pair; the cliSuite and cliLand facts state the skip rule; D0421's consequences clause is left as history. Residual: a self-reading test that reaches the repository by a path other than CARGO_MANIFEST_DIR is keyed on K_code only; the touched.rs scan names the one env var that all eighteen use today, and a second idiom would be added to the scan, not to a reminder. Measured expectation to verify: repeat land on an unchanged tree runs zero binaries; land after a ceremony write runs the self-reading set only.";
    }
    #SupersedeClause dependency from d0474 to d0421;
    #DependsOn dependency from d0474 to d0371;

    // acceptance event (D0121 review-queue sign-off; D0066/D0106 — human-judged, not fabricated)
    verification d0474Accept : Test { :>> id = "32b71779-64af-4fd6-962e-33b2a1627479"; :>> method = VerificationMethod::confirmation; :>> procedureText = "chat acceptance of the three panel proposals labelled A (D0474), B (D0475), C (D0476) in the panel report of 2026-09-13; their words verbatim: ABC, continue! - their words, verbatim: “ABC, continue!” WARN: read-back - the quoted words do not name d0474 (D0201 B); recorded as given (D0423)."; }
    part d0474AcceptR1 : TestResult { :>> id = "fbc2d1c6-bad2-4f8b-819f-90238c76ae0e"; :>> outcome = VerdictKind::pass; :>> judgedAgainst = "8b731e6"; :>> judgedAt = "2026-09-14"; :>> judgedBy = "wweatherholtz"; :>> createdBy = "claudeFable5"; }
}
