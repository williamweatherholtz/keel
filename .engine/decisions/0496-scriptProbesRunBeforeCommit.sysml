// D0496 (status: the `status` field below is the truth) — The script probes CI runs run before the commit - one runner, scripts/script_probes.py, discovers every `# ci-probe:` script for ci.yml and for the pre-commit hook whenever a staged path matches scripts/**/*.py
// Recorded via `keel record decision` (D0105 RMWX axis; issue054). Acceptance is a separate explicit
// human gate (method=confirmation, D0106): flip status + add the d0496Accept event on sign-off.
package Decision0496 {
    private import EngineElement::*;
    private import EngineWork::*;
    private import EngineVerification::*;
    private import EngineRelationships::*;

    // #ProspectiveChange (D0070) - this Decision governs a process/schema change; the co-committed
    // change rides the process-change guard's hard lock.
    #ProspectiveChange part d0496 : Decision {
        :>> id = "e9d6f586-f9ff-4e54-bddb-1cc1462f4337";
        :>> title = "The script probes CI runs run before the commit - one runner, scripts/script_probes.py, discovers every `# ci-probe:` script for ci.yml and for the pre-commit hook whenever a staged path matches scripts/**/*.py";
        :>> createdAt = "2026-09-16";
        :>> createdBy = "claudeFable5";
        :>> status = DecisionStatus::accepted;
        :>> context = "Two commits reached main red on ci.yml's `script probes` step with every local gate green: eb82b52 and its fix 6a493f4 both failed `scripts/module_home.py --probe` in CI while the D0476 ladder, the pre-commit hook, the VERIFIER and keel land's touched set had all passed. The step's discovery - every scripts/**/*.py whose `# ci-probe: <flag>` line names a flag is run with it and must exit 0 - lived only in a bash heredoc inside .github/workflows/ci.yml (lines 59-87 before this Decision), so no local surface could run the same set. It was the third member of the local-gate-differs-from-CI class: issue453 (the touched set ran only in CI), issue572 (clippy lints only the host's cfg), issue574 (this one). The class's shape is the same each time - a check exists on exactly one of the two surfaces, and the surface it is missing from is the one that runs first. The runner written for this Decision runs the current tree's seven probes in about 4 seconds on this host (`python scripts/script_probes.py`: artefact, check_templates --self-test, module_home, probes/issue400_reproduction, probes/receipt_shape_census, script_probes, textpatch), and its D0388 pair passes over two temp trees before any real tree is read.";
        :>> decision = "The script-probe discovery and run live in ONE executable, scripts/script_probes.py, and both surfaces call it. ci.yml's `script probes` step is `python3 scripts/script_probes.py`, no heredoc. .githooks/pre-commit runs `python scripts/script_probes.py` whenever a staged path matches scripts/**/*.py; a red probe aborts the commit with `SCRIPT PROBES FAILED:` naming each script and its flag; python missing on the host is GATE CANNOT RUN naming the remedy and exits 1 - never a skip (D0098). The runner carries its own `# ci-probe: --probe` line, so it is a member of the set it runs.";
        :>> rationale = "A check that exists on one surface only is not a gate on the other, and the class this Decision closes its third member of is exactly that: the commit is judged twice, and the two judges read different lists. Making the list one file the two surfaces execute is the only shape in which they cannot drift - a second copy of the discovery in the hook would be the same defect waiting for its next edit. The hook runs the set only when a script is staged because that is the only edit that can change the set's verdict; the cost is about 4 seconds on those commits and nothing on the rest (D0054). Python missing must block rather than skip because the probes would then be first run by CI, after the push - the failure mode this Decision exists to remove. This is a process-change: .githooks/pre-commit and ci.yml are enforcement surfaces under D0209 clause 2, so both edits are co-committed with this Decision under the `CR:` prefix and the Decision is held for the human under D0337.";
        :>> consequences = "scripts/script_probes.py is new and is the one runner; ci.yml's step shrinks to one line calling it; .githooks/pre-commit gains a script-probes block after the templates block, gated on `^scripts/.*/.py$` in the staged set. A future `# ci-probe:` script is picked up by both surfaces with no edit to either. Delivered by dcScriptProbesRunBeforeCommit, which resolves issue574. Nothing changes for a commit that stages no script. Resolves obligation664abc60: the verifier's SubagentStop yielded red on this sprint's retro wording (`not tracked` is not a justification the retro-backlog guard reads) and on the runner's missing instrument line, both corrected in the commit that carries this Decision.";
    }

    // acceptance event (D0121 review-queue sign-off; D0066/D0106 — human-judged, not fabricated)
    verification d0496Accept : Test { :>> id = "63370d43-e538-4a6e-8abf-7520ce56c55a"; :>> method = VerificationMethod::confirmation; :>> procedureText = "recorded from chat - their words, verbatim: “Accept all decisions as recommended. Proceed to release and fix downstream” WARN: read-back - the quoted words do not name d0496 (D0201 B); recorded as given (D0423)."; }
    part d0496AcceptR1 : TestResult { :>> id = "bf835fc6-64c8-4ba5-b2f8-774b67e14b86"; :>> outcome = VerdictKind::pass; :>> judgedAgainst = "4d00c1bc"; :>> judgedAt = "2026-09-18"; :>> judgedBy = "wweatherholtz"; :>> createdBy = "claudeFable5"; }
}
