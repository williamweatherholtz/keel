// D0526 (status: the `status` field below is the truth) — downstreamBatchRoutedAsRecommended: the open downstream issues GH#9 to GH#95 are routed as their triage recommends - twenty-six become tracked Issues with resolver tasks, eleven are verified fixed or declined, and five architecture asks each get their own fork
// Recorded via `keel record decision` (D0105 RMWX axis; issue054). Acceptance is a separate explicit
// human gate (method=confirmation, D0106): flip status + add the d0526Accept event on sign-off.
package Decision0526 {
    private import EngineElement::*;
    private import EngineWork::*;
    private import EngineVerification::*;
    private import EngineRelationships::*;

    part d0526 : Decision {
        :>> id = "03533302-81b7-40ea-af6e-81f6fe6f9929";
        :>> title = "downstreamBatchRoutedAsRecommended: the open downstream issues GH#9 to GH#95 are routed as their triage recommends - twenty-six become tracked Issues with resolver tasks, eleven are verified fixed or declined, and five architecture asks each get their own fork";
        :>> createdAt = "2026-09-19";
        :>> createdBy = "claudeFable5";
        :>> status = DecisionStatus::accepted;
        :>> context = "Forty-four open issues on the public repository, every one filed by the owner's GitHub login from downstream projects (obsidian-selfsync, Penumbra, a murder-mystery project, an irrigation design) or by the retired decision channel's bot, were pulled as verbatim untrusted Statements (D0264) across 2026-08-30 to 2026-09-19 and triaged into stories with a recommendation each. The tier says a human accepts before anything becomes work. The owner's standing word for the previous batch (st089: all work, these are essentially from me) named the same filer; today's words (st168: continue, let's make downstream projects whole; st060: ingest github issues and fix) are the directive this batch executes. Each recommendation was checked against source before it was written: every Issue description names the file and line that establishes the defect.";
        :>> decision = "Route as recommended. The tracked Issues, each with its resolver task in NextWork: issue635 (dcAcceptFindsTheExistingEvent, High), issue636 (dcValidateReadsANamedDependency, High), issue637 (dcLandRefusesAnUnknownArgument, High), issue638 (dcAClaimCommitCarriesOnlyTheClaim, Medium), issue639 (dcRecordDecisionNamesEveryMissingFlagAtOnce, Low), issue640 (dcActivateWritesTheCharter, Medium), issue641 (dcPreBashSeesABacktickInsideARecordArgument, High), issue642 (dcHookIntegrityExpandsTheProjectDir, Medium), issue643 (dcBuildStampsAFixedWidthCommit, Low), issue644 (dcParserKeepsEveryMarkerInAnActionDef, High), issue645 (dcMigrateBlocksOnAProjectExtendedEngineFile, High), issue646 (dcDispositionNeedsItsResult, High), issue647 (dcMigrateTracksTheOverlayHook, High), issue648 (dcRecordResultFindsAStandaloneTest, Medium), issue649 (dcLandReadsPorcelainBeforeLanded, High), issue650 (dcProtectedPathsBindToThePath, High), issue651 (dcScaffoldPlaceholderSeesTheStarterActors, Medium), issue652 (dcTraceWalksMarkerEdges, High), issue653 (dcCompoundGuardExemptsASupersededDecision, Medium), issue654 (dcRecordDecisionRefusesACompoundClause, Medium), issue655 (dcReviewRoundTripRefusesAnAgentVerdict, High), issue656 (dcMigrateSeesARemovedEnumMember, Medium), issue657 (dcIntakeShowsANeedStoryWithoutANeed, Medium), issue658 (dcResolverLookupCoversEveryDef, Medium), issue634 (dcInitAppendsToGitignore, Medium). Verified fixed or declined, answered on the issue with the reason: GH#70 (issue451 resolved), GH#76 (premise false since D0224), GH#63 (dcAddTaskLandsInsideItsDef), GH#64 (D0260), GH#65 (doc-sync in this commit), GH#29 (bot boilerplate), GH#35 (moot), GH#36 (issue377 resolved), GH#37 (D0348), GH#38 (D0291), GH#40 (issue272, issue274 resolved). The five architecture asks - GH#78 lenses, GH#82 ceremony chain, GH#67 marker traversal, GH#66 analysis suspicion, GH#31 design inputs - are each a fork Decision recorded beside this one and held for the human. NOT A PROCESS CHANGE: this Decision routes; a resolver that changes a hook, guard or workflow carries its own D0209 Decision when it is delivered.";
        :>> rationale = "WHY ONE DECISION AND NOT TWENTY-SIX ACCEPTANCES: D0264 asks that an untrusted story reach work only through a Decision a human accepts, and guard untrusted-routing sees one Decision among every story's targets; D0292 is the precedent for a batch routed on the owner's word with the receipt on the Decision. WHY THE SEVERITIES: High is given where a control or write path is silently wrong downstream - a landing that pushes on --help, a landing that prints landed over an unstaged file, an Issue closed by an unjudged Test, a migrate that deletes a project's declarations, a hook that cannot see the injection class it exists for, a parser that drops edges - because each is the D0098 class where the tool reports a state that is not so. WHY THE FORKS ARE SEPARATE: each asks the engine to take a position on its own vocabulary or ceremony, which is a direction the human owns, and folding them into a routing Decision would accept them by default. WHAT WAS FOUND WHILE ROUTING: fourteen open issues were never ingested because pull reads one page (issue633, dcGithubPullWalksEveryPage), and every re-ingested duplicate (GH#9 to GH#69 appear twice) is the dedup defect dcGithubIngestDedupsOnTheIssueIdentity already tracks.";
        :>> consequences = "Twenty-seven items enter the frontier; their ranking is by declaration order and is read from keel show whats-next, not from this text. The reporter reads the tracked ids and verdicts where they filed (github-intake step 4). The five forks appear on the decision brief with D0525. REMOVAL PATH (D0163): a superseding Decision; the Issues then need a mooting resolver each.";
    }
    #DerivedFrom dependency from d0526 to st168;
    #DerivedFrom dependency from d0526 to st060;

    // acceptance event (D0121 review-queue sign-off; D0066/D0106 — human-judged, not fabricated)
    verification d0526Accept : Test { :>> id = "dd79940f-67a5-413b-913a-98a84b25bdd4"; :>> method = VerificationMethod::confirmation; :>> procedureText = "AUTO-ACCEPTED under standing consent (D0207). Their standing words, verbatim: 'issues raised are automatically accepted. they can be customizedly changed post-fact.' Not individually reviewed; override by a superseding Decision (D0290) or the human's quoted word in chat (D0289)."; }
    part d0526AcceptR1 : TestResult { :>> id = "f78cd576-c7c5-4089-bc5d-298b73d3b84e"; :>> outcome = VerdictKind::pass; :>> judgedAgainst = "5d2e799f"; :>> judgedAt = "2026-09-19"; :>> judgedBy = "wweatherholtz"; :>> createdBy = "claudeFable5"; }
}
