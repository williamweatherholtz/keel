// D0467 (status: the `status` field below is the truth) — retroFindingIsAnIssueFirst: a retro finding is discharged by an Issue by default; a retro whose only new item is a Decision says why the finding is not a one-off, or the retro-backlog guard warns
// Recorded via `keel record decision` (D0105 RMWX axis; issue054). Acceptance is a separate explicit
// human gate (method=confirmation, D0106): flip status + add the d0467Accept event on sign-off.
package Decision0467 {
    private import EngineElement::*;
    private import EngineWork::*;
    private import EngineVerification::*;
    private import EngineRelationships::*;

    // RESEARCH: Their words, st122, 2026-09-13, on the nineteenth-publish copy-out: 'I didn't care if the name is caps, and I usually want issues coming out of retros, not decisions. Usually retro findings are based on empirical evidence. If they're proposing a non occasion issue, it could be a decision, I suppose'. Story us110 derived from it. The guard as it stands (keel-cli/src/guards.rs retro_backlog_violations, D0131/D0293/issue424) accepts any of issueNNN, dcTaskName, dNNNN or D0NNN as the item a retro names, added by the commit or already in the tree, and prefers none.
    // #ProspectiveChange (D0070) - this Decision governs a process/schema change; the co-committed
    // change rides the process-change guard's hard lock.
    #ProspectiveChange part d0467 : Decision {
        :>> id = "c3bd3864-0876-409a-9d6c-3c62756ede5b";
        :>> title = "retroFindingIsAnIssueFirst: a retro finding is discharged by an Issue by default; a retro whose only new item is a Decision says why the finding is not a one-off, or the retro-backlog guard warns";
        :>> createdAt = "2026-09-13";
        :>> createdBy = "claudeFable5";
        :>> status = DecisionStatus::accepted;
        :>> context = "D0131 made a retro's findings become tracked items in the same commit, or the retro says why not; the guard reads three item forms - an Issue, a task, a Decision - and treats them as equal discharges. The human's note on the retro ask (d0461, which reads the capital form of a Decision's name) says the form of the name was never their question: what they want out of a retro is Issues, because a retro's findings rest on empirical evidence - a run that failed, a refusal, a number - and an Issue is a tracked, closable defect with a resolver. A Decision is the right discharge only where the finding proposes a standing rule rather than a one-off. In the tree as it stands, sprint 694's retro discharged its finding by naming a Decision (d0466) and passed; sprint 693's discharged by an Issue (issue518) and passed the same way. The guard cannot tell the human's preferred case from the exception.";
        :>> decision = "The retro-backlog guard prefers an Issue. When the tracked items a retro names that THIS COMMIT ADDS are Decisions only (dNNNN, either case) and no Issue or task among them, the guard emits a WARNING - not a violation - unless the retro text carries the phrase 'standing rule:' followed by why the finding is not a one-off. A retro that adds an Issue or a task, or that justifies with an existing item under the D0293 phrases, is silent as today. An existing Issue named as already tracking the finding stays a silent discharge. The warning names the sprint file and the Decision(s) and says: a retro finding rests on evidence and is an Issue with a #Resolves edge; a Decision discharges it only where it proposes a rule, and the retro says so. Blocking is unchanged: this is a warning because the honest state of a retro that names a Decision is 'tracked' (D0098), and the preference is theirs to read in the burndown, not a gate to fake past. NOT A FORK: their words name the default and the exception; the alternative - refusing a Decision-only retro - would block a legitimate discharge and is the completeness-gate shape D0098 forbids.";
        :>> rationale = "Their words carry both halves: Issues by default because retro findings are empirical, a Decision where the finding is 'a non occasion issue' - a standing rule. A warning that fires exactly on the Decision-only case and is discharged by one phrase naming the rule makes the exception visible and the default silent, which is the shape the human asked for on the brief itself (D0359: say something when the state changes, nothing when it does not). Reading the phrase rather than judging the finding keeps the guard's claim small: that the retro SAID why, not that it was right - the reader's judgment, as retro_backlog_violations already leaves the coverage question to the reader.";
        :>> consequences = "Held proposed for the human (process-change, D0337). On acceptance: retro_backlog_violations returns warnings as well as violations for the Decision-only case; the D0388 pair in guards.rs - a retro adding only d0NNN with no phrase warns, the same with 'standing rule:' is silent, a retro adding issueNNN is silent; guards.md's retro-backlog row states the preference; the sprint-retro skill's finding step says Issue first, Decision with 'standing rule:'; applied in a sprint chartered by this Decision through the D0465 path. Resolver dcRetroFindingIsAnIssueFirst, derived from us110. d0461 stands as its own clause - the guard must read the capital form to find an existing Decision a retro cites as already tracking a finding, whichever discharge the retro chose - and this Decision does not depend on its answer.";
    }

    // acceptance event (D0121 review-queue sign-off; D0066/D0106 — human-judged, not fabricated)
    verification d0467Accept : Test { :>> id = "bd3de984-1a14-47b4-9149-f1841c2bc3dc"; :>> method = VerificationMethod::confirmation; :>> procedureText = "Said in chat 2026-09-14 over the twenty-eighth publish of the decision brief, which carried fifteen held asks; one instruction covers the fourteen non-forks, d0467 among them. The fork d0466 is not covered - it needs an option letter and stays held. - their words, verbatim: “Accept all proposals. Proceed to design with needs, etc.” WARN: read-back - the quoted words do not name d0467 (D0201 B); recorded as given (D0423)."; }
    part d0467AcceptR1 : TestResult { :>> id = "c169faaa-ba82-40a3-8bb6-ec6491a08de9"; :>> outcome = VerdictKind::pass; :>> judgedAgainst = "d110d0a"; :>> judgedAt = "2026-09-14"; :>> judgedBy = "wweatherholtz"; :>> createdBy = "claudeFable5"; }
}
