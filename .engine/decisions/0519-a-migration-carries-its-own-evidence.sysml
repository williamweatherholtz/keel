// D0519 (status: the `status` field below is the truth) — A project-migration writes the evidence its own gate reads, and the surface it moved
// Recorded via `keel record decision` (D0105 RMWX axis; issue054). Acceptance is a separate explicit
// human gate (method=confirmation, D0106): flip status + add the d0519Accept event on sign-off.
package Decision0519 {
    private import EngineElement::*;
    private import EngineWork::*;
    private import EngineVerification::*;
    private import EngineRelationships::*;

    // #ProspectiveChange (D0070) - this Decision governs a process/schema change; the co-committed
    // change rides the process-change guard's hard lock.
    #ProspectiveChange part d0519 : Decision {
        :>> id = "563d5d8b-28f3-4bff-b496-06bbe3c0c31c";
        :>> title = "A project-migration writes the evidence its own gate reads, and the surface it moved";
        :>> createdAt = "2026-09-18";
        :>> createdBy = "claudeOpus5";
        :>> status = DecisionStatus::accepted;
        :>> context = "`keel migrate` could not complete in any downstream project. A resync rewrites `.engine/` in place, and the items there name the upstream actors who authored them: mm-site's copy alone carries five distinct createdBy values. The ownership guard reads a field edit by a non-owner as a D0108 violation, so the post-migrate gate went red and the run reverted itself, every time, in every project the command exists to serve. No actor could clear it, because no actor owns all five. The guard already has the answer. D0067 and D0108 collide by design for a bulk transform, and the guard resolves that collision on evidence rather than on a flag: cross-owner edits are permitted when a transform under `.engine/tools/migrations/` is co-committed, where a reviewer can read it. But `is_engine_dev_only` excludes every path with a `tools` component from shipping, so the one directory that lifts D0108 was the one directory a migration could not write. The exemption was unreachable from outside the self-build repo. The same shape appeared a second time once ownership cleared. `claude-surface-drift` compares the deployed `.claude/` surface against the engine, and the resync moves `.engine/skills/`; the gate then reported every skill stale. `keel sync-claude` fixes exactly that, but it cannot run until the migration it is blocking has landed.";
        :>> decision = "`keel migrate` writes its own resync record, generated, into `.engine/tools/migrations/<date>-engine-resync-<build>.md`, naming the build moved to and the control totals and file list of the step it accounts for. It also regenerates the `.claude/` surface as part of the run. Both land inside the migration, so the gate judges one coherent tree; `.claude/` joins `.engine/` and `.tracking/` in the cleanliness precondition and in the rollback, so a reverted run is byte-for-byte as before.";
        :>> rationale = "The record is generated rather than shipped, and only when the resync actually wrote something. That is what keeps the exemption honest: it is not a flag a caller sets and not a file that sits in the tree granting a standing pass, it is an account of a boundary that was actually crossed, written into the commit that crossed it — the guard's own stated reason for reading that directory. Shipping the sixteen upstream transforms instead would have put dev-only scripts in every adopting project and granted the exemption permanently. A migrate-only marker the guard trusts would have been the claimable shape the guard explicitly refuses. The surface follows the same principle. A post-condition that only the run can satisfy belongs to the run, not to a chore afterwards; a tree holding one vintage's engine and another's surface is the half-migrated state D0252 forbids.";
        :>> consequences = "This closes issue609: `keel migrate` completes in a downstream project. Each migration leaves a dated record, so a project accumulates a readable ledger of the vintages it has moved through. `.claude/` must now be clean before a migration and is restored with everything else if one reverts, which is a new refusal for a caller who kept uncommitted surface edits. The exemption is reachable outside the self-build repo for the first time, so the ownership guard's suspension now fires on real downstream migrations; it still requires the record to be present in the change, and a no-op resync writes none. Two things a migration still will not fix, both correct: project-owned contracts under `.engine/contracts/` are never overwritten (issue314), and a project's own CLAUDE.md is its own. Both can carry stale command spellings after a rename, and both are the project's to repair.";
    }

    // acceptance event (D0121 review-queue sign-off; D0066/D0106 — human-judged, not fabricated)
    verification d0519Accept : Test { :>> id = "3f65aa8c-2677-4805-9a64-27e9fc9ec84e"; :>> method = VerificationMethod::confirmation; :>> procedureText = "recorded from chat - their words, verbatim: “Accept all decisions as recommended. Proceed to release and fix downstream” WARN: read-back - the quoted words do not name d0519 (D0201 B); recorded as given (D0423)."; }
    part d0519AcceptR1 : TestResult { :>> id = "9ecd8bc8-ed72-40f0-9f81-e16d6397ce1e"; :>> outcome = VerdictKind::pass; :>> judgedAgainst = "4d00c1bc"; :>> judgedAt = "2026-09-18"; :>> judgedBy = "wweatherholtz"; :>> createdBy = "claudeFable5"; }
}
