// D0516 (status: the `status` field below is the truth) — recorderRefusalCannotCiteTheVerifiersNotedWritesLine: a REFUSED line that cites the verifier receipt's noted-writes line as its reason is refused by check_report.py, and the receipt labels that line VERIFIER-NOTED WRITES so it cannot read as the recorder's owed count
// Recorded via `keel record decision` (D0105 RMWX axis; issue054). Acceptance is a separate explicit
// human gate (method=confirmation, D0106): flip status + add the d0516Accept event on sign-off.
package Decision0516 {
    private import EngineElement::*;
    private import EngineWork::*;
    private import EngineVerification::*;
    private import EngineRelationships::*;

    // #ProspectiveChange (D0070) - this Decision governs a process/schema change; the co-committed
    // change rides the process-change guard's hard lock.
    #ProspectiveChange part d0516 : Decision {
        :>> id = "f1fcf7b6-d388-4549-87d3-36eb9a475162";
        :>> title = "recorderRefusalCannotCiteTheVerifiersNotedWritesLine: a REFUSED line that cites the verifier receipt's noted-writes line as its reason is refused by check_report.py, and the receipt labels that line VERIFIER-NOTED WRITES so it cannot read as the recorder's owed count";
        :>> createdAt = "2026-09-18";
        :>> createdBy = "claudeFable5";
        :>> status = DecisionStatus::accepted;
        :>> context = "Sprint 735's second RECORDER (D0425: haiku, no Write or Edit tool) was dispatched --owed 1 to write dcSuiteIsAMember's DoD result from the verifier receipt the first recorder had written seven records from. It wrote nothing and reported REFUSED: task dcSuiteIsAMember: receipt line 19 states OWED WRITES: NONE; no writes owed per verifier. Line 19 is the test-verify receipt's closing line - the writes the VERIFIER noticed while checking, addressed to the recorder (test-verify skill, issue471) - and says nothing about what the recorder owes; the dispatch's count is the only owed count (D0492). check_report.py --owed 1 passed the report, because a REFUSED line accounts for a record whatever its reason: the seven refusals read the WROTE lines and count the REFUSED lines, and none reads what a REFUSED line says. The misread was visible only to the primary reading the report; a second message naming the line's meaning produced the write (dcSuiteIsAMemberDoDR1 at 7394a28). issue590 (Medium) is the finding. The class is a receipt line whose label reads as the recorder's own instruction: OWED WRITES, read by an agent told it owes writes, is that agent's count.";
        :>> decision = "One clause, one control: check_report.py (.engine/skills/delegated-ceremony/references, and its generated .claude copy) gains an eighth refusal - a REFUSED: line whose text cites the receipt's noted-writes label, OWED WRITES or VERIFIER-NOTED WRITES, is refused naming the line and what that receipt line counts: writes the verifier noticed for the recorder, never what the recorder owes. A dispatched record is a WROTE line, or a REFUSED line naming what the write API lacks; a receipt line is never the reason. The receipt line itself is relabelled VERIFIER-NOTED WRITES: NONE | <a write the verifier noticed is owed beyond the dispatch, for the recorder> wherever its shape is stated (the test-verify skill, the delegated-ceremony process step, the verifier agent type), and the recorder brief says in one sentence that the dispatch's COUNT is the only owed count and that receipt line is the verifier's, never the recorder's - both are the doc-sync of this control, not decisions of their own, and ride the same commit. Fixtures under references/fixtures: positive-sprint735-refused-citing-owed-writes.txt is the second recorder's first report as returned (one REFUSED line citing line 19) and is REFUSED under --owed 1 naming the citation; negative-sprint735-one-owed.txt is its rewritten report (one WROTE line) and PASSES under --owed 1. The D0388 pair is those two PAIRS rows, run through check_report.py --probe <FIXTURE> from the sprint's pair file (D0500). Refusals 1 to 7 are unchanged.";
        :>> rationale = "The seven refusals of D0473 and D0492 each hold the report's shape - what is typed, what is written, how many are accounted for - and a REFUSED line is the accounting's escape hatch: it exists so a marker or edge the API lacks is reported, never typed (D0425). Sprint 735 used the hatch for a reason no refusal reads, and the count-based control passed it, so the reason a REFUSED line gives is now read too. The narrowest honest rule is not 'a REFUSED line must be justified' - the checker cannot judge a reason - but 'a REFUSED line cannot cite the one receipt line whose label reads as the recorder's own instruction', because that citation is a misread by construction: the line is the verifier's, addressed to the recorder, and the dispatch alone says what is owed (D0492). Relabelling the line closes the same class from the receipt's side; a label that names whose writes they are cannot be read as a count of one's own. Fixture negative-sprint647-receipt-driven.txt names OWED WRITES on a prose line and puts the API gap on its REFUSED line, which is the shape a legitimate report takes, and it still passes. Alternatives not taken: NOT A FORK - a hook that reads the recorder's report against the dispatch text would need the dispatch as a fact the tree does not hold, and a checker that judges the substance of a REFUSED reason is testimony, not a receipt (D0232).";
        :>> consequences = "Eight refusals in check_report.py; two fixtures and two PAIRS rows added; the test-verify skill's receipt shape, the delegated-ceremony process steps, the verifier agent type, the recorder brief, CLAUDE.md's subagent paragraph and the skill's refusal list say the eighth refusal and the new label in the same commit (doc-sync). A verifier that still writes OWED WRITES is not refused - the checker reads the recorder's report, not the receipt, and the old label in a citation is refused either way - so the relabel is enforced only by the skill text and the fixtures; that residual is stated here. Sprint 744 (dcRecorderRefusalCannotCiteTheVerifiersNoWritesLine) delivers this; issue590's resolution is computed from its #Resolves edge. HELD proposed under D0337 for the human's word: the change rides this record's marker (D0209 cl.2), and the human may reject the relabel, the eighth refusal, or both.";
    }
    #DependsOn dependency from d0516 to d0492;
    #DependsOn dependency from d0516 to d0473;
    #DependsOn dependency from d0516 to d0438;

    // acceptance event (D0121 review-queue sign-off; D0066/D0106 — human-judged, not fabricated)
    verification d0516Accept : Test { :>> id = "cbd1a8dc-fa15-4570-80a8-d59f39554fdc"; :>> method = VerificationMethod::confirmation; :>> procedureText = "recorded from chat - their words, verbatim: “Accept all decisions as recommended. Proceed to release and fix downstream” WARN: read-back - the quoted words do not name d0516 (D0201 B); recorded as given (D0423)."; }
    part d0516AcceptR1 : TestResult { :>> id = "97dbc131-fbdb-4bb1-8bec-b9fcc8bff4e3"; :>> outcome = VerdictKind::pass; :>> judgedAgainst = "4d00c1bc"; :>> judgedAt = "2026-09-18"; :>> judgedBy = "wweatherholtz"; :>> createdBy = "claudeFable5"; }

    // grounded (D0098 rootedness): this Decision serves the Need that a pass is never AI testimony alone -
    // st065, the human's words behind the D0425 ceremony line (verifier, recorder, ladder, rendered receipt)
    #DerivedFrom dependency from d0516 to nVerificationByAuthorityAndMethod;
}
