// D0509 (status: the `status` field below is the truth) — keelServeSitsAboveEveryMemberAndBelowTheBinary: the console is member keel-serve, reading every member and read by keel-cli alone; reports and attestation ride with it; ci_runs joins keel-github, which gains keel-model; the orient computation descends to keel-model; the guard that audits the HTTP surface reads the console where it lives
// Recorded via `keel record decision` (D0105 RMWX axis; issue054). Acceptance is a separate explicit
// human gate (method=confirmation, D0106): flip status + add the d0509Accept event on sign-off.
package Decision0509 {
    private import EngineElement::*;
    private import EngineWork::*;
    private import EngineVerification::*;
    private import EngineRelationships::*;

    // #ProspectiveChange (D0070) - this Decision governs a process/schema change; the co-committed
    // change rides the process-change guard's hard lock.
    #ProspectiveChange part d0509 : Decision {
        :>> id = "2347c494-ad67-4a06-9c8a-222d5cd52a9c";
        :>> title = "keelServeSitsAboveEveryMemberAndBelowTheBinary: the console is member keel-serve, reading every member and read by keel-cli alone; reports and attestation ride with it; ci_runs joins keel-github, which gains keel-model; the orient computation descends to keel-model; the guard that audits the HTTP surface reads the console where it lives";
        :>> createdAt = "2026-09-17";
        :>> createdBy = "claudeFable5";
        :>> status = DecisionStatus::accepted;
        :>> context = "Sprint 738 (dcServeAndGithubAreMembers) is the eighth D0479 extraction: serve, deck, launcher and console_registry leave keel-cli/src for members/keel-serve, ci_runs leaves it for members/keel-github, verification leaves it for members/keel-view, and the embedded console page moves with the module that includes it. D0479 named the console as the extraction before the binary is thinned; its DoD's probe is the build fact - an edit to serve.rs recompiles keel-serve and keel-cli and nothing else. Four things the DoD did not say had to be settled for the probe to hold. First, reports.rs and attestation.rs stayed in keel-cli when their neighbours left, and each reads across the whole stack - reports reads the guards' readiness, the view layer, attestation and the receipts; attestation reads the write API's reverify, the actor and the workspace - so no member below the console can hold them without depending upward, and a keel-cli that keeps them is not thin. Second, ci_runs reads the corpus (collect_sysml), so keel-github, which had no member dependency at all, must depend on keel-model to hold it; keel-model does not depend on keel-github, so the edge is acyclic, and keel-guards and keel-view already sit above both. Third, the orient computation (OrientReport, compute_orient_state, orient_root, whats_next_root) sat in keel-cli's lib.rs and serve.rs reads whats_next_root - a member cannot read the binary crate, so the four descend to keel_model::readiness beside the corpus and cursor they read. Fourth, the hardening guard's api_surface lens and its route test read keel-cli/src/serve.rs and keel-cli/assets/console.html by path; the guard file is under the keystone lock, and so are the obligation-review process and its skill registry, whose purpose sentences cite deck.rs by path - three locked files whose only change is a path string following the source it names.";
        :>> decision = "Member keel-serve holds serve, deck, launcher, console_registry, reports and attestation and the console page they embed; it depends on every member (keel-perf, keel-git, keel-json, keel-actor, keel-schema, keel-model, keel-write, keel-view, keel-guards, keel-process, keel-issues) and is depended on by keel-cli alone - the root manifest lists it last before the binary and no member names it. ci_runs is keel-github's, and keel-github depends on keel-json, keel-git and keel-model; it stays below keel-view and keel-guards. verification is keel-view's beside the views it reads. The orient computation is keel_model::readiness; keel-cli re-exports the four names at its root and every moved module at its old path, so no caller in main.rs or the tests moved and `keel --help` is byte-identical. The hardening guard reads members/keel-serve/src/serve.rs and members/keel-serve/assets/console.html: a guard that audits a source file reads that file where the manifests put it, and moving the file moves the string in the same commit, under this marked Decision.";
        :>> rationale = "D0479's rule is that a fact lives where its readers are, and the console's readers are the person at the browser and the binary that starts it - nothing in the engine reads the console, so the console is the top of the member graph and the binary is the only thing above it. reports and attestation belong there by the same rule: their readers are the console's routes and the render verbs, and their reads span the stack, so any lower home would make a member depend upward and any stay in keel-cli would leave the binary holding two thousand lines of computation. keel-github gaining keel-model is the smaller of two moves: ci_runs is a CI-run receipt gate whose one non-trivial read is the corpus, and the alternative - a corpus-free ci_runs that re-reads files by hand - is the two-vocabularies class. The orient descent is forced by the same probe that forces everything else: a member cannot name the binary crate, so what a member reads must live below it. The marker: members/keel-guards/src/hardening.rs, .engine/processes/obligation-review.sysml and .engine/skills/obligation-review/registry.sysml are locked paths (is_process_def, GUARD_SOURCE_DIRS), and though each change is a path string following its source, D0209 clause 2 asks for the marked Decision beside every such edit and the human judges it; a path that lies about where the audited file is would make the api_surface lens read nothing and say so (issue183), which is the guard fail-closed as designed, not a reason to leave the string stale.";
        :>> consequences = "members/keel-serve holds six modules and assets/console.html under the member lint preamble, with a Cargo.toml naming eleven members, serde, serde_json, toml, tokio, axum, async-stream and tokio-stream, and dev-deps keel-fs and tower; keel-cli's manifest drops tokio, axum, async-stream, tokio-stream and the tower dev-dep and gains keel-serve. members/keel-github/src/ci_runs.rs and members/keel-view/src/verification.rs exist; members/keel-model/src/readiness.rs holds the orient computation. cargo tree -p keel-serve names no keel-cli; cargo tree -p keel-github names no keel-view, keel-guards, keel-process, keel-suite or keel-serve; touching members/keel-serve/src/serve.rs recompiles keel-serve and keel-cli with every other member Fresh. keel --help is byte-identical to the pre-move render and keel version's guard line is unchanged at 75. The transform is scripts/extract_serve.py (idempotent, dry-run default). The deliverable manifest's two task rows and the code registry's two claudeFable5 elements name the new paths; nine other registry values that earlier extractions left stale are issue593's. The next extraction is the last: dcKeelCliIsThinDispatch, which leaves keel-cli as main.rs and the dispatch it holds. NOT A FORK: the alternatives (reports and attestation kept in keel-cli; ci_runs re-reading files without the corpus; whats_next_root duplicated into the console; the guard's path strings left pointing at files that no longer exist) each break a standing fact named above or the DoD's own probe, and nothing here is left for a later choice.";
    }
    #DependsOn dependency from d0509 to d0479;

    // acceptance event (D0121 review-queue sign-off; D0066/D0106 — human-judged, not fabricated)
    verification d0509Accept : Test { :>> id = "2d26f95b-8126-42ea-96d5-90636b7e134e"; :>> method = VerificationMethod::confirmation; :>> procedureText = "recorded from chat - their words, verbatim: “Accept all decisions as recommended. Proceed to release and fix downstream” WARN: read-back - the quoted words do not name d0509 (D0201 B); recorded as given (D0423)."; }
    part d0509AcceptR1 : TestResult { :>> id = "9e9b1cd2-adcc-4939-86d2-78e07fecc4d6"; :>> outcome = VerdictKind::pass; :>> judgedAgainst = "4d00c1bc"; :>> judgedAt = "2026-09-18"; :>> judgedBy = "wweatherholtz"; :>> createdBy = "claudeFable5"; }
}
