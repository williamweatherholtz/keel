// Intake for 2026-09-14 — their words, my translation, the triage verdict (D0166/D0216).
// Written by `keel record statement` / `keel record story` (D0236): a Statement's text is
// VERBATIM, so it is escaped for the literal and otherwise untouched.
package ProjectIntake20260914 {
    private import EngineElement::*;
    private import EngineIntake::*;
    private import EngineRelationships::*;

    part st123 : Statement {
        :>> id = "2e9c7c89-208a-4ea0-a4e5-27b4f1d2ef66";
        :>> title = "GH#74 [proposal] keel claim commits the claim file by pathspec (or land refuses a claim commit with ride-alongs) - a whole-index commit carried another session's staged deletion";
        :>> createdAt = "2026-09-14"; :>> createdBy = "githubRecorder";
        :>> text = "**Proposal.** Make a claim commit structurally unable to carry a ride-along: `keel claim` should commit exactly `.tracking/claims/<actor>.sysml` by pathspec (`git commit -- .tracking/claims/<actor>.sysml`), or `keel land` should refuse to push a claim commit whose tree touches anything outside `.tracking/claims/`.\n\n**What happened downstream.** Penumbra, two sessions sharing one checkout. Landing claim `claimai001` (commit `558ce25`) committed the deletion of `tools/spoke-augment-use-cases.py` alongside the claim file, because the deletion was already in the git index - staged by the co-resident session whose in-flight work replaced that spoke - and `git commit` takes the whole index. `main` then deleted the Python spoke while `README.md`, `CONTRIBUTORS.md` and `spokes/README.md` at HEAD still referenced it, ahead of the replacement landing. Recorded as Penumbra issue088.\n\n**Measured since (git log --stat over the claim-titled commits, 2026-09-14).** Five commits titled as claims: two touched only the claim file (`b4f9530`, `4ae15eb`); two carried tracking edits their messages name deliberately (`4cc0c02`, `5f21906`); one carried the unintended ride-along (`558ce25`). Manual staging discipline held four times in five, which is what a habit does; the control is the pathspec.\n\n**Where.** At v0.4.1, `keel claim` (`keel-cli/src/claim.rs`, dispatched at `keel-cli/src/main.rs` line 4814) writes the claim file and makes no commit; `keel land` (`keel-cli/src/sync.rs` line 205, `cmd_land`) gates the tree and pushes the branch. Neither knows which commit is the claim, so the whole-index commit is left to the operator.\n\n**Suggested shape.** Either (a) `keel claim` ends by committing the claim file by pathspec with a fixed message, so the operator never runs `git commit` for a claim; or (b) `cmd_land` inspects the commits it is about to push and refuses one whose message is the claim form and whose tree touches paths outside `.tracking/claims/`. (a) removes the hazard; (b) detects it. Either makes the record verifiable after the fact without a human remembering to stage nothing else.\n\nFiled from Penumbra, 2026-09-14 (proposeClaimPathspecCommit, resolving issue088).\n";
        :>> saidBy = "williamweatherholtz"; :>> saidAt = "2026-09-14"; :>> channel = StatementChannel::github;
        :>> sourceUrl = "https://github.com/williamweatherholtz/sysmlv2-ai-toolkit/issues/74";
        :>> sourceTrust = SourceTrust::untrusted;
    }

    part st124 : Statement {
        :>> id = "811ce417-801a-4fc7-be1c-2e419b103fe0";
        :>> title = "GH#73 [control defect] keel land --help does not print usage - it runs the landing and pushes the branch";
        :>> createdAt = "2026-09-14"; :>> createdBy = "githubRecorder";
        :>> text = "**Observed.** `keel land --help` did not print usage. It ran the landing and pushed the current branch:\n\n```\n$ keel land --help\nkeel land: pushing vintage-0.4.1-and-review-corpus -> origin (attempt 1/3)\nkeel land: landed.\n```\n\nkeel 0.4.1 (binary and pin agree). The branch had no upstream before; it now exists on the remote.\n\n**Where.** `keel-cli/src/main.rs` line 4774 dispatches `Some(''land'') => keel_cli::sync::cmd_land(&repo_arg(rest), 3)`, and `cmd_land` (`keel-cli/src/sync.rs` line 205) takes only the repository path: an unknown flag in `rest` is neither refused nor read. Other subcommands refuse the same probe by name - `keel validate --help` says ''`--help` looks like a flag, not a path'', `keel sync-claude --help` says ''unknown flag `--help`'', `keel record decision --help` prints the required arguments.\n\n**Why it matters.** `land` is the one keel command whose effect leaves the machine. A documentation probe that becomes a push is a control defect in the sense of D0047: the operator's intent was to read, the tool acted. Downstream (Penumbra) has a standing rule that the AI never pushes; the probe broke it without any write intent.\n\n**Suggested shape.** Give `land` the same argument discipline `validate` and `sync-claude` have: any argument beginning with `-` refuses with usage and exit 2, before `gate_passes` and before the push loop. A regression test in `keel-cli/tests/land_gate.rs`: `land --help` against a repository with a bare remote leaves the remote untouched and exits non-zero.\n\nFiled from Penumbra, 2026-09-14.\n";
        :>> saidBy = "williamweatherholtz"; :>> saidAt = "2026-09-14"; :>> channel = StatementChannel::github;
        :>> sourceUrl = "https://github.com/williamweatherholtz/sysmlv2-ai-toolkit/issues/73";
        :>> sourceTrust = SourceTrust::untrusted;
    }

    part st125 : Statement {
        :>> id = "afde8da4-0bf6-413c-ac8b-35875e7fd042";
        :>> title = "GH#72 [bug] keel-parser refuses a NAMED dependency (dependency <name> from A to B;) - the OMG grammar allows Identification? before from";
        :>> createdAt = "2026-09-14"; :>> createdBy = "githubRecorder";
        :>> text = "**Observed.** `keel validate` refuses a SysML v2 file at the first *named* dependency:\n\n```\nFAIL:  ./.tracking/Shadow.sysml — ./.tracking/Shadow.sysml:798468:16: expected From, got Ident(''derive_50511'')\n```\n\nThe statement it refused:\n\n```\n    dependency derive_50511 from LOGDC2_PRD_Rqmts_105 to LOGDC2_SYSRQ_418;\n```\n\n**Grammar.** The OMG pilot implementation's textual grammar allows an optional identification before `from` (`org.omg.sysml.xtext/src/org/omg/sysml/xtext/SysML.xtext`, rule `Dependency`, lines 53-59):\n\n```\n'dependency' ( Identification? 'from' )?\n    client += [SysML::Element|QualifiedName] ( ',' client += ... )* 'to'\n    supplier += [SysML::Element|QualifiedName] ( ',' supplier += ... )*\n    RelationshipBody\n```\n\nSo `dependency <name> from A to B;` is vanilla SysML v2.\n\n**Where keel diverges.** `keel-parser/src/parser.rs`, `parse_bare_dependency` (v0.4.1, lines 738-741): after consuming `dependency` it does `p.expect(&TokenKind::From, filename)?` with no room for an identification, so any named dependency fails as above. The marker form (`#Marker dependency ...`, line 724-725) has the same shape.\n\n**Reproduction.** Penumbra (a downstream keel project that emits a Jama project as vanilla SysML v2) emitted its full shadow - 38,723 elements, 5,409 dependencies, 115 MB - and ran `keel validate` over it as an independent conformance parser:\n\n1. as emitted: refused at the first dependency (above);\n2. the same file with the names removed by `sed -E 's/^(    dependency) [A-Za-z0-9_]+ from //1 from /'`: `1 tracking file(s) validated clean.`\n\nThe two runs isolate the divergence to the identification alone; everything else in the emitted text parses.\n\n**Why it matters downstream.** The name carries the source relationship id, which the emitter needs for round-tripping edges (`dependency derive_50511` is Jama relationship 50511). Dropping the name would lose the id; keeping it means keel cannot be used as the independent conformance check until the grammar's optional identification is read.\n\n**Suggested shape.** In both dependency parsers, after `dependency`, accept an optional `Ident` (and `<shortName>`) before `From`, and carry it on `DependencyAnnotation` (a `name: Option<String>`) so the census can count named and unnamed alike.\n\nFiled from Penumbra, 2026-09-14 (sprint 199, retroIndependentParserForConformance).\n";
        :>> saidBy = "williamweatherholtz"; :>> saidAt = "2026-09-14"; :>> channel = StatementChannel::github;
        :>> sourceUrl = "https://github.com/williamweatherholtz/sysmlv2-ai-toolkit/issues/72";
        :>> sourceTrust = SourceTrust::untrusted;
    }

    part st126 : Statement {
        :>> id = "23296527-7207-40df-b035-9639f93c8c49";
        :>> title = "split keel into granular workspace members; keel-issues, not an external tracker";
        :>> createdAt = "2026-09-14"; :>> createdBy = "claudeFable5";
        :>> text = "totally agree on splitting the crate into workspace members.  give us lots of granularity - no need to couple code just to keep it in one place.  making it broad and uncoupled makes it modular and easy to rebuild.  i like the ''test binaries'' improvements and the Guards one also.  I think your identification of ''where the boundary sits'' is a bit naive.  What we're talking about here is the value of granularly splitting apart keel into disparate functions, which is a great idea and i expect will largely help the issues with recompiling, etc.  But the second implicit idea here is - use an issue tracker to enforce process and track/expose state.  I think that's fine, but I do think Keel does it better in many ways - we can read plain sysml processes, interpret them, add guards (really jsut CI/CD), etc.  This has become a more and more obvious need as this project goes forward - how to hook into custom processes that have absolute discipline?  You're proposing an issue tracker, which is fine.  I say let's just make keel-issues or something, which can manage the subset of processes related to items/issues (and not e.g. decisions about keel itself).  Big modularity pass incoming, I think.  Decouple the code wherever it's helpful, and let's divide and conquer to increase speed, reliability, and anchor points into our processes where possible.";
        :>> saidBy = "wweatherholtz"; :>> saidAt = "2026-09-14"; :>> channel = StatementChannel::chat;
    }

    part us111 : UserStory {
        :>> id = "7e8cd8e9-15b1-415c-b854-ccf43627507c";
        :>> title = "keel split into granular workspace members";
        :>> createdAt = "2026-09-14"; :>> createdBy = "claudeFable5";
        :>> asA = "keel maintainer who rebuilds the binary after every edit";
        :>> iWant = "keel split into many small workspace members, each one function of the engine with its dependencies declared in its own manifest, so that an edit rebuilds the member it touches and the members above it and nothing beside or below";
        :>> soThat = "keel is 'modular and easy to rebuild' and 'lots of granularity' ends 'the issues with recompiling' (their words); the rebuild that follows a one-line edit stops relinking a 44k-line crate";
        :>> implication = ImplicationKind::architecture;
        :>> triageNote = "D0479 (accepted) already names the layering and sprints 714-718 extracted eleven members under it; this story is the elicited origin of that program and of the remaining extraction items (dcViewIsAMember, dcSuiteIsAMember, dcGuardsAreMembersPerFamily, dcTouchedSetDescendsTheWorkspace). Architecture worked ahead of the Story under D0064; the Needs below are the contract the remaining items satisfy";
    }
    #DerivedFrom dependency from us111 to st126;

    part us112 : UserStory {
        :>> id = "3ee4d299-b4bf-4e4b-a9c0-cd49b2bbf774";
        :>> title = "keel-issues manages the item/issue process subset";
        :>> createdAt = "2026-09-14"; :>> createdBy = "claudeFable5";
        :>> asA = "downstream project lead who tracks items and issues and does not govern keel";
        :>> iWant = "a member of keel - 'keel-issues or something' - that manages the subset of processes about items and issues (record, resolve, ready, blocked, done, what is next, what is open), and NOT the processes about keel itself (Decisions about the engine, Change Requests, the CR guards)";
        :>> soThat = "the reasons keel was proposed over an external tracker hold for the item subset on its own: the process is enforced and the state exposed, and the member is small enough that a project which only tracks items carries none of the engine-governance surface";
        :>> implication = ImplicationKind::architecture;
        :>> triageNote = "The answer to 'why a self-authored tracker over an external one' in the same statement was: keel reads plain SysML processes and interprets them, enforcement via guards is CI/CD, state is computed - an external tracker gives none of those. The boundary named here (items/issues in; decisions about keel itself out) is theirs verbatim; where exactly Decisions about a PROJECT's own work fall is the read-back question";
    }
    #DerivedFrom dependency from us112 to st126;

    part us113 : UserStory {
        :>> id = "74805d01-f911-44a6-b9a7-b6281ad6db27";
        :>> title = "a custom process hooked with absolute discipline";
        :>> createdAt = "2026-09-14"; :>> createdBy = "claudeFable5";
        :>> asA = "downstream project lead who authors a process in plain SysML";
        :>> iWant = "to hook a custom process - plain SysML a project authors for its own work - into the engine so that it runs with 'absolute discipline': a step whose gate is red cannot be advanced past, and the refusal is the same in the editor hook, at the commit gate and in CI";
        :>> soThat = "'This has become a more and more obvious need' (their words); the outcome it serves was not stated - the read-back asks for the last concrete process that could not be hooked";
        :>> implication = ImplicationKind::need;
        :>> triageNote = "Their question was 'how to hook into custom processes that have absolute discipline?' - a need, not yet a use case, because no concrete custom process was named. beAsk (pain, not features): what was the last process you wanted enforced and could not hook. Elicitation is open; the story records what was said";
    }
    #DerivedFrom dependency from us113 to st126;

    part us114 : UserStory {
        :>> id = "0d13dc42-73df-4c17-b122-6eb14ded750c";
        :>> title = "divide and conquer: decouple wherever helpful, guards and test binaries first";
        :>> createdAt = "2026-09-14"; :>> createdBy = "claudeFable5";
        :>> asA = "keel maintainer";
        :>> iWant = "the code decoupled 'wherever it's helpful' and the work divided so that speed, reliability and 'anchor points into our processes' all increase; the test-binary and guard items ('the Guards one') worked first";
        :>> soThat = "divide and conquer: several small members are built, tested and reasoned about apart, and each is a place a process can anchor a control";
        :>> implication = ImplicationKind::priority;
        :>> triageNote = "Priority implication: the ordering they asked for is already the frontier's (dcGuardsAreMembersPerFamily, dcTouchedSetDescendsTheWorkspace stand ahead of the rest under D0481/D0482/D0483). 'Anchor points into our processes' is read as: a member boundary is where a guard, a hook or a sensor can bind - carried into the Needs as nMemberIsAnAnchor, my reading, marked so";
    }
    #DerivedFrom dependency from us114 to st126;
}
