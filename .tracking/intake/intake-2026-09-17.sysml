// Intake for 2026-09-17 — their words, my translation, the triage verdict (D0166/D0216).
// Written by `keel record statement` / `keel record story` (D0236): a Statement's text is
// VERBATIM, so it is escaped for the literal and otherwise untouched.
package ProjectIntake20260917 {
    private import EngineElement::*;
    private import EngineIntake::*;
    private import EngineRelationships::*;

    part st158 : Statement {
        :>> id = "8bdaa102-f5ff-4584-9147-1bb6086cf965";
        :>> title = "GH#83 keel init overwrites an existing .gitignore instead of appending, silently dropping the project's own ignore rules";
        :>> createdAt = "2026-09-17"; :>> createdBy = "githubRecorder";
        :>> text = "`keel init` on a project with existing content **overwrites** `.gitignore` instead of appending to it, so the project's own ignore rules are silently deleted.\n\n## What happened\n\nAdopting keel into an existing Rust repository (`plotwright`), keel 0.4.1 build `b171cd7`, Windows:\n\n```\nkeel init plotwright --profile strict\n```\n\nBefore:\n\n```\n/target\n/build\n__pycache__/\n```\n\nAfter:\n\n```\n# keel machine-local state — never commit these.\n#\n# .keel/actor is THIS MACHINE's identity binding (D0129). ...\n.keel/\n\n# `keel serve` per-clone preferences.\n.keel-serve.json\n\n# Generated views/reports — regenerable from the model, so they are outputs, not facts.\n*.keel.html\n```\n\nAll three original rules are gone. `git status` then showed `target/` and `build/` as untracked, and the next `git add -A` would have committed a Rust build directory — in this case ~1 GB — plus `__pycache__`. It was caught by reading `git diff .gitignore` before committing, which is not a control.\n\n## Why this is more than a cosmetic overwrite\n\n`keel init` already knows the project is not empty: it **refuses** without a declared profile precisely because there is existing content —\n\n```\nerror: plotwright has existing content — an adoption profile must be DECLARED, never inferred (D0174).\n```\n\nSo the one code path that has established ''this project has a history'' then discards a file that is part of that history. Every other file keel writes at init is new (`.engine/`, `.claude/`, `.githooks/`, `CLAUDE.md`, `keelw`); `.gitignore` is the only one likely to already exist and to be load-bearing, and it is the one that gets clobbered.\n\nThe failure is also silent in the direction that matters. Nothing is reported, the tree still gates green, and the damage shows up later as either a huge accidental commit or a confusing `git status`.\n\n## Expected\n\nAppend keel's block to an existing `.gitignore`, idempotently — leaving the project's rules in place and skipping lines already present. Failing that, refuse and print the block for the adopter to paste, which is consistent with how `init` treats the profile.\n\n## Environment\n\n- keel 0.4.1, build `b171cd7`, `keel-windows-x86_64.exe`\n- Target: an existing git repository with 20 commits, a `.gitignore`, `Cargo.toml`, and no prior keel state\n- Command: `keel init plotwright --profile strict`\n";
        :>> saidBy = "williamweatherholtz"; :>> saidAt = "2026-09-16"; :>> channel = StatementChannel::github;
        :>> sourceUrl = "https://github.com/williamweatherholtz/keel/issues/83";
        :>> sourceTrust = SourceTrust::untrusted;
    }

    part st159 : Statement {
        :>> id = "9bac374f-1539-475b-9db3-5d97d65cd28b";
        :>> title = "GH#82 [proposal] let a project declare its ceremony chain - advance matches six baked gate names, so a project cannot substitute planning for standup";
        :>> createdAt = "2026-09-17"; :>> createdBy = "githubRecorder";
        :>> text = "## The ask\n\nLet a project declare its own ceremony chain, instead of `advance` matching gate names against a fixed set of six.\n\n## What is fixed today, measured rather than assumed\n\n`keel new sprint` scaffolds six gates, and `keel advance` recognises them by name. Renaming one is enough to prove the list is baked rather than read:\n\n```\n$ keel advance sprint1\n  defined: Refine -> Standup -> Implement -> Review -> CloseOut -> Retro\n  passed:  Refine, Standup, Implement\n  current step: Review\n\n# rename plotwrightBuilderStandupGate -> plotwrightBuilderPlanningGate in the sprint file\n$ keel advance sprint1\n  defined: Refine -> Implement -> Review -> CloseOut -> Retro\n  passed:  Refine, Implement\n  current step: Review\n```\n\nStandup drops out cleanly, and `Planning` is **not** picked up. So omitting a ceremony is already supported by omission, but *substituting* one is not: an authored `PlanningGate` is invisible to `advance`, which means a project cannot put a step in its own chain even when the engine already declares the process for it.\n\n## Why this project wants it\n\n`.engine/processes/agile-workflow.sysml` already declares `action planning : Process` at line 90, next to `refinement` (:42) and `standup` (:120). So the process exists, has a skill (`sprint-planning`), and cannot be a gate.\n\nMeanwhile standup earns nothing here. This project is one author working alone in evening sittings; D0049's own framing is that the sprint gates run autonomously with a single human touchpoint per sitting. A three-question blocker check against yourself, recorded as a judgment, is ceremony with no counterparty. The project's actual need is the step D0258 describes — assigning priority against the computed signals — and its author asked for exactly that swap: drop standup, add planning where priority is assigned.\n\n## Two shapes that would work\n\n1. **Declared chain.** `.engine/contracts/activation.toml` (or a sibling) carries an ordered list of ceremony names, and `advance` reads it. The shipped default stays the six, so nothing changes for a project that declares nothing.\n2. **Known-name set widened.** Add `Planning` to the recognised names. Cheaper, and it covers this case, but the next project wanting a different chain is back here.\n\nThe first is the one that generalises; the second unblocks a real project this week.\n\n## What this project will do in the meantime\n\nAuthor sprints with no `StandupGate` (which works today) and fold the priority assessment into the refine gate's procedure text, since that is where `refineAssessPriority` already lives. Recorded as a Decision on our side. Sprint 1 keeps its standup gate and its recorded pass, because that result was true when it was recorded.\n\n## Environment\n\n- `keel 0.4.1`, build commit `b171cd7` (release asset `keel-windows-x86_64.exe`)\n- Windows 11, git-bash, a `keel init --profile strict` project with one sprint\n\n## Provenance\n\nRaised from an agent session after the project's author asked why `refine` and `closeOut` were in his chain at all, and asked for standup to be replaced by planning.\n";
        :>> saidBy = "williamweatherholtz"; :>> saidAt = "2026-09-16"; :>> channel = StatementChannel::github;
        :>> sourceUrl = "https://github.com/williamweatherholtz/keel/issues/82";
        :>> sourceTrust = SourceTrust::untrusted;
    }
}
