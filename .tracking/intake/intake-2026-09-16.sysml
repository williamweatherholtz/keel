// Intake for 2026-09-16 — their words, my translation, the triage verdict (D0166/D0216).
// Written by `keel record statement` / `keel record story` (D0236): a Statement's text is
// VERBATIM, so it is escaped for the literal and otherwise untouched.
package ProjectIntake20260916 {
    private import EngineElement::*;
    private import EngineIntake::*;
    private import EngineRelationships::*;

    part st128 : Statement {
        :>> id = "23bc106f-ff6f-4772-ada8-442045d0b183";
        :>> title = "GH#81 Build stamp uses `git rev-parse --short`, so the same commit yields 444333d on one machine and 444333d5 on another; claude-surface-drift then fails between two builds of the same commit";
        :>> createdAt = "2026-09-16"; :>> createdBy = "githubRecorder";
        :>> text = "**Observed** (obsidian-selfsync, 2026-09-16): one machine built keel at commit 444333d and stamped `.claude/.keel-surface` / `settings.json` with `444333d` (7 chars). A second machine built the SAME commit; its `git rev-parse --short HEAD` returned `444333d5` (8 chars, because `core.abbrev=auto` scales with object count), so `keel version` reported build `444333d5` and `guard claude-surface-drift` FAILED with:\n\n```\nERROR surface stamped by build 444333d; this binary is build 444333d5 - a different generator wrote what is on disk\n```\n\nSame source, same commit, two ''generators'' as far as the guard can tell. Workaround used: `git config core.abbrev 7` in the toolkit checkout, `touch keel-cli/build.rs`, rebuild.\n\n**Where:** `keel-cli/build.rs:32` derives `KEEL_BUILD_COMMIT` from `git rev-parse --short HEAD`.\n\n**Suggested fix:** use a fixed width (`git rev-parse --short=7 HEAD`, or store the full 40-char hash and compare by prefix), so the stamp is a property of the commit rather than of the builder's git configuration. A unit test that the stamp length is constant would pin it.\n\nFiled by the agent working obsidian-selfsync, on the owner's behalf.";
        :>> saidBy = "williamweatherholtz"; :>> saidAt = "2026-09-16"; :>> channel = StatementChannel::github;
        :>> sourceUrl = "https://github.com/williamweatherholtz/keel/issues/81";
        :>> sourceTrust = SourceTrust::untrusted;
    }

    part st129 : Statement {
        :>> id = "4a5c0ddf-310c-47e6-86fb-8a0d577469b8";
        :>> title = "GH#80 [control defect] guard hook-config-integrity reports a working hook script as missing - it does not expand $CLAUDE_PROJECT_DIR (issue093)";
        :>> createdAt = "2026-09-16"; :>> createdBy = "githubRecorder";
        :>> text = "## The wrong verdict\n\n```\n$ keel guard hook-config-integrity\n  WARN  .claude/settings.local.json: PreToolUse hook references `$CLAUDE_PROJECT_DIR/scripts/guard-keel-prose.py`, which does not exist — that hook FAILS every time it fires (issue093)\n[guard:hook-config-integrity] PASS — 8 scanned, 1 warning(s), 0 violation(s)\n```\n\nThe file exists and the hook fires correctly.\n\n```\n$ ls -la scripts/\n-rwxr-xr-x 1 ... 2892 Sep 15 12:42 guard-keel-prose.py\n-rw-r--r-- 1 ... 1320 Sep 15 12:43 test_guard_keel_prose.py\n```\n\nThe hook config, verbatim, in `.claude/settings.local.json`:\n\n```json\n{ ''type'': ''command'', ''command'': ''python /''$CLAUDE_PROJECT_DIR/scripts/guard-keel-prose.py/'''' }\n```\n\nProof it fires — it blocked a command of mine in the same session, printing the script's own deny text:\n\n```\nPreToolUse:Bash hook error: [python ''$CLAUDE_PROJECT_DIR/scripts/guard-keel-prose.py'']:\nBLOCKED by scripts/guard-keel-prose.py (MM26 issue001): this is a keel WRITE command\ncontaining a backtick.\n```\n\nSo the guard's existence check is not expanding `$CLAUDE_PROJECT_DIR` before resolving the path. `$CLAUDE_PROJECT_DIR` is the documented way for a hook to reference a project file, and keel's own generated `settings.json` uses `${CLAUDE_PROJECT_DIR:-.}` in its hook commands — which may be why the braced-with-default form passes and the bare form does not.\n\n## Why it matters beyond the noise\n\nissue093's intent is sound: a hook pointing at a missing script fails silently every time it fires, and that is worth catching. But a false ''does not exist'' on a working hook inverts the signal. The reasonable response to this warning is to delete or rewrite a hook that is in fact correct — and in this case the hook is the only control standing between a shell and the tracked record (see #79). A control whose warning argues for removing another control is worse than silence.\n\nIt also fires on a file the guard cannot be sure about in general: `settings.local.json` is machine-local by convention, so a warning about it will show up on one contributor's machine and not another's, with no way to tell a real miss from an unexpanded variable.\n\n## Ask\n\nExpand the documented variables before the existence check — at minimum `$CLAUDE_PROJECT_DIR` and `${CLAUDE_PROJECT_DIR}` / `${CLAUDE_PROJECT_DIR:-...}` — and where a path still cannot be resolved (a variable keel does not know), say *that* rather than asserting the file does not exist. ''references a path keel could not resolve'' is honest; ''which does not exist'' is a claim the guard did not check.\n\n## Environment\n\n- `keel 0.4.1`, build commit `b171cd7` (release asset `keel-windows-x86_64.exe`)\n- Windows 11, git-bash, Claude Code harness, `keel init --profile strict` project\n- `keel sync-claude --check` reports no drift, so the keel-owned surface is intact; the finding is purely about the local hook file\n\n## Provenance\n\nFound from an agent session immediately after adding the hook that #79 asks keel to make unnecessary.\n";
        :>> saidBy = "williamweatherholtz"; :>> saidAt = "2026-09-15"; :>> channel = StatementChannel::github;
        :>> sourceUrl = "https://github.com/williamweatherholtz/keel/issues/80";
        :>> sourceTrust = SourceTrust::untrusted;
    }

    part st130 : Statement {
        :>> id = "efce25b9-da1c-442d-9de9-e3248c04d71e";
        :>> title = "GH#79 [control gap] hook pre-bash does not block backticks in a keel write - fourth recorded occurrence of prose being command-substituted into the record (D0224/issue315)";
        :>> createdAt = "2026-09-16"; :>> createdBy = "githubRecorder";
        :>> text = "## The class, and the fact that keel already knows it recurs\n\n`keel record issue` refuses with this text:\n\n```\nerror: --title --description --severity --resolver are all required.\n  PREFER --description-from FILE for anything long: prose passed as a shell argument\n  has had its backticks EXECUTED into the record three times now (D0224/issue315).\n```\n\n''three times now''. This report is the fourth, and the mitigation in place for it is a sentence inside an error message on `record issue` — the one verb that already has the file channel. Nothing warns on `record story`, which is where it happened to me, and nothing blocks it anywhere.\n\n## What it did\n\nDuring `project-onboarding` on a fresh project, two `keel record story` calls carried backticks inside prose arguments:\n\n- `--triage-note ''Strikes the /`migration/` recommendation. Corrects us008…''`\n- `--i-want ''to know what /`indicator/` would actually do here before deciding on it''`\n\nBash executed both spans, printed `migration: command not found` and `indicator: command not found` on stderr among eight successful `recorded usNNN` lines, and substituted empty strings. keel recorded:\n\n- `us013.triageNote = ''Strikes the recommendation. Corrects us008…''`\n- `us020.iWant = ''to know what would actually do here before deciding on it''`\n\nGrammatical English, load-bearing word deleted, attributed to an AI actor as if authored that way. **`keel validate .` reported clean. `keel guard` reported ALL PASS.** No computed check can see it, because a shorter string is a valid string. I found it by reading the file back by eye, which is not a control.\n\n## The guard that exists for the sibling class\n\nThe harness-level `pre-bash` hook *does* block the adjacent hazard, and blocked me on it in the same session:\n\n```\n[keel] heredoc <<PYEOF carries a backslash (`K = r''C:/Users/.../keel.exe''`) - this harness\ncollapses backslash pairs before bash runs, so source written this way is silently rewritten\n(D0309/issue372, recurred 8+ times). Write the file with the Write tool and run it by path;\na heredoc is for prose without backslashes.\n```\n\nThat is the right shape of control: fail before the write, name the decision record, say what to do instead. The backtick case is the same family — shell text transformation silently rewriting what gets recorded — with a worse outcome, because the heredoc case corrupts *source* while this one corrupts *the tracked record itself*.\n\nVerified on 2026-09-15, keel 0.4.1 build `b171cd7`:\n\n```\n$ echo '{''tool_name'':''Bash'',''tool_input'':{''command'':''keel record story --title X --triage-note /''strikes the `migration` recommendation/''''}}' /\n    | keel hook pre-bash internal\nexit=0\n```\n\n## Ask\n\nExtend `keel hook pre-bash` to refuse a Bash command that contains a backtick **and** invokes a keel write verb (`record`, `accept`, `reject`, `judge-set`, `enroll`, `override`, `apply-review`), with a message in the style of the D0309 refusal: name the substitution, name the decision record (D0224/issue315), and say to pass the prose through a file channel or to build the argument list without a shell.\n\nTwo notes on scope, from building the equivalent locally:\n\n- **Backticks only is the right first cut.** `$(...)` and `$VAR` are the same hazard, but keel invocations legitimately carry shell variables (`$K`, `$SP`, `$CLAUDE_PROJECT_DIR`), so denying those denies every call. A narrow guard that fires is worth more than a broad one that gets disabled.\n- **The refusal should probably name the file channel per verb**, since it is not uniform: on 0.4.1 `record statement` has `--from`, `record issue` has `--description-from`, `accept`/`reject` have `--note-from`, and `record story` and `record decision` have none (see #76). Telling a caller to ''use the file channel'' on `record story` currently sends them at a flag that does not exist.\n\n## What I did locally in the meantime\n\n`scripts/guard-keel-prose.py` wired as a `PreToolUse` Bash hook in `.claude/settings.local.json` — deny on (backtick AND keel write verb), seven-case regression test, no `sync-claude --check` drift. It blocked its own test command on first use. Recorded in that project as `issue001` resolved by `d0002`. Happy to hand over the script if it is useful as a starting point, though the real home is `hook pre-bash` where it protects every project rather than one.\n\n## Environment\n\n- `keel 0.4.1`, build commit `b171cd7` (release asset `keel-windows-x86_64.exe`)\n- Windows 11, git-bash, Claude Code harness, fresh `keel init --profile strict` project\n\n## Provenance\n\nFound and reported from an agent session during `project-onboarding`. The two corrupted records were repaired by hand before the control existed; their current text is correct.\n";
        :>> saidBy = "williamweatherholtz"; :>> saidAt = "2026-09-15"; :>> channel = StatementChannel::github;
        :>> sourceUrl = "https://github.com/williamweatherholtz/keel/issues/79";
        :>> sourceTrust = SourceTrust::untrusted;
    }

    part st131 : Statement {
        :>> id = "31eb5f4d-e198-4cc0-a00e-ed6177245eef";
        :>> title = "GH#78 [proposal] critique lenses are requirement-quality only - a non-software project cannot gate critique on its own domain questions";
        :>> createdAt = "2026-09-16"; :>> createdBy = "githubRecorder";
        :>> text = "## The situation\n\nA fresh project whose deliverable is not software cannot gate critique on questions that mean anything in its domain.\n\nThe lens vocabulary is the requirement-quality canon and it is the only one available:\n\n`.engine/schema/core/element.sysml:32`\n\n```\nenum def CritiqueLens { completeness; correctness; ambiguity; testability; feasibility; consistency; necessity; }  // requirement-quality canon\n```\n\n`.engine/contracts/critique-policy.toml` invites a project to override the required set, and then constrains it to that enum:\n\n> Lenses MUST be `CritiqueLens` variants (the requirement-quality canon, schema/core element.sysml) … An unknown lens name is a fail-loud error (`keel show critique-coverage` / `guard critique`).\n>\n> These lenses are GENERIC deficit-classes, not industry-specific — they apply whatever the deliverable domain is. Different PROJECTS may merit a different required SET … EDIT this file.\n\nThe second paragraph is true for engineering deliverables and false outside them. The project in question is a murder mystery party: roughly ten characters, three acts, ninety authored story beats, where the elements that must survive critique are a plot, a finale and a set of beats. ''Is this plot point testable'' is not a question about a plot point. The questions that matter are whether the solution is reachable from the clues actually distributed, whether a critic can name the culprit too early, whether a beat changes anyone's belief or is filler, and whether any character has nothing to do in an act. None of them force-fit onto the seven canon lenses, and `critique-policy.toml` cannot name them because the enum is closed and `schema/core` is frozen (invariant 5).\n\nSame story for `adversarial-panel-review`, whose roster is fixed in the process text (`.engine/processes/adversarial-panel-review.sysml:20`): ''2 pessimists — premise and operations; 2 optimists — steelman/anti-dilution and value/ROI; 3 pedants — factual accuracy, internal consistency, mechanism failure modes; 1 reduction advocate; 1 systems engineer deriving implementation-free kernel invariants''. The machinery around it is domain-neutral and good — independent concurrent contexts, ACCEPT conditional on a named flip set, round-2 cross-rebuttal, the honesty rule — but the personas are engineering and business personas.\n\n## The engine already knows the answer, and hides it\n\n`.engine/schema/propriety/propriety.sysml:4`\n\n> WHY A NEW PACKAGE AND NOT NEW CritiqueLens MEMBERS: schema/core is frozen (invariant 5), and the five propriety questions do not map onto the requirement-quality canon without force-fitting — overfit is not necessity, circumvention is not correctness. The intake rule generalises: a kind the vocabulary cannot express is a CHANGE to the vocabulary, never a forced fit. A non-core package (the schema/safety precedent) adds the vocabulary without touching the frozen surface.\n\nThat is exactly the guidance a domain project needs, and it is stated as a comment inside a package about control propriety. Nothing on the onboarding path points at it. `project-onboarding` step 3 tells the AI to research the domain's practice and, where a discipline is uncovered, ''map the practice to an existing process, or define a new one'' — but it says nothing about the vocabulary, which is where the force-fit actually happens. Without the propriety comment I would have had to choose between abusing `testability` for a plot beat and inventing a lens name that `guard critique` fails loud on.\n\n## Ask\n\nPick either or both:\n\n1. **Document the path.** `project-onboarding` step 3 (or the critique-policy header) should state the rule the propriety package discovered: a lens the canon cannot express is a new non-core package, never a forced fit. Two sentences on the onboarding path would have been enough.\n2. **Let the policy declare a lens package.** `critique-policy.toml` currently reads ''MUST be `CritiqueLens` variants''. If it could name a project package supplying additional lens variants, a domain project could gate critique on its own questions without touching `schema/core`, and `guard critique` would still fail loud on a name nothing declares.\n\nNot asking for members to be added to the frozen enum — the frozen surface is the point.\n\n## Environment\n\n- `keel 0.4.1`, build commit `b171cd7` (release asset `keel-windows-x86_64.exe`)\n- Windows 11, fresh `keel init --profile strict` project, non-software deliverable\n\n## Provenance\n\nRaised from a `project-onboarding` run in an agent session, after the project author asked whether the shipped critique lenses would give real literary plot assessment rather than technical review. They do not.\n";
        :>> saidBy = "williamweatherholtz"; :>> saidAt = "2026-09-15"; :>> channel = StatementChannel::github;
        :>> sourceUrl = "https://github.com/williamweatherholtz/keel/issues/78";
        :>> sourceTrust = SourceTrust::untrusted;
    }

    part st132 : Statement {
        :>> id = "879cbb46-1f5c-424a-81ab-741bdfc9533a";
        :>> title = "GH#77 [proposal] nothing writes charteredBy - the only path to a chartered activation manifest is hand-editing .engine/contracts";
        :>> createdAt = "2026-09-16"; :>> createdBy = "githubRecorder";
        :>> text = "## What happened\n\n`project-onboarding` step 5 requires the activation manifest to name the Decision that chartered it:\n\n`.engine/skills/project-onboarding/SKILL.md`:\n\n> Write `.engine/contracts/activation.toml` to match, with `charteredBy = ''dNNNN''` under `[processes]`.\n> An activation file without a charter is a set of switches nobody can account for.\n\n`keel activate` / `keel deactivate` write the manifest, and correctly seed it from the effective state on first use:\n\n```\n$ keel activate agile-workflow\nNo manifest existed (everything was active), so one was written with the current effective\nstate before applying the change — behaviour is otherwise unchanged.\nactivated `agile-workflow`. Active: actor-enrollment, agile-workflow, deploy, ...\n```\n\nBut neither command takes the chartering Decision, and no other command writes it. The resulting manifest has `[processes] active = [...]` and no `charteredBy`. `keel onboard` continues to report `NOT CHARTERED` until the key is added, and the only way to add it is to hand-edit a file under `.engine/contracts/` — which the generated project `CLAUDE.md` tells the author not to do (''`.engine/` is the tool — don't modify it'') and which the write-API discipline exists to avoid.\n\nI hand-edited it. `keel onboard` then read back `CHARTERED by d0001 (33 process(es) declared)` and `guard` stayed ALL PASS, so the key is honoured — it just has no writer.\n\n## Expected\n\nA write path, e.g.\n\n- `keel activate <process> --charter dNNNN` / `keel deactivate <process> --charter dNNNN`, or\n- a dedicated `keel charter dNNNN` that stamps the manifest.\n\n## Secondary observation, same area\n\n`keel onboard` reported `NOT CHARTERED` while the charter Decision existed in the tree in `proposed` state. That is arguably correct (an unaccepted Decision charters nothing), but the message reads as ''nobody has recorded WHY these processes and not others'' when in fact someone had, and it was awaiting the human's acceptance. A distinct wording for ''chartered by a Decision that is still proposed'' would tell the author to go accept it rather than to re-run onboarding.\n\n## Environment\n\n- `keel 0.4.1`, build commit `b171cd7` (release asset `keel-windows-x86_64.exe`)\n- Windows 11, git-bash, fresh `keel init --profile strict` project\n\n## Provenance\n\nFound while executing `project-onboarding` step 5 and step 6 in an agent session.\n";
        :>> saidBy = "williamweatherholtz"; :>> saidAt = "2026-09-15"; :>> channel = StatementChannel::github;
        :>> sourceUrl = "https://github.com/williamweatherholtz/keel/issues/77";
        :>> sourceTrust = SourceTrust::untrusted;
    }

    part st133 : Statement {
        :>> id = "4d009f17-b5ff-434f-b62e-abe736f8acb1";
        :>> title = "GH#76 [bug] record story has no file channel, and the five record verbs use four different conventions for one";
        :>> createdAt = "2026-09-16"; :>> createdBy = "githubRecorder";
        :>> text = "## What happened\n\nThe shipped `project-onboarding` skill instructs the caller to pass Decision prose through a file, citing D0224:\n\n`.engine/skills/project-onboarding/SKILL.md`, step 5 (Charter):\n\n> `keel record decision --from FILE` (prose goes through a file — D0224): the chosen set, the elicited facts behind it, and **what was deliberately not adopted and why**.\n\nNo such flag exists on `record decision`. Neither `--from` nor a per-field `--context-from` is accepted:\n\n```\n$ keel record decision --slug t --title t --context-from /dev/null --decision t --rationale t --consequences t\nerror: --slug --title --context --decision --rationale --consequences are all required (a substantive why — D0103)\n```\n\nThe only path is inline strings. Compare `record statement` (`--text | --from FILE`), `record story` (`--i-want-from`, `--so-that-from`, `--triage-note-from`) and `accept`/`reject` (`--note-from`), all of which do offer the file channel.\n\n## Why it matters\n\nThe D0224 hazard is real and I hit it in this session. Passing four long prose fields inline through a shell mangled the content: backticks inside the prose were command-substituted away, so two recorded items silently lost words (`` `migration` `` and `` `indicator` `` vanished from a `triageNote` and an `iWant`, leaving grammatical but wrong sentences). The file channel exists on the sibling commands precisely to prevent that class of corruption, and the skill already tells callers to use it.\n\n## Expected\n\nEither\n\n1. `record decision` grows the file channel its own skill documents — `--context-from`, `--decision-from`, `--rationale-from`, `--consequences-from`, or a single `--from FILE` carrying the structured fields; or\n2. the skill is corrected to describe the interface that actually exists.\n\nOption 1 looks right given that every comparable write command has the file channel and that the prose fields here are the longest in the system.\n\n## Environment\n\n- `keel 0.4.1`, build commit `b171cd7` (release asset `keel-windows-x86_64.exe`)\n- Windows 11, git-bash, fresh `keel init --profile strict` project\n\n## Provenance\n\nFound while executing `project-onboarding` step 5 in an agent session.\n";
        :>> saidBy = "williamweatherholtz"; :>> saidAt = "2026-09-15"; :>> channel = StatementChannel::github;
        :>> sourceUrl = "https://github.com/williamweatherholtz/keel/issues/76";
        :>> sourceTrust = SourceTrust::untrusted;
    }

    part st134 : Statement {
        :>> id = "1c428252-aa59-44ee-9fef-8688790c75ac";
        :>> title = "GH#75 [bug] keel record decision reveals --date only after the six prose flags are satisfied";
        :>> createdAt = "2026-09-16"; :>> createdBy = "githubRecorder";
        :>> text = "## What happened\n\n`keel record decision` reports its required flags in two stages. The first error names six required flags but omits `--date`, so you satisfy all six, run again, and get a seventh requirement you were never told about.\n\n```\n$ keel record decision\nerror: --slug --title --context --decision --rationale --consequences are all required (a substantive why — D0103)\n\n$ keel record decision --slug processSetCharter --title ''...'' --context ''...'' /\n    --decision ''...'' --rationale ''...'' --consequences ''...'' --by claudeOpus5 --at 2026-09-15\nerror: --date YYYY-MM-DD required (the attestation time is its own irreducible fact)\n```\n\n## Why it matters more here than for a short flag\n\nThe six fields in the first message are the long prose ones. A caller assembling them has just built a large command (in my case roughly 6 KB of context/decision/rationale/consequences, assembled in a script to survive shell quoting). Discovering a seventh required flag after that assembly means re-running the whole construction. A short flag discovered late is a nuisance; a late requirement behind four prose fields is a re-do.\n\n## Expected\n\nOne refusal that names every missing required flag, `--date` included.\n\n## Environment\n\n- `keel 0.4.1`, build commit `b171cd7` (release asset `keel-windows-x86_64.exe`)\n- Windows 11, git-bash, fresh `keel init --profile strict` project\n\n## Provenance\n\nFound during a `project-onboarding` run in an agent session; the command that hit it was recording the project's charter Decision.\n";
        :>> saidBy = "williamweatherholtz"; :>> saidAt = "2026-09-15"; :>> channel = StatementChannel::github;
        :>> sourceUrl = "https://github.com/williamweatherholtz/keel/issues/75";
        :>> sourceTrust = SourceTrust::untrusted;
    }

    part st135 : Statement {
        :>> id = "013b54ab-3bd7-41c4-8225-980f5a05ab09";
        :>> title = "GH#74 [proposal] keel claim commits the claim file by pathspec (or land refuses a claim commit with ride-alongs) - a whole-index commit carried another session's staged deletion";
        :>> createdAt = "2026-09-16"; :>> createdBy = "githubRecorder";
        :>> text = "**Proposal.** Make a claim commit structurally unable to carry a ride-along: `keel claim` should commit exactly `.tracking/claims/<actor>.sysml` by pathspec (`git commit -- .tracking/claims/<actor>.sysml`), or `keel land` should refuse to push a claim commit whose tree touches anything outside `.tracking/claims/`.\n\n**What happened downstream.** Penumbra, two sessions sharing one checkout. Landing claim `claimai001` (commit `558ce25`) committed the deletion of `tools/spoke-augment-use-cases.py` alongside the claim file, because the deletion was already in the git index - staged by the co-resident session whose in-flight work replaced that spoke - and `git commit` takes the whole index. `main` then deleted the Python spoke while `README.md`, `CONTRIBUTORS.md` and `spokes/README.md` at HEAD still referenced it, ahead of the replacement landing. Recorded as Penumbra issue088.\n\n**Measured since (git log --stat over the claim-titled commits, 2026-09-14).** Five commits titled as claims: two touched only the claim file (`b4f9530`, `4ae15eb`); two carried tracking edits their messages name deliberately (`4cc0c02`, `5f21906`); one carried the unintended ride-along (`558ce25`). Manual staging discipline held four times in five, which is what a habit does; the control is the pathspec.\n\n**Where.** At v0.4.1, `keel claim` (`keel-cli/src/claim.rs`, dispatched at `keel-cli/src/main.rs` line 4814) writes the claim file and makes no commit; `keel land` (`keel-cli/src/sync.rs` line 205, `cmd_land`) gates the tree and pushes the branch. Neither knows which commit is the claim, so the whole-index commit is left to the operator.\n\n**Suggested shape.** Either (a) `keel claim` ends by committing the claim file by pathspec with a fixed message, so the operator never runs `git commit` for a claim; or (b) `cmd_land` inspects the commits it is about to push and refuses one whose message is the claim form and whose tree touches paths outside `.tracking/claims/`. (a) removes the hazard; (b) detects it. Either makes the record verifiable after the fact without a human remembering to stage nothing else.\n\nFiled from Penumbra, 2026-09-14 (proposeClaimPathspecCommit, resolving issue088).\n";
        :>> saidBy = "williamweatherholtz"; :>> saidAt = "2026-09-14"; :>> channel = StatementChannel::github;
        :>> sourceUrl = "https://github.com/williamweatherholtz/keel/issues/74";
        :>> sourceTrust = SourceTrust::untrusted;
    }

    part st136 : Statement {
        :>> id = "dc61be03-df30-4516-8d2d-396ceb387736";
        :>> title = "GH#73 [control defect] keel land --help does not print usage - it runs the landing and pushes the branch";
        :>> createdAt = "2026-09-16"; :>> createdBy = "githubRecorder";
        :>> text = "**Observed.** `keel land --help` did not print usage. It ran the landing and pushed the current branch:\n\n```\n$ keel land --help\nkeel land: pushing vintage-0.4.1-and-review-corpus -> origin (attempt 1/3)\nkeel land: landed.\n```\n\nkeel 0.4.1 (binary and pin agree). The branch had no upstream before; it now exists on the remote.\n\n**Where.** `keel-cli/src/main.rs` line 4774 dispatches `Some(''land'') => keel_cli::sync::cmd_land(&repo_arg(rest), 3)`, and `cmd_land` (`keel-cli/src/sync.rs` line 205) takes only the repository path: an unknown flag in `rest` is neither refused nor read. Other subcommands refuse the same probe by name - `keel validate --help` says ''`--help` looks like a flag, not a path'', `keel sync-claude --help` says ''unknown flag `--help`'', `keel record decision --help` prints the required arguments.\n\n**Why it matters.** `land` is the one keel command whose effect leaves the machine. A documentation probe that becomes a push is a control defect in the sense of D0047: the operator's intent was to read, the tool acted. Downstream (Penumbra) has a standing rule that the AI never pushes; the probe broke it without any write intent.\n\n**Suggested shape.** Give `land` the same argument discipline `validate` and `sync-claude` have: any argument beginning with `-` refuses with usage and exit 2, before `gate_passes` and before the push loop. A regression test in `keel-cli/tests/land_gate.rs`: `land --help` against a repository with a bare remote leaves the remote untouched and exits non-zero.\n\nFiled from Penumbra, 2026-09-14.\n";
        :>> saidBy = "williamweatherholtz"; :>> saidAt = "2026-09-14"; :>> channel = StatementChannel::github;
        :>> sourceUrl = "https://github.com/williamweatherholtz/keel/issues/73";
        :>> sourceTrust = SourceTrust::untrusted;
    }

    part st137 : Statement {
        :>> id = "cde3bffa-b673-4260-890b-9105be87b940";
        :>> title = "GH#72 [bug] keel-parser refuses a NAMED dependency (dependency <name> from A to B;) - the OMG grammar allows Identification? before from";
        :>> createdAt = "2026-09-16"; :>> createdBy = "githubRecorder";
        :>> text = "**Observed.** `keel validate` refuses a SysML v2 file at the first *named* dependency:\n\n```\nFAIL:  ./.tracking/Shadow.sysml — ./.tracking/Shadow.sysml:798468:16: expected From, got Ident(''derive_50511'')\n```\n\nThe statement it refused:\n\n```\n    dependency derive_50511 from LOGDC2_PRD_Rqmts_105 to LOGDC2_SYSRQ_418;\n```\n\n**Grammar.** The OMG pilot implementation's textual grammar allows an optional identification before `from` (`org.omg.sysml.xtext/src/org/omg/sysml/xtext/SysML.xtext`, rule `Dependency`, lines 53-59):\n\n```\n'dependency' ( Identification? 'from' )?\n    client += [SysML::Element|QualifiedName] ( ',' client += ... )* 'to'\n    supplier += [SysML::Element|QualifiedName] ( ',' supplier += ... )*\n    RelationshipBody\n```\n\nSo `dependency <name> from A to B;` is vanilla SysML v2.\n\n**Where keel diverges.** `keel-parser/src/parser.rs`, `parse_bare_dependency` (v0.4.1, lines 738-741): after consuming `dependency` it does `p.expect(&TokenKind::From, filename)?` with no room for an identification, so any named dependency fails as above. The marker form (`#Marker dependency ...`, line 724-725) has the same shape.\n\n**Reproduction.** Penumbra (a downstream keel project that emits a Jama project as vanilla SysML v2) emitted its full shadow - 38,723 elements, 5,409 dependencies, 115 MB - and ran `keel validate` over it as an independent conformance parser:\n\n1. as emitted: refused at the first dependency (above);\n2. the same file with the names removed by `sed -E 's/^(    dependency) [A-Za-z0-9_]+ from //1 from /'`: `1 tracking file(s) validated clean.`\n\nThe two runs isolate the divergence to the identification alone; everything else in the emitted text parses.\n\n**Why it matters downstream.** The name carries the source relationship id, which the emitter needs for round-tripping edges (`dependency derive_50511` is Jama relationship 50511). Dropping the name would lose the id; keeping it means keel cannot be used as the independent conformance check until the grammar's optional identification is read.\n\n**Suggested shape.** In both dependency parsers, after `dependency`, accept an optional `Ident` (and `<shortName>`) before `From`, and carry it on `DependencyAnnotation` (a `name: Option<String>`) so the census can count named and unnamed alike.\n\nFiled from Penumbra, 2026-09-14 (sprint 199, retroIndependentParserForConformance).\n";
        :>> saidBy = "williamweatherholtz"; :>> saidAt = "2026-09-14"; :>> channel = StatementChannel::github;
        :>> sourceUrl = "https://github.com/williamweatherholtz/keel/issues/72";
        :>> sourceTrust = SourceTrust::untrusted;
    }

    part st138 : Statement {
        :>> id = "50b9d82d-ab50-4bb3-be7d-b00357f7079a";
        :>> title = "GH#71 keel accept appends a verification named <id>Accept, colliding with a hand-authored one of the same name";
        :>> createdAt = "2026-09-16"; :>> createdBy = "githubRecorder";
        :>> text = "**keel 0.3.1.** A project Decision file authored by hand in the shape the docs show (`#ProspectiveChange part d0054 : Decision {...}` plus a `verification d0054Accept : Test { method = confirmation; procedureText = ''...'' }` describing the planned human attestation) collides with `keel accept d0054`: the command appends its own\n\n```\nverification d0054Accept : Test { ... method = VerificationMethod::confirmation; procedureText = ''<the --note>''; }\npart d0054AcceptR1 : TestResult { ... }\n```\n\nso `keel guard duplicate-identity` then FAILs (`duplicate declared name d0054Accept in package ProjectDecision0054`) and the commit is blocked right after the human accepted. Seen 2026-09-12 on obsidian-selfsync for d0054/d0055/d0056 (the same will happen to any file that already carries a `<id>Accept` verification).\n\n**Ask:** either (a) `keel accept` reuses an existing `<id>Accept` verification (append only the TestResult), or (b) it names its record distinctly (`<id>AcceptEvent`), or (c) `keel guard` / `keel validate` warns BEFORE acceptance that a hand-authored `<id>Accept` will collide. (a) seems most natural — the hand-authored procedureText is exactly the attestation the result records.\n\n**Workaround used:** delete the hand-authored placeholder after acceptance and keep keel's record.";
        :>> saidBy = "williamweatherholtz"; :>> saidAt = "2026-09-12"; :>> channel = StatementChannel::github;
        :>> sourceUrl = "https://github.com/williamweatherholtz/keel/issues/71";
        :>> sourceTrust = SourceTrust::untrusted;
    }

    part st139 : Statement {
        :>> id = "11ade94c-c12f-4912-b8d5-489165661755";
        :>> title = "GH#70 [bug] add-task rejects --method analyze (the schema's member) and accepts 'analysis', writing an enum value keel validate rejects";
        :>> createdAt = "2026-09-16"; :>> createdBy = "githubRecorder";
        :>> text = "**Observed (keel 0.3.1).** `keel add-task --method analyze` is refused: `error: invalid method 'analyze'`. `keel add-task --method analysis` is accepted and writes `:>> method = VerificationMethod::analysis;` — which `keel validate` then flags as a semantic diagnostic: `hint: valid members: analyze, confirmation, critique, demo, inspect, test`. So the CLI's method vocabulary and the schema's `VerificationMethod` enum disagree on the one member; the write path accepts the invalid spelling and rejects the valid one.\n\n**Expected.** `add-task` validates `--method` against the schema enum it writes (`analyze`), or maps the CLAUDE.md prose form `analysis` to it. As it stands the sanctioned write path produces a record the validator rejects, and the only fix is a hand edit of the `.sysml`.\n\n---\nFiled from obsidian-selfsync (keel 0.3.1, 2026-09-09).\n";
        :>> saidBy = "williamweatherholtz"; :>> saidAt = "2026-09-09"; :>> channel = StatementChannel::github;
        :>> sourceUrl = "https://github.com/williamweatherholtz/keel/issues/70";
        :>> sourceTrust = SourceTrust::untrusted;
    }

    part st140 : Statement {
        :>> id = "0c6430c5-65ab-4200-812d-caad5eac5639";
        :>> title = "GH#69 append-result cannot address a standalone verification - the write API misses the shape the RED-first rule produces";
        :>> createdAt = "2026-09-16"; :>> createdBy = "githubRecorder";
        :>> text = "`keel append-result` cannot address a standalone `verification … : Test`. Given one, it answers `error: task not found`. It only resolves a `--task` that is an `action` inside an `action def` with a sibling `<task>DoD` verification.\n\n## Why this matters more than it looks\n\nThe TDD discipline the engine asks for — author the test RED first, before implementation — produces exactly the shape the API cannot reach: a standalone verification with no action beside it. In one downstream project that is every RED test file (`verification-wave5.sysml`, `verification-reviewhistory.sysml`, `verification-reviewcorpus.sysml`). So the moment a RED test goes green, its passing result has to be hand-appended into the `.sysml` — the one write the write API exists to make unnecessary, and the one place where a hand-written `TestResult` skips the API's UUID minting and append-only guarantees. The pre-write hook only advises on these files.\n\n## Repro\n\n```sysml\npackage X {\n    private import EngineElement::*;\n    private import EngineVerification::*;\n    verification tFoo : Test {\n        :>> id = ''…''; :>> title = ''RED - …''; :>> createdAt = ''2026-09-08''; :>> createdBy = ''ai'';\n        :>> method = VerificationMethod::test;\n        :>> procedureText = ''…'';\n    }\n}\n```\n\n```\n$ keel append-result --file .tracking/x.sysml --task tFoo --sha 0f5a1d1 --verdict pass --judged-by ai --judged-at 2026-09-08\nerror: task not found: tFoo\n```\n\nThe same command against an `action tFoo;` + `verification tFooDoD : Test {…}` pair succeeds.\n\n## Suggested fix\n\nEither resolve `--task` to a standalone verification by name when no action of that name exists in the file (the result part name would be `<name>R<n>`, matching the idiom hand-appended records already use), or add an explicit `--verification NAME`. Either keeps the API's minting and append-only semantics on the path the TDD rule makes most common.\n\nFound closing a downstream sprint where two wave-5 RED verifications went green and both had to be hand-appended, as two before them had been on 2026-08-21.\n";
        :>> saidBy = "williamweatherholtz"; :>> saidAt = "2026-09-08"; :>> channel = StatementChannel::github;
        :>> sourceUrl = "https://github.com/williamweatherholtz/keel/issues/69";
        :>> sourceTrust = SourceTrust::untrusted;
    }

    part st141 : Statement {
        :>> id = "fb245923-0e98-4c7f-a85f-95e1d83b0ef0";
        :>> title = "GH#68 migrate: verified-or-reverted makes a project overlay unreachable, and an engine resync reads as a non-owner overwrite of computed-owned items";
        :>> createdAt = "2026-09-16"; :>> createdBy = "githubRecorder";
        :>> text = "Two defects found moving a downstream project (penumbra) from v0.3.1 to v0.4.1. Both are in the migrate path, both are structural rather than incidental, and neither is caught by a test. Reporting together because they were hit in the same run and the second only becomes visible after working around the first.\n\n## 1. Verified-or-reverted (D0336) forbids a project overlay from ever being applied\n\n`keel migrate` applies, gates under the new binary, and reverts `.engine/` + `.tracking/` on any red. This project must run `python tools/after_migrate.py` **after** migrate, because migrate rewrites engine-shipped files and four pins that make its adopted vintage usable live inside them. The two rules cannot both hold: the apply resets the pins, the gate runs before any repair can, and the revert lands before the repair could ever be applied.\n\n**Measured, not reasoned.** The first verified run reported ~87 failing lines and rolled back 484 files. Running the overlay afterwards proved every one of those failures was an artefact of the apply:\n\n| Repaired by the overlay | Was |\n|---|---|\n| `acceptQuotesDelegatedWords` | `2026-08-22` → project adoption date `2026-09-01` |\n| `confirmationQuotesOrAttested` | `2026-08-23` → `2026-09-01` |\n| critique-policy D1028 override | 3 armed tiers → 6 (the apply had **loosened** the gate) |\n| registry entries | 2 restored — these were the two `process-skill` ''inert process'' violations |\n\nThe cutoff resets are the retroactive-cutoff failure the project's own overlay script documents: reset to the engine's adoption date, 73 of 90 acceptance records fail at once. The engine ships **upstream's** adoption date, so installed verbatim downstream a forward-only rule becomes retroactive.\n\nSo the gate was reporting its own apply, and the revert guaranteed the fix could never run.\n\n**The only exit is `--no-verify`,** which the `project-migration` skill says never to use — on the sound general ground that it disables every other check to get past one that is usually correct. Here the one being got past was not correct. That skill also calls this the least-tested surface in the system, seven defects deep with four untested, which is exactly why a downstream author cannot tell a real red from a reset one.\n\n**Suggested fixes, in preference order:**\n\n1. A post-apply hook migrate runs *before* it gates — the project declares its overlay command in a contract, migrate runs it, then gates. This makes verified-or-reverted correct for projects with overlays instead of unreachable.\n2. Treat the cutoff-bearing rule files as project-owned, the way `attestation-policy.toml` already is under D0340 (''an adopter's grants survive a resync byte-identically''). The cutoffs are the same kind of fact: a value the engine cannot supply.\n3. Failing either, document the overlay contract so `--no-verify` is a named step rather than a violation of a skill's explicit instruction.\n\n## 2. Migrate overwrites items whose ownership is COMPUTED, so an engine resync reads as a non-owner edit\n\nAfter working around (1), `guard:ownership` refuses the tree with 16 violations:\n\n```\n.engine/views/viewpoint-registry.sysml: 'decisionsVP' is owned by 'wweatherholtz'\n  and its fields were edited by 'ai' — D0108: a non-owner ADDS items and typed edges\n  or SUPERSEDES, never overwrites in place.\n```\n\nFourteen owned by the human, two by `claudeOpus5`.\n\n**The guard is right about what happened, and the content change is still correct and necessary.** v0.4.1 moved read views under a `show` subcommand, so every `renderer` string had to change — `keel decisions` → `keel show decisions`, `keel suspect` → `keel show suspect`, sixteen in all. Left unchanged they name commands that no longer exist, which is precisely what `guard:viewpoint-renderer` fails on before the apply. The tree cannot be honest either way: keep the old strings and the renderers name nothing; take the new ones and a non-owner has overwritten owned items.\n\n**The root is that ownership here is not authored.** There is no `owner =` field anywhere in that file — `grep -c ''owner = ''` returns 0 before and after. Ownership is computed from provenance, so the acting actor at write time becomes the editor, and the bound actor running migrate is `ai`.\n\nThat makes it structural: **any migrate touching any engine-shipped file whose lines a human last authored reproduces this, on every project.** Not specific to viewpoints, not specific to this project.\n\nD0108's own escapes do not fit. Superseding sixteen viewpoints to rename a command is a workaround wearing a supersession's clothes. ''Have the owner make the change'' means a human hand-editing sixteen strings the engine already knows the correct value of. Disarming the guard is what `control-propriety` exists to refuse.\n\n**Suggested fixes:** `guard:ownership` learns that an engine resync is not an authorship claim (migrate could stamp the resync as engine-authored rather than as the invoking actor); or engine-shipped view registries stop carrying computed project ownership; or migrate reports owned-item overwrites as a distinct, dispositionable class rather than as a generic ownership violation.\n\n## State this left behind\n\nThe migration is applied and the tree is green on `keel validate .`, `keel check-engine .`, and the project's full 614-test suite. `guard:ownership` is the only violation and it blocks the commit — so the tree is neither fully migrated nor byte-identical to its preflight commit, which is the third state the `project-migration` process says must not exist.\n\nAlso worth noting, minor: migrate's rollback restored `.engine/` and `.tracking/` but **not** `.claude/`, so the new binary's surface stamp survived a revert that reported the tree was ''as it was before this run''.\n\nTracked downstream as issue218 and issue219. Happy to open PRs for either fix.\n";
        :>> saidBy = "williamweatherholtz"; :>> saidAt = "2026-09-08"; :>> channel = StatementChannel::github;
        :>> sourceUrl = "https://github.com/williamweatherholtz/keel/issues/68";
        :>> sourceTrust = SourceTrust::untrusted;
    }

    part st142 : Statement {
        :>> id = "c14688f7-503e-453a-b306-1a3f892a66d3";
        :>> title = "GH#67 [feature] TOML views cannot traverse a PROJECT-declared marker edge (only engine edge kinds are known)";
        :>> createdAt = "2026-09-16"; :>> createdBy = "githubRecorder";
        :>> text = "**Observed (keel 0.3.1).** A project declares its own marker edges in `.engine/schema/core/relationships.sysml` (`metadata def Causes; ... LeadsTo; Inverts; Mitigates; RealizedBy; Analyzes; Enforces; Senses; Explains; Satisfies` - each with the D0139(B) `doc` justification) and uses them 200+ times in its STPA model. A TOML view that tries to traverse them fails:\n\n```\nview error: view 'safety' references unknown edge kind 'causes' (known: allocate, capability, charteredby, contains, controls, covers, dependency, dependson, derivedfrom, dispositions, ..., verify, view)\n```\n\nand `edges = [''dependency'']` does NOT include marker-form dependency statements either (a `[select] type = ''UnsafeControlAction''` + `traverse dependency both closure` returned only the 22 UCAs).\n\n**Expected.** Either (a) a project-declared `metadata def` becomes a traversable edge kind by name (the declaration is type-checked already - D0133 - so the vocabulary is known to the engine), or (b) `dependency` covers every `#Marker dependency from A to B;` statement regardless of marker, with `[traverse.target]` available to filter. Without one of these a project's own edge vocabulary is authored, validated, guarded - and invisible to every declared view; the safety viewpoint here had to fall back to the SR -> Test `verify` slice.\n\n---\nFiled from obsidian-selfsync (keel 0.3.1, 2026-09-07). Context: https://github.com/williamweatherholtz/obsidian-selfsync/blob/main/.engine/views/safety.view.toml\n";
        :>> saidBy = "williamweatherholtz"; :>> saidAt = "2026-09-08"; :>> channel = StatementChannel::github;
        :>> sourceUrl = "https://github.com/williamweatherholtz/keel/issues/67";
        :>> sourceTrust = SourceTrust::untrusted;
    }

    part st143 : Statement {
        :>> id = "2b5d3a0e-82cb-43fb-9456-9d9b306ba6aa";
        :>> title = "GH#66 [feature] Propagate suspicion from architectural elements to dependent STPA analysis artifacts (reassess-on-change)";
        :>> createdAt = "2026-09-16"; :>> createdBy = "githubRecorder";
        :>> text = "Downstream project decision (obsidian-selfsync D0017), carried here because it is a keel change.\n\n**Ask.** Extend the suspicion computation to propagate along the analysis->architecture linkage edges: when an architectural element (Controller, ControlAction, Feedback, Sensor, ProcessModel) is modified at a commit LATER than a dependent analysis element (UnsafeControlAction, LossScenario, SafetyRequirement) was last REASSESSED, mark that analysis element suspect (surfaced in `keel orient`, the safety view and `keel show suspect` with a reason). Follow `#Analyzes` / `#RealizedBy` / `#Senses` directly and `#Explains` / `#Mitigates` / `#Inverts` / `#Enforces` transitively, to fixpoint. Hazards and Losses are NOT flagged by an architecture change (only by a loss/stakeholder/boundary change).\n\n**Needs.** A per-element `reassessedAtCommit` stamp on the analysis elements in EngineSafety (schema addition, human sign-off), the propagation to fixpoint, and the surfacing. Verified by a keel test that edits a controller and asserts its UCAs/requirements go suspect while the hazards do not.\n\n**Why.** Without it an STPA silently diverges from the code it abstracts: obsidian-selfsync has a 25-SR STPA whose control structure is a first-class model with 100+ marker edges into the architecture, and today nothing tells the author that a controller changed under an analysed UCA. The project keeps `stpaSuspicionPropagation` open on this.\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/66";
        :>> sourceTrust = SourceTrust::untrusted;
    }

    part st144 : Statement {
        :>> id = "a2a22797-3278-42e1-b984-bbd0d01689a4";
        :>> title = "GH#65 [docs] Stale engine-shipped docs after D0222 / per-actor issue files";
        :>> createdAt = "2026-09-16"; :>> createdBy = "githubRecorder";
        :>> text = "`.engine/docs/usage.md` still says ''Register an AI skill | Add an AISkill/Agent to skills-registry.sysml''\n(now per-skill `registry.sysml`, D0222) and ''Track an issue | Author a part in .tracking/issues.sysml''\n(now `keel record issue` -> `.tracking/issues-<actor>.sysml`). Engine-owned, so not fixed downstream.\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/65";
        :>> sourceTrust = SourceTrust::untrusted;
    }

    part st145 : Statement {
        :>> id = "a9b7d25c-7c23-4ade-ae1b-9359a2280e22";
        :>> title = "GH#64 [bug] `sprint-closure` exempts an unstamped task by the TEXT of its action-line comment";
        :>> createdAt = "2026-09-16"; :>> createdBy = "githubRecorder";
        :>> text = "**Observed.** `action dodBackfillStamp;` (open, unstamped, in the OPEN section of the def) failed\n`sprint-closure` (''work has moved on to a later sprint''). Changing ONLY the trailing comment to\n`action dodBackfillStamp;  // resolver for issueHistoricalDoDsUnstamped` made the guard PASS; moving the\ntask elsewhere in the def did not. So the exemption is decided by comment text (presumably ''resolver for'' /\n''OPEN''), which a `.sysml` comment is not a typed fact. A task that is genuinely open should be exempt by a\ntyped signal (e.g. it is the `#Resolves` source of an open Issue, or it sits in the highest-numbered\nsprint as D0260 states) — not by whether the author wrote a particular phrase after `//`.\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/64";
        :>> sourceTrust = SourceTrust::untrusted;
    }

    part st146 : Statement {
        :>> id = "cca27dee-6e49-485e-b514-9afb27e9231b";
        :>> title = "GH#63 [bug] `keel add-task --def X` appends the task OUTSIDE the action def when the def is not the last block in the package";
        :>> createdAt = "2026-09-16"; :>> createdBy = "githubRecorder";
        :>> text = "**Observed.** `.tracking/delivery/delivery.sysml` is `package ProjectDelivery { action def SelfSyncDelivery {...}  <#Capability stories, edges...> }`.\n`keel add-task --file ... --def SelfSyncDelivery --task coversEdgesHoisted --method inspect --dod-from F` (and a\nsecond call) appended `action coversEdgesHoisted; verification ...DoD ...` immediately before the PACKAGE's closing\nbrace — after package-level `#Covers` edges and `#Capability` stories — i.e. outside the def it was told to\nextend. `keel validate` accepted it and `keel guard` was green (the task still resolved its issue), so nothing\nsignalled the mis-placement; `sprint-closure` then judged the open task by its position after every shipped\nsprint (''work has moved on to a later sprint''). The stock template happens to end the file with the def, which\nis presumably why the anchor works there.\n\n**Expected.** Insert before the named def's own closing brace (or refuse with ''def close not found''), never at\nthe package tail. Also: `keel record issue` numbers a new record as `issueNNN` by counting existing `issueNNN`\nnames in the per-actor file, so after a rename (issue001 -> a semantic name) the next record is `issue001` again;\nminting from a counter or the id would avoid the collision-by-rename.\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/63";
        :>> sourceTrust = SourceTrust::untrusted;
    }

    part st147 : Statement {
        :>> id = "7fbbccce-f2d6-4e0e-a2b4-ef5a4e25c87d";
        :>> title = "GH#62 [bug] `open-issues` treats a finding with a `#Dispositions` edge as closed even when the disposition Test has NO TestResult";
        :>> createdAt = "2026-09-16"; :>> createdBy = "githubRecorder";
        :>> text = "**Observed.** A `method=confirmation` Test carrying `disposition = DispositionKind::acceptRisk`,\ndeliberately WITHOUT a TestResult (the owner had not yet attested), linked to a finding with\n`#Dispositions dependency from <test> to <issue>;`. `keel show open-issues` then dropped the issue\nfrom BOTH the open and resolved lists; `keel show dispositions` did not list it as a finding.\nDeleting the single edge line made the issue reappear as open; restoring it hid it again.\n\n**Expected.** Per D0092 a disposition is a typed RECORDED JUDGMENT — the judgment is the TestResult\n(who/when/against what), not the edge. An unattested disposition should leave the finding OPEN,\nexactly as an unstamped DoD leaves a task open. As it stands, an item awaiting the owner's word is\ninvisible to the owner.\n\n**Local mitigation.** The edge is withheld until the attestation is recorded (comment in\n`.tracking/verification/acceptance.sysml` carries the exact edge to author at that moment); issue\n`issueUnattestedDispositionClosesFinding`, resolver `keelDispositionLensReport`.\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/62";
        :>> sourceTrust = SourceTrust::untrusted;
    }

    part st148 : Statement {
        :>> id = "3317ad1b-17a7-45a6-811b-7293b632d91b";
        :>> title = "GH#61 [bug] `keel migrate --dry-run` reports 0 blockers for a change that deletes a project's schema additions";
        :>> createdAt = "2026-09-16"; :>> createdBy = "githubRecorder";
        :>> text = "**Observed.** On a July-2026-vintage tree with 25 `metadata def` declarations in\n`.engine/schema/core/relationships.sysml` (18 engine + 7 project markers added by an accepted project\nDecision D0045), `keel migrate . --dry-run` reported ''481 files / 481 edits / 0 blockers''. The live\n`keel migrate .` overwrote the file with the stock copy: 25 -> 18 declarations, and the project's\ninstance data then failed `keel validate` (marker-vocabulary 0 -> 228 violations, attribute-vocabulary\n0 -> 1216). Rolled back at the time (project D0048), later redone under a committed transform that\nre-adds the project's declarations by name (project D0050).\n\n**Expected.** A dry-run that would overwrite an engine-shipped file the project has EXTENDED (its\ncurrent content is not byte-equal to any stock vintage) should list that file as a blocker — or at\nleast as ''project-modified, will be overwritten'' — rather than 0 blockers. The same applies to the\nshared skills registry (8 project-only AISkill registrations were dropped) and to project-only\nprocess files whose shape the new schema rejects (`part X : Process` vs `action def Process`,\n`:>> order` no longer declared).\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/61";
        :>> sourceTrust = SourceTrust::untrusted;
    }

    part st149 : Statement {
        :>> id = "be93e976-d4e2-49f7-a7a1-422f0c96a4f3";
        :>> title = "GH#60 [bug] keel-parser skips a `dependency` statement nested inside an `action def` body — silently";
        :>> createdAt = "2026-09-16"; :>> createdBy = "githubRecorder";
        :>> text = "**Observed.** `.tracking/delivery/delivery.sysml` had 74 `#Covers dependency from <sittingReview> to <task>;`\nstatements at indent 8, inside `action def SelfSyncDelivery { ... }`. `keel show marker-census` reported\n`Covers` edges = 0 (proseMentions 86); `keel show sitting-coverage` reported 0 covered sprints; the\nparser-coverage guard reported 81 skipped statements = 7 successions + 74 dependency. Package-level\n`#Verify dependency` statements in the same project (114) were all counted.\n\n**Reproduction.** Four probe files run through `keel check`: (a) package-level marker dependency,\n(b) two marker dependencies on one line, (c) a marker dependency with a trailing `//` comment,\n(d) a dependency nested inside a `part`/`action` body. ALL four report `1 file(s) checked clean`.\nOnly (d) is skipped by the census. Hoisting the 74 statements to package level: Covers edges 74,\nskipped count 7, sitting-coverage counts covering reviews.\n\n**Why it matters.** The sitting review is the single human gate in the sprint discipline (D0049); the\nlens that reports its coverage read a false zero for the life of the record, and `keel check` gave no\nsignal. A construct the parser does not read should be a parse error (or the nested form should be\nparsed), never a clean check. The parser-coverage ratchet catches the COUNT but not the location —\nlisting the skipped statements' file:line in the warning would have made this a two-minute fix.\n\n**Local mitigation.** Edges hoisted (obsidian-selfsync commit 4a991a54, `coversEdgesHoisted`);\nbaseline kept at the stock 7; issue `issueNestedCoversEdgesSkipped` (#ProcessDefect) records it.\n\n---\nFiled from obsidian-selfsync (keel 0.3.1, 2026-09-07). Full report with context: https://github.com/williamweatherholtz/obsidian-selfsync/blob/main/docs/upstream/2026-09-07-keel-toolkit-defect-reports.md";
        :>> saidBy = "williamweatherholtz"; :>> saidAt = "2026-09-08"; :>> channel = StatementChannel::github;
        :>> sourceUrl = "https://github.com/williamweatherholtz/keel/issues/60";
        :>> sourceTrust = SourceTrust::untrusted;
    }

    part st150 : Statement {
        :>> id = "83e0eba5-09fd-4de8-a84d-4caf2a49cc07";
        :>> title = "GH#41 guard:resolver-kind rejects an action resolver while naming 'action' as valid";
        :>> createdAt = "2026-09-16"; :>> createdBy = "githubRecorder";
        :>> text = "`#Resolves` pointing at an `action` declared inside a project `action def` is rejected, and the rejection message names the resolver's kind as exactly the kind it says is required.\n\n**Observed**\n\n```\nERROR aimQuantization: #Resolves comes from layoutControl, which is a action — a resolver\nmust be a declared action (work that closes it) or a Decision (which moots it); ...(issue136)\n```\n\n**Repro** — in a `.tracking/` package:\n\n```\naction def MyBacklog {\n    action layoutControl;\n    verification layoutControlDoD : Test { ... }\n    part layoutControlR1 : TestResult { ... outcome = VerdictKind::pass; }\n}\n#Resolves dependency from layoutControl to someIssue;\n```\n\n`keel validate` is clean; `guard:resolver-kind` errors as above.\n\n**Neither placement works.** Moving the edge *inside* the `action def` silences `resolver-kind` — but only because it no longer sees the edge at all: `guard:issues` then reports `untriaged — no #Resolves edge`. So the two guards disagree about where the edge must live, and one of the two always fires. Qualifying the reference (`MyBacklog::layoutControl`) is a parse error: `expected To, got ColonColon`.\n\n**Workaround used:** point `#Resolves` at a Decision instead, keeping the action as the work record. That loses the action/Decision distinction the rule exists to preserve — a Decision *moots* an Issue, an action *closes* it, and here the work genuinely closed them.\n\nguards.md notes this predicate is deliberately bespoke because `objectType` filters by declared item TYPE and an action is not a typed element, so it must recognise actions some other way; that recognition appears not to reach actions declared in a project `action def`, or the message misreports the kind it found.";
        :>> saidBy = "williamweatherholtz"; :>> saidAt = "2026-08-31"; :>> channel = StatementChannel::github;
        :>> sourceUrl = "https://github.com/williamweatherholtz/keel/issues/41";
        :>> sourceTrust = SourceTrust::untrusted;
    }

    part st151 : Statement {
        :>> id = "05ef197b-58bc-4160-8f85-2cab5e7251cf";
        :>> title = "GH#40 A strict-profile project cannot make its INITIAL commit: the keystone lock counts all 128 scaffolded files as a process change, and init emits no #ProspectiveChange Decision";
        :>> createdAt = "2026-09-16"; :>> createdBy = "githubRecorder";
        :>> text = "## Summary\n\nA strict-profile project cannot make its **initial commit**. The keystone hard-lock counts every scaffolded file as a process-definition change — because a root commit has no parent to diff against — and `keel init` does not emit the `#ProspectiveChange` Decision the guard demands. The scaffold the tool produces is rejected by the gate the tool installs.\n\nSecond, smaller defect in the same flow: consuming a `keel override` writes an obligation file that **does not validate**, so the sanctioned escape hatch also leaves the tree red.\n\n## Repro — the initial commit\n\n1. `keel init myproject --profile strict`\n2. `cd myproject && git init && git config core.hooksPath .githooks`\n3. Author anything, `git add -A`, `git commit`\n\n## Observed\n\n```\nERROR locked file(s) changed (.engine/contracts/activation.toml, ... 128 paths ...,\n.githooks/pre-commit, .github/workflows/keel-gate.yml) with NO co-committed process-change\nDecision (a #ProspectiveChange/#SafetyChange-marked .engine/decisions/*.sysml). HARD LOCK: ...\n[guard:process-change] FAIL — 128 scanned, 0 warning(s), 1 violation(s)\npre-commit: keel guard FAILED — commit aborted\n```\n\nAll 128 are files `keel init` itself wrote moments earlier — every process definition, every skill, the contracts, the pre-commit hook, the CI workflow.\n\nThe guard's premise is right: an enforcement surface may not change without a human signing for it, and that holds on the commit that *introduces* the surface no less than on one that edits it. The defect is that `keel init` leaves the project unable to satisfy it.\n\n## Workaround\n\nAuthor a `#ProspectiveChange` Decision adopting the scaffold, and **co-commit it**:\n\n```\nkeel record decision --from DRAFT.md --process-change\ngit add -A          # the Decision must be in the SAME changeset\nkeel guard .        # exit 0\n```\n\nNote the ordering trap: staging before recording the Decision leaves the guard still failing, because it looks for the Decision in the same changeset. That is correct behaviour, but it is easy to hit and the error message does not mention it.\n\n## Expected\n\nEither:\n\n1. `keel init` emits the adoption Decision as part of the scaffold — it knows exactly which surface it wrote; or\n2. the keystone guard recognises a **root commit** (no parent) and reports the scaffold adoption as an obligation to sign rather than a violation; or\n3. `keel init` prints the required next step, so the operator is not left deducing it from a 128-path error.\n\n(1) is the cleanest — the Decision's content is fully determined by what init just wrote, including the binary version and build commit that produced it, which is exactly the provenance a human should be signing for.\n\n## Second defect: the override obligation does not validate\n\n`keel override <path> --reason ''...''` then writing through the unlocked path records an obligation at `.tracking/obligations/override-<hash>.sysml`. The generated file declares:\n\n```sysml\npackage Obligation7c7fff9e {\n    private import EngineElement::*;\n\n    part obligation7c7fff9e : Issue {\n        ...\n        :>> severity = Severity::Low;\n```\n\n`Issue` and `Severity` are defined in **`EngineWork`** (`.engine/schema/core/work.sysml:70`), which is not imported. The result:\n\n```\nERROR .tracking/obligations/override-7c7fff9e.sysml:7 — unresolved type reference `Issue`\n```\n\nSo the sanctioned override path leaves the model broken and the operator must hand-repair keel's own generated output by adding `private import EngineWork::*;`.\n\nCombined with the initial-commit lock above, both the primary path and its escape hatch are currently red out of the box.\n\n## Environment\n\n```\nkeel 0.3.0\nbuild commit: c444ca5\nguards: 51 (42 hard-blocking, 9 warning-only)\n```\nBoth reproduced on Windows 11 with a project scaffolded 2026-08-29 via `keel init . --profile strict`. The obligation defect was re-confirmed on 0.3.1.\n";
        :>> saidBy = "williamweatherholtz"; :>> saidAt = "2026-08-31"; :>> channel = StatementChannel::github;
        :>> sourceUrl = "https://github.com/williamweatherholtz/keel/issues/40";
        :>> sourceTrust = SourceTrust::untrusted;
    }

    part st152 : Statement {
        :>> id = "c57821e0-4fff-4d46-a6a5-304165ccca0a";
        :>> title = "GH#38 The decision-channel workflows use third-party actions, so under an org Actions allowlist they startup_failure forever and the cron emails on every run";
        :>> createdAt = "2026-09-16"; :>> createdBy = "githubRecorder";
        :>> text = "Verified: `.github/workflows/decision-issue.yml` and `.github/workflows/decision-record.yml` both reference `dtolnay/rust-toolchain` and `Swatinem/rust-cache`.\n\n## What happens in a project that adopts the channel\n\nMany GitHub organisations restrict Actions to GitHub-owned plus a named allowlist. Where neither third-party action is allowlisted, the workflow never parses into a run — every trigger is a `startup_failure`, not a failing step.\n\nIn the deployment we hit this in: **57 of 57 runs startup_failed, zero successes ever.** The channel had therefore never worked in that repo at all — including the `issue_comment` path, so a one-letter acceptance comment recorded nothing, silently.\n\nThe second cost is attention. The sweeper cron (`*/30`) retries twice an hour indefinitely, and GitHub emails the workflow actor on every failed scheduled run — roughly 48 mails a day. That is what surfaced it: the human asked why they were getting so much mail from a repo, not why decisions weren't recording.\n\n## Why this is worth fixing rather than documenting\n\nThe failure is invisible in the direction that matters. A channel that has never once run looks, from inside the project, exactly like a channel with nothing to say — there is no decision sitting unrecorded that anyone can see. The only signal is the mail volume, which reads as noise rather than as a broken mechanism.\n\n## Direction (yours)\n\n`ubuntu-latest` ships a Rust toolchain and `rustup` is preinstalled, so the third-party actions may not be needed at all for these two workflows — dropping them would make the channel work under any allowlist without asking every adopting org to change policy. Vendoring a release binary would also do it.\n\nWorth considering separately: a startup_failure is not observable from the project side, so if the channel is meant to be relied on, it may want a way to say ''I have never successfully run here''.\n\nFor context on the reporting project: we retired the channel locally rather than pursue an org allowlist change, so this is filed for other adopters, not as a blocker for us.";
        :>> saidBy = "williamweatherholtz"; :>> saidAt = "2026-08-30"; :>> channel = StatementChannel::github;
        :>> sourceUrl = "https://github.com/williamweatherholtz/keel/issues/38";
        :>> sourceTrust = SourceTrust::untrusted;
    }

    part st153 : Statement {
        :>> id = "3169ce4b-3c3a-4575-a8ad-2821d3ab010c";
        :>> title = "GH#37 A project cannot decline an engine-shipped skill: removing the deployed copy reds guard:activation-manifest, and the registry is engine-owned";
        :>> createdAt = "2026-09-16"; :>> createdBy = "githubRecorder";
        :>> text = "Verified against `keel-cli/src/claude_surface.rs` at 6146f43 (0.3.1).\n\n## What happens\n\n`claude_surface` iterates `registry_skills(root)` and, for every entry, requires a byte-identical `.claude/skills/<name>/SKILL.md`:\n\n```rust\nfor (title, loc) in &registry {\n    let dst = claude.join(''skills'').join(title).join(''SKILL.md'');\n    ...\n    if std::fs::read_to_string(&dst).unwrap_or_default() != src_text { missing_skills += 1; }\n}\nif missing_skills > 0 { drift.push(format!(''{missing_skills} skill(s) missing or stale under .claude/skills/'')); }\n```\n\nSo a project that deliberately retires a workflow has no way to stop the skill being offered. Deleting the deployed copy gives:\n\n```\nERROR 1 skill(s) missing or stale under .claude/skills/\n[guard:activation-manifest] FAIL\n```\n\nand the registry that drives it lives under `.engine/`, which a project must not edit.\n\n## Why it matters\n\nWe retired a workflow with an accepted Decision recording exactly why. We could record the retirement but not enforce it: the skill still appears in the agent's skill listing, and the strongest signal available is a paragraph inside a decision file that the next session may never open. A listed skill reads as an available one.\n\nThis is the same shape as an inert contract left in place — except a contract sitting unused is harmless, while a deployed skill actively advertises itself to the agent.\n\n## What would help\n\nA project-scoped opt-out the guard honours, so ''we do not use this here'' is a computable fact rather than prose. Shapes that would work for us, in rough order of preference:\n\n1. A declined-skills list in `.tracking/` (or wherever project activation already lives), consulted by `claude_surface` before requiring deployment.\n2. A `retired`/`declined` flag the registry can carry per project.\n3. Failing both: have the guard treat an absent skill as satisfied when the project records the decline somewhere the engine already reads.\n\nHappy to be told this belongs in the activation manifest rather than the registry — the ask is only that declining is expressible without editing `.engine/`.";
        :>> saidBy = "williamweatherholtz"; :>> saidAt = "2026-08-30"; :>> channel = StatementChannel::github;
        :>> sourceUrl = "https://github.com/williamweatherholtz/keel/issues/37";
        :>> sourceTrust = SourceTrust::untrusted;
    }

    part st154 : Statement {
        :>> id = "e122da8a-c4b9-4529-b76f-03fdfda99907";
        :>> title = "GH#36 keel migrate: the removed-type scan reads prose, so a description mentioning `ureq::Agent` blocks migration with no way through";
        :>> createdAt = "2026-09-16"; :>> createdBy = "githubRecorder";
        :>> text = "Reported from a downstream project that is pinned to 0.3.0 because of this. Verified against `keel-cli/src/migrate.rs` at 6146f43 (0.3.1).\n\n## What happens\n\n`step_removed_types` scans every authored file **line by line** and applies `types_as(line, ty)` with no awareness of string literals or comments. `types_as` accepts a hit when the text before it ends with `:` or `:>`.\n\nThat makes ordinary prose look like an instance of a removed type. The case that blocked us:\n\n```\n:>> description = ''... the HTTP client is a ureq::Agent held by the adapter ...'';\n```\n\n`ureq::Agent` → the text before `Agent` ends with `:`, the left char `:` is not an ident char, nothing follows → **matches the removed `Agent` type**. The line is a description string. There is no `Agent` item anywhere in the model.\n\nAny `foo: Agent`, `Risk`, `Task`, `Epic`, `Role` etc. inside a `description`, `procedureText`, `notes` or `rationale` will do the same — and those fields are exactly where a project explains *why it removed something*, so writing the migration note can itself block the migration.\n\n## Why there's no way through\n\n- The blocker is prose, so there is nothing to ''migrate''.\n- The advice on `REMOVED_TYPES` says to re-add the def in your own `.engine/schema/`. That doesn't clear it: `REMOVED_TYPES` is a static list and the scan never consults the project's schema, so a project that *has* re-added the type is still blocked, on prose, forever.\n- Rewording the prose works, but it means editing authored history to satisfy a scanner — and on a large model you find them one migration run at a time.\n\n## Minimal repro\n\nIn any project on 0.3.0, add to an authored `.sysml`:\n\n```\n:>> description = ''the client is a ureq::Agent'';\n```\n\nthen `keel migrate .` — it reports a `removed-types` blocker for `Agent` on that line.\n\n## Direction (yours to choose)\n\nThe general fix is for the scan to understand what it's reading rather than pattern-match raw lines: skip string literals and comments, or scan only *declaration* positions rather than any `:`-adjacent occurrence. A narrower fix that would have unblocked us: consult the project's own `.engine/schema/` before reporting a removed type, so the documented ''re-add it yourself'' advice actually works.\n\nRelated, same class: #33 and #34 are also scans whose coverage or precision differs from what they report.";
        :>> saidBy = "williamweatherholtz"; :>> saidAt = "2026-08-30"; :>> channel = StatementChannel::github;
        :>> sourceUrl = "https://github.com/williamweatherholtz/keel/issues/36";
        :>> sourceTrust = SourceTrust::untrusted;
    }

    part st155 : Statement {
        :>> id = "3f1d38fb-cd41-4b7a-8c41-53b1c05f87f3";
        :>> title = "GH#35 status-report skill is inert: it invokes .engine/tools/report.py, which the binary does not ship";
        :>> createdAt = "2026-09-16"; :>> createdBy = "githubRecorder";
        :>> text = "## Summary\n\nThe `status-report` skill that `keel init` deploys instructs the operator to run `python .engine/tools/report.py`. That file does not exist in a scaffolded project, and the binary does not ship it. The skill is discoverable and inert.\n\n## Repro\n\n1. `keel init myproject --profile strict`\n2. Invoke the `status-report` skill (or read `.claude/skills/status-report/SKILL.md`)\n3. Follow its ''How to Invoke'' section\n\n## Observed\n\n`.claude/skills/status-report/SKILL.md` says:\n\n```powershell\n# From repo root — generates and opens in browser:\npython .engine/tools/report.py\n\n# With explicit output path:\npython .engine/tools/report.py --output docs/status.html\n```\n\nand adds:\n\n> The script requires only Python standard library + the `target/release/keel.exe` binary for orient JSON.\n\nBut:\n\n```\n$ ls .engine/tools/\ndeck_inbox_record.py\ntest_deck_e2e.py\n\n$ find . -name 'report.py'\n(no results)\n```\n\nTwo separate problems in that quote:\n\n1. **`report.py` is absent.** Nothing in the scaffolded tree provides it.\n2. **`target/release/keel.exe` is a path from the engine's own source tree.** No scaffolded project has a `target/release/`; a downstream user installs the released binary onto PATH. Even if `report.py` shipped, that reference would not resolve.\n\n## Working equivalents that DO ship\n\nThe CLI already covers the skill's stated output:\n\n```\nkeel orient . --html                          # the dashboard\nkeel report governance . --html               # and assurance | traceability |\n                                              # quality-debt | flow | friction\n```\n\nBoth produce self-contained HTML carrying the right provenance meta tag:\n\n```html\n<meta name=''generator'' content=''keel report (computed #View; regenerate, do not commit as truth)''>\n```\n\nThe scaffolded `.gitignore` also already reserves `*.keel.html` for these outputs, so the convention exists — only the skill is out of date.\n\n## Expected\n\nEither ship `.engine/tools/report.py`, or rewrite the skill onto `keel orient --html` / `keel report <r> --html` and drop the `target/release/keel.exe` reference. The second looks correct given the CLI already does the job and needs no Python at all.\n\n## Sharper point\n\nA skill that is deployed, listed and inert is worse than an absent one. It is discoverable, so an operator finds it and follows it, and the failure only surfaces at the shell. `keel sync-claude --check` reports drift in the keel-owned `.claude/` surface but did not catch this, because the skill file is present and internally consistent — it is only its *referent* that is missing. A check that a skill's named tool paths resolve would have caught it.\n\n## Environment\n\n```\nkeel 0.3.0\nbuild commit: c444ca5\napi contract: 2.0.0 (derived)\nguards: 51 (42 hard-blocking, 9 warning-only)\nclaude surface: 0.3.0 (generated from this binary)\n```\nWindows 11. Project scaffolded 2026-08-29 via `keel init . --profile strict`. 38 skills deployed.\n";
        :>> saidBy = "williamweatherholtz"; :>> saidAt = "2026-08-30"; :>> channel = StatementChannel::github;
        :>> sourceUrl = "https://github.com/williamweatherholtz/keel/issues/35";
        :>> sourceTrust = SourceTrust::untrusted;
    }

    part st156 : Statement {
        :>> id = "bc0822b0-bfbb-4de5-9a1a-29b7c9f795bd";
        :>> title = "GH#34 keel trace reports no edges for marker-carried dependencies while marker-census counts 111 in the same model";
        :>> createdAt = "2026-09-16"; :>> createdBy = "githubRecorder";
        :>> text = "## Summary\n\n`keel trace <item>` reports `upstream: []` / `downstream: []` for every item tested, in a model where `keel marker-census` AST-counts **111 marker edges**. Two computed views disagree about the same tree.\n\n`keel --help` describes trace as *''every typed edge reaching an item, both directions''*, which promises the marker-authored edges are included.\n\n## Observed\n\nAuthored in `.tracking/intake/`, both endpoints declared as parts in the same model:\n\n```sysml\n#DerivedFrom dependency from us18 to s8;\n```\n\n`keel validate .` — clean, 7 files. Then:\n\n```\n$ keel trace us18 .\n{''name'':''us18'',''upstream'':[],''downstream'':[]}\n\n$ keel trace s8 .\n{''name'':''s8'',''upstream'':[],''downstream'':[]}\n```\n\nSame empty result for 7 items spanning both trees and four item kinds — `s1`, `s8`, `us18`, `us24`, `us31`, `supplyFlowBucketTest`, `d0230`, plus `d0226` from `.engine/reference/`.\n\nMeanwhile, on the same tree:\n\n```\n$ keel marker-census .\nDerivedFrom 37 | Supersede 32 | Resolves 17 | DependsOn 11 | JustifiedBy 10\nImplicates 2  | Verify 1     | Dispositions 1        (edges, AST-counted)\n```\n\n## Name resolution is not the cause\n\nTrace distinguishes an unknown name from an empty result, and the bare names resolve:\n\n```\n$ keel trace IntakeReadback::us18 .\nkeel trace: no item named `IntakeReadback::us18` is declared in this model. An unknown name\nexits non-zero rather than answering with an empty result, because an empty result reads as\n`this item has no edges` ...\n```\n\nSo a qualified name errors, a bare name returns the empty result — trace is finding the item and reporting that it has no edges.\n\n## Question rather than a claim\n\nTrace may be scoped to **native** typed edges (`satisfy`, `allocate`, `:>`) by design, with metadata-marker dependencies deliberately excluded. If that is the intent, this is a documentation defect rather than a logic one — but it is still a defect, because the help text says ''every typed edge'' and the engine's own `relationships.sysml` header documents markers as the edge algebra's carrier wherever no native form exists:\n\n> `verify` -> NO BASE FORM EXISTS for this edge. `#Verify` is a JUSTIFIED last resort (D0140).\n> `#DerivedFrom` is a JUSTIFIED last resort (D0140): all 37 of its edges are CROSS-metaclass ...\n\nIf the majority of a project's real graph is marker-carried by design, a trace that omits markers shows almost nothing.\n\n## Why it matters\n\n`relationships.sysml:28-30` documents suspicion propagating along `satisfy`, `verify`, `:>`, `allocate` and semantic `dependsOn`. Trace is the natural view for checking that a change actually reaches its dependents before relying on it. In this project the author's stated need is precisely that — every layered assumption verified, with invalidation propagating upward when a layer is overturned. Today the propagation can be authored but not inspected.\n\n## Environment\n\n```\nkeel 0.3.0\nbuild commit: c444ca5\napi contract: 2.0.0 (derived)\nguards: 51 (42 hard-blocking, 9 warning-only)\n```\nWindows 11. Project scaffolded 2026-08-29 via `keel init . --profile strict`. `keel validate` and `keel guard` both green at time of observation.\n";
        :>> saidBy = "williamweatherholtz"; :>> saidAt = "2026-08-30"; :>> channel = StatementChannel::github;
        :>> sourceUrl = "https://github.com/williamweatherholtz/keel/issues/34";
        :>> sourceTrust = SourceTrust::untrusted;
    }

    part st157 : Statement {
        :>> id = "5d7ae730-a771-47a0-9fb5-09780eafeddd";
        :>> title = "GH#33 guard:scaffold-placeholder misses placeholder ACTORS - a Person named 'Your Name' survives a fully green run";
        :>> createdAt = "2026-09-16"; :>> createdBy = "githubRecorder";
        :>> text = "## Summary\n\n`guard:scaffold-placeholder` passes while the shipped placeholder actors — including a `Person` named `''Your Name''` — are still registered in `.tracking/actors.sysml`. `keel enroll` appends real actors beside them without removing or flagging them, so a scaffolded project can run fully green with an unowned human identity in its actor registry.\n\n## Repro\n\n1. `keel init myproject --profile strict`\n2. `keel enroll --actor will --name ''William Weatherholtz'' --kind human --role supervisor --email ... .`\n3. `keel enroll --actor claudeOpus5 --name ''...'' --kind ai --role contributor .`\n4. `keel guard .`\n\n## Observed\n\n`.tracking/actors.sysml` after both enrollments:\n\n```sysml\npackage ProjectActors {\n    private import EngineElement::*;\n\n    part you : Person { :>> name = ''Your Name''; :>> email = ''you@example.com''; }\n    part ai : Actor { :>> name = ''AI assistant''; :>> kind = ActorKind::ai; }\n    part will : Person { :>> name = ''William Weatherholtz''; ... :>> role = ''supervisor''; }\n    part claudeOpus5 : Actor { :>> name = ''Claude Opus 5 (Claude Code)''; ... }\n}\n```\n\nGuard output:\n\n```\n[guard:scaffold-placeholder] PASS — 326 scanned, 0 warning(s), 0 violation(s)\n[guard:actors]               PASS — 3 scanned, 0 warning(s), 0 violation(s)\n[guard] ALL PASS\n```\n\nBoth placeholders survive a full green run. (Side observation: `guard:actors` reports **3 scanned** against **4** declared parts — possibly unrelated, but the count does not match the file.)\n\n## Why it matters\n\n`you` is a registered `Person`, and `Person` is the type that gates human-only authority. Per D0106 and the enroll output itself, accepting a Decision, dispositioning a >= Medium finding and adjudicating a contributor conflict all require a human actor — `keel enroll --kind ai` explicitly refuses them. A placeholder `Person` is therefore a registered human identity that nobody owns.\n\nThe scaffold comment does say `EDIT to your real actors`, but that is a reminder, and D0047 is explicit that manual vigilance is not a control.\n\n## NOT tested\n\nI did **not** run `keel accept <decision> --by you` to see whether an attestation attributed to the placeholder would be accepted, because doing so would record a real acceptance in a real project. This is reported as an untested exposure, not a demonstrated exploit.\n\n## Expected\n\nEither:\n\n1. `guard:scaffold-placeholder` flags placeholder actors the way it flags other scaffold residue — the strings are fixed and known (`Your Name`, `you@example.com`, `AI assistant`); or\n2. `keel enroll` removes or supersedes the placeholders on the first real enrollment, since that is the moment the project stops needing them.\n\n(1) is the control; (2) removes the occasion. Both would be better than either.\n\nNote that the workaround is itself awkward: removing them by hand is blocked by the fact-surface write guard (`[keel] in-place sed over a fact surface`), so a user following the scaffold's own advice to ''EDIT to your real actors'' hits a gate telling them to use a write API that has no actor-removal verb.\n\n## Environment\n\n```\nkeel 0.3.0\nbuild commit: c444ca5\napi contract: 2.0.0 (derived)\nguards: 51 (42 hard-blocking, 9 warning-only)\n```\nWindows 11. Project scaffolded 2026-08-29 via `keel init . --profile strict`.\n";
        :>> saidBy = "williamweatherholtz"; :>> saidAt = "2026-08-30"; :>> channel = StatementChannel::github;
        :>> sourceUrl = "https://github.com/williamweatherholtz/keel/issues/33";
        :>> sourceTrust = SourceTrust::untrusted;
    }
}
