// Intake for 2026-09-18 — their words, my translation, the triage verdict (D0166/D0216).
// Written by `keel record statement` / `keel record story` (D0236): a Statement's text is
// VERBATIM, so it is escaped for the literal and otherwise untouched.
package ProjectIntake20260918 {
    private import EngineElement::*;
    private import EngineIntake::*;
    private import EngineRelationships::*;

    part st160 : Statement {
        :>> id = "241c5ac5-f188-4703-84ea-57f0ede3cf16";
        :>> title = "GH#85 [bug] Two packages may reuse a part name: every gate stays green, a typed edge binds to the wrong item, and a qualified reference does not parse";
        :>> createdAt = "2026-09-18"; :>> createdBy = "claudeFable5";
        :>> text = "Two packages may declare the same part name. Nothing detects it, a typed edge then binds to the wrong item **silently**, and there is no syntax to disambiguate because a qualified reference does not parse. Found in a downstream project (plotwright), where two `#DerivedFrom` edges are already pointing at the wrong UserStory and a guard's prescribed fix cannot be written at all.\n\nBinary: `keel 0.4.1`, build `444333d`.\n\n## Minimal repro, on a tree freshly created by this binary\n\n`keel init`, then two files under `.tracking/intake/`:\n\n`alpha.sysml`\n```\npackage IntakeAlpha {\n    private import EngineElement::*;\n    private import EngineIntake::*;\n    private import EngineRelationships::*;\n\n    part st001 : Statement {\n        :>> id = ''11111111-1111-4111-8111-111111111111'';\n        :>> title = ''ALPHA - the statement the edge below actually means'';\n        ...\n    }\n\n    part us001 : UserStory {\n        :>> id = ''33333333-3333-4333-8333-333333333333'';\n        :>> title = ''ALPHA story - derived from the ALPHA statement'';\n        ...\n    }\n    #DerivedFrom dependency from us001 to st001;\n}\n```\n\n`beta.sysml` declares a **different** Statement, different UUID, reusing the part name:\n```\npackage IntakeBeta {\n    part st001 : Statement {\n        :>> id = ''22222222-2222-4222-8222-222222222222'';\n        :>> title = ''BETA - a DIFFERENT statement that happens to reuse the part name st001'';\n        ...\n    }\n}\n```\n\nNote the edge is written **inside `IntakeAlpha`**, which declares its own `st001` three lines above it.\n\n### Result\n\n```\n$ keel gate validate .\n3 tracking file(s) validated clean.\n\n$ keel gate guard .\n[guard:duplicate-identity] PASS — 608 scanned, 0 warning(s), 0 violation(s)\n[guard:type-collision]     PASS — 0 scanned, 0 warning(s), 0 violation(s)\n\n$ keel show why us001\n  ''element'': ''us001'',\n  ''title'':   ''ALPHA story - derived from the ALPHA statement'',\n  ''file'':    ''.tracking/intake/alpha.sysml'',\n\n  ''element'': ''st001'',\n  ''title'':   ''BETA - a DIFFERENT statement that happens to reuse the part name st001'',\n  ''via'':     ''us001 ->derivedfrom st001'',\n  ''file'':    ''.tracking/intake/beta.sysml'',\n```\n\nThe edge reaches **beta**. A local declaration in the edge's own package does not win, and every gate is green while the model asserts a provenance link that is false.\n\n## Why this is severe rather than untidy\n\n`duplicate-identity` passes because it compares UUIDs, and the UUIDs genuinely differ. So the one control whose name suggests it covers this is looking at a different axis. Meanwhile `CLAUDE.md` invariant 3 states plainly that *''Every item has an immutable `id` (UUID); `title` is a human string; `displayLabel` is computed. Items never collide on name.''* That invariant is asserted in the contract and enforced nowhere.\n\nThe failure is silent in the worst way: the tree is green, the edge exists, `trace`/`why`/coverage all report confidently, and the only symptom is that the wrong item is named.\n\n## There is no way to write the disambiguation\n\nThe obvious fix at the authoring site is a qualified reference. The parser rejects it:\n\n```\n#DerivedFrom dependency from d0010 to ProjectIntake20260917::st022;\n```\n```\nPARSE: 0010-recommendationIsTheCourse.sysml:26:64: expected Semicolon, got ColonColon\n```\n\nSo an author who *notices* the collision still cannot express which item they mean. The only remedy available today is renaming one of the colliding parts, which is a bulk migration across every file that references it.\n\n(This is adjacent to #72, which reports the parser refusing a *named* dependency. Same area, different clause: this one is the reference target, not the dependency's own identification.)\n\n## What it did to a real project\n\nIn plotwright, `.tracking/intake/intake-2026-09-18.sysml` restarts Statement and UserStory numbering at `st022`/`us069` and collides with `intake-2026-09-17.sysml` on **eleven** names — `st022`–`st025` and `us069`–`us075`. The file's own header documents renumbering the three colliding *Decisions* on merge under D0022; the Statements and UserStories were missed, and nothing said so.\n\nTwo edges are already mis-bound, in `.tracking/business/plotwright-beat-facets.sysml` lines 90 and 91:\n\n| Edge | Binds to | Means |\n|---|---|---|\n| `srPwBeatFacets -> us071` | 09-18 ''Each stage page carries the feedback relevant to that stage'' | 09-17 ''The beat facets live in the tool's schema, not in a process document'' |\n| `srPwDeedRatio -> us072` | 09-18 ''Is there enough material: beats per character per act'' | 09-17 ''The deed ratio is a computed reading, not a rule of thumb'' |\n\nWorse, it makes another guard's instruction impossible to follow. `guard:direction-cited` fails d0010 with:\n\n> `d0010: quotes the human and no #DerivedFrom edge to a Statement ... Record their words with keel record statement and author #DerivedFrom dependency from d0010 to <stNNN>;`\n\nThe Statement holding the quoted span exists — `st022`, id `11829d9e-43e5-470f-9691-5f6b670b5e18`, at `intake-2026-09-17.sysml:61`. Authoring exactly the prescribed edge changed the complaint to *''no linked Statement's text holds this span verbatim''*, because it bound to the 09-18 `st022` instead. The edge was reverted rather than left in place: a link to the wrong Statement is a false provenance claim and worse than a missing one. So `direction-cited` currently cannot be discharged by any edge the grammar accepts.\n\nThere is a sharp irony in that pairing. `direction-cited` exists (issue428/D0463, hazard EHZ3) so the tree holds the human's real words rather than the agent's rendering of them — and the resolution mechanism it mandates can quietly attach those words to the wrong statement.\n\n## Suggested fixes\n\n1. **A guard that fails on a duplicate part name across the model**, sitting beside `duplicate-identity` and checking the name axis rather than the UUID axis. This is the smallest fix and it turns a silent mis-binding into a loud one.\n2. **Make an ambiguous reference an error rather than a silent pick.** If two declarations match a bare name, the edge should refuse to resolve and name both candidates with their files, instead of choosing.\n3. **Accept a qualified reference in an edge target** (`Package::name`), so an author who has a legitimate reason to keep both names has a way to say which one they mean. Without at least one of 2 or 3, noticing the bug does not help you fix it.\n4. **Cover Statements and UserStories at merge time the way Decisions already are.** Worth being precise about where the eleven collisions came from, because it is not the minting path: `keel record statement` allocates globally today — run in this same project a few minutes ago it produced `st036`, correctly above the existing high-water mark of `st035`. The collisions came from two branches each minting from their own view and then merging. That is exactly the case Decisions have handling for (this project's D0022 records the three Decisions being renumbered on merge, and #30 covered the engine-reference side), and Statements and UserStories have none. A merge that silently produces eleven duplicate names is the upstream cause; items 1–3 are what stops it being silent.\n";
        :>> saidBy = "williamweatherholtz"; :>> saidAt = "2026-09-18"; :>> channel = StatementChannel::github;
        :>> sourceUrl = "https://github.com/williamweatherholtz/keel/issues/85";
        :>> sourceTrust = SourceTrust::untrusted;
    }

    part st161 : Statement {
        :>> id = "43209b75-477f-4d2a-8fc8-4637fda75ade";
        :>> title = "GH#84 decision-surfacing dsGround binds checkedBy to judgment-request-quality, which never reads the rendered decision page";
        :>> createdAt = "2026-09-18"; :>> createdBy = "claudeFable5";
        :>> text = "Found in the Penumbra project (asirobots/Penumbra) on 2026-09-18 after its owner could not see the bifurcation on a six-tab decision page and a five-critic panel read the tabs against the rules that govern them.\n\n**What the process says.** `processes/decision-surfacing.sysml`, step `dsGround` (''Give them what an INDEPENDENT judgment needs, not a request to bless my pick'') demands the item itself, what accepting binds, the fork and the evidence inline, and declares `checkedBy = ''judgment-request-quality''`.\n\n**What the check reads.** Per `docs/guards.md`, `judgment-request-quality` scans a PROPOSED fork Decision's title, rationale, RESEARCH statement and per-OPTION cost in the decisions directory. It does not read the rendered exec-summary page or the project's tab file, and `scripts/check_templates.py` is structural only (word budgets, field presence, chain order). So the step promises enforcement of a content property and nothing enforces it.\n\n**What got through** (six tabs, one page): two tabs whose options differed only by a verdict verb (''Judge ... as PASS'' / ''Fail ... with a direction''); one option whose cost read literally `None.` (the exec-summary skill's own text says never ''none''); before/after rows whose both cells were record states (''PROPOSED'' -> ''judged''); a computed classification preamble rendered before every tab. The skill forbade three of the four; nothing read the tab.\n\n**Proposed fix, either of:**\n\n1. Retarget `checkedBy` to a check that reads the rendered page. The shapes are structural enough for `check_templates.py`: a `data-d=''cost''` whose text is exactly none, n/a or a dash; a choice label starting with a verdict verb (accept, reject, approve, confirm, pass, fail, judge); a before/after table row whose two cells are both drawn from a closed record-state vocabulary; and, if you take the field, a required `data-d=''premise''` rendered before the choices, budgeted like `stake`.\n2. Or declare the step unenforceable with a reason, per D0321's own convention, so the process stops claiming a control it does not have.\n\n**Reference implementation.** Penumbra's project-side floor is `tools/tab_quality.py` on branch `sitting-2026-09-17-attestations` (its `--self-test` holds the two offending tabs as the shapes that must refuse, and a premise-led tab and a hand-only tab as the shapes that must pass); the decision recording the panel's findings is that project's D1132.\n";
        :>> saidBy = "williamweatherholtz"; :>> saidAt = "2026-09-18"; :>> channel = StatementChannel::github;
        :>> sourceUrl = "https://github.com/williamweatherholtz/keel/issues/84";
        :>> sourceTrust = SourceTrust::untrusted;
    }

    part us115 : UserStory {
        :>> id = "13c81de1-0cba-4003-a985-25a9c5d5c7b3";
        :>> title = "A declared name is unique across the model, and a bare reference two declarations match refuses";
        :>> createdAt = "2026-09-18"; :>> createdBy = "claudeFable5";
        :>> asA = "keel adopter authoring typed edges across packages";
        :>> iWant = "a second declaration of a part name anywhere in the model to fail the tree loudly, and a bare reference that two declarations match to refuse naming both with their files, instead of a typed edge silently binding to whichever declaration the model read last";
        :>> soThat = "a green tree never asserts a provenance edge to the wrong item";
        :>> implication = ImplicationKind::bug;
        :>> triageNote = "Verified against this tree before triage, not taken from the report. members/keel-model/src/model.rs:70 declares `items: HashMap<String, ItemInfo>` keyed by the bare declared name, and the build at model.rs:244 does `items.insert(name, info)` - a second declaration of the same name in another package REPLACES the first, so every edge naming it binds to whichever file the walk read last. members/keel-guards/src/identity.rs:309 scopes the duplicate-name check to `within one package` (the violation text at :389 says `in package`), so the reported cross-package case passes duplicate-identity exactly as described; CLAUDE.md invariant 3 (`Items never collide on name`) is asserted and enforced by nothing. UNTRUSTED source (public repo, D0264): plan only. The reporter's fixes 1 (a name guard on the name axis), 2 (an ambiguous bare reference refuses naming both candidates) and 4 (the silence at merge time) are ONE defect - the model's identity key is the bare name and nothing holds it unique - routed to one Issue and one proposed Decision; fix 3 (a qualified `Package::name` target) is its own story. Fix 4's automation (renumbering Statements and UserStories on merge the way Decisions were) is not adopted here: once the name is held unique model-wide, a merge that lands two declarations goes red at the land gate naming both files, and the rename across references is the author's migration (D0067), not a silent renumber. Severity High: the tree stays green while `why`, `trace` and coverage assert a false provenance link, and a guard's prescribed fix (direction-cited) becomes impossible to discharge.";
    }
    #DerivedFrom dependency from us115 to st160;

    part us116 : UserStory {
        :>> id = "d4f7ecf6-a702-4ae6-ab9b-2e74d0627244";
        :>> title = "A qualified Package::name is accepted as the target of a typed edge";
        :>> createdAt = "2026-09-18"; :>> createdBy = "claudeFable5";
        :>> asA = "keel adopter who has noticed two packages share a part name";
        :>> iWant = "to write a qualified reference (Package::name) as the target of a typed edge, so that when two packages legitimately keep the same part name I can say which one I mean instead of renaming one of them across every file that references it";
        :>> soThat = "noticing the collision gives me a way to say which item I mean";
        :>> implication = ImplicationKind::bug;
        :>> triageNote = "The reporter's fix 3, split from the defect because it is the way out the control then requires, not the control. The parse refusal is real (the report quotes `expected Semicolon, got ColonColon` on 0.4.1) and the OMG grammar allows a qualified name there. First triaged as declined on the premise that names would be made unique model-wide; the measurement that followed (271 declared names duplicated across this tree's own .tracking and .engine, 247 of them sprint gate names reused across sprint packages by design) showed that premise renames history for a property the language does not require, so the recommended course became D0517 OPTION A: a bare reference resolves locally, else uniquely, else REFUSES naming every candidate - and the author that refusal stops needs exactly this qualified target to say which item they mean. Adopted as part of OPTION A; declined only if the human chooses OPTION B (model-wide unique names, a 271-name migration). The parser lane is GH#72's (a named dependency: the sibling clause of the same grammar rule). Routed with us115 to the same Issue and Decision.";
    }
    #DerivedFrom dependency from us116 to st160;

    part us117 : UserStory {
        :>> id = "2946c31c-ac2e-45a8-9c66-87a4dfcc945e";
        :>> title = "The dsGround step binds to a check that reads the rendered decision page";
        :>> createdAt = "2026-09-18"; :>> createdBy = "claudeFable5";
        :>> asA = "human judging a decision page built by an agent";
        :>> iWant = "the decision-surfacing step that promises every tab carries the item, what accepting binds, the fork and the evidence to be bound to a check that reads the rendered page, or to say plainly that no check does, so the process stops claiming a control it does not have";
        :>> soThat = "a tab that fails the step's own rules is refused before I see it, or the process admits nothing refuses it";
        :>> implication = ImplicationKind::process;
        :>> triageNote = "Verified in this tree: .engine/processes/decision-surfacing.sysml:49 sets dsGround `checkedBy = 'judgment-request-quality'`, and .engine/docs/guards.md:38 describes that guard as reading a PROPOSED fork Decision's title, rationale, RESEARCH statement and per-OPTION cost in the decisions directory - it never opens the rendered page, and no guard names scripts/check_templates.py (grep of guards.md: none). check_templates.py --brief (check_brief at :264) holds word budgets, field presence and chain order; none of the four content shapes the report names (a cost reading literally none/n-a/dash, a choice label led by a verdict verb, a before/after row whose two cells are both record states, a premise rendered before the choices) is read by anything. So the step binds a content promise to a check of a different artefact: a D0321 binding that resolves (the guard exists) and does not check what the step says. UNTRUSTED source (public repo, D0264): plan only. Implication `process`: the fix is to the process step and its check, routed to one Issue with a resolver and one proposed Decision carrying the reporter's two courses as OPTIONS - retarget the binding to a check that reads the page (the four shapes added to check_templates --brief, which the build script already runs and refuses on, since the page is machine-local and no tree guard can open it), or declare the step unenforceable with a reason per D0321's own convention. The reporter's reference implementation (Penumbra tools/tab_quality.py, its --self-test holding the two offending tabs) is named in the Statement and is the shape the resolver's D0388 pair takes.";
    }
    #DerivedFrom dependency from us117 to st161;

    // Routing (github-intake step 3; D0264 untrusted: every routed story names a Decision among its
    // targets, so guard untrusted-routing holds while the change waits on the human's word).
    #Implicates dependency from us115 to issue605;
    #Implicates dependency from us115 to d0517;
    #Implicates dependency from us116 to issue605;
    #Implicates dependency from us116 to d0517;
    #Implicates dependency from us117 to issue606;
    #Implicates dependency from us117 to d0518;

    part st162 : Statement {
        :>> id = "ea52c2a9-77e6-4571-9bf8-349ab460058d";
        :>> title = "GH#90 [bug] parser-coverage baseline ships at the engine's own census with no headroom for the adopter, so migrate reverts on its own output";
        :>> createdAt = "2026-09-18"; :>> createdBy = "claudeFable5";
        :>> text = "The resync ships `parser-coverage-baseline.toml` with `skipped = 7`, which is the engine's own census with no headroom for the adopting project. Any project carrying even one skipped statement of its own goes red the instant migrate installs the baseline, so `keel migrate` reverts on its own output.\n\nSecond of two blockers I hit on the same migrate run; the other is the `charteredBy` path mismatch filed alongside this. Both must clear before a migration can land.\n\n## What happens\n\n`keel migrate` writes, then its post-write gate fails:\n\n```\nERROR skipped-statement count 8 EXCEEDS the committed baseline 7 — a new\n      statement class became invisible to every guard and view (issue231\n      ratchet). Either teach keel-parser the construct, or raise the baseline\n      IN THE SAME COMMIT with the reason (a visible diff, never silent growth).\n[guard:parser-coverage] FAIL — 596 scanned, 1 warning(s), 1 violation(s)\n```\n\n## Cause\n\nThe shipped baseline documents itself as the engine's own legacy set:\n\n`.engine/contracts/parser-coverage-baseline.toml`\n\n```toml\n# Current census: 7 succession statements (`first X then Y` forms the parser reads for ordering\n# but records as skipped in workflow files) - the known, bounded legacy set.\nskipped = 7\n```\n\nThe guard counts skipped statements across the whole tree — `.tracking/` and `.engine/` together — and compares that total against the baseline: `members/keel-guards/src/identity.rs:1127`.\n\nSo the arithmetic in an adopting project is the engine's 7 plus whatever the project contributes. Measured in mine:\n\n- Before migrate, with no baseline file present, the guard reports a warning and passes: `3 statement(s) across 177 file(s) are SKIPPED ... srLocalJamaToolSurface×1, srReviewFragmentFidelity×1, srUpstreamGapIdentification×1`. All three are the project's own `.tracking` items, none are successions, and the old engine contributes none.\n- At the commit migrate actually ran against, one of those three was committed, so the project contributed exactly 1.\n- Post-migrate the count is 8: the engine's 7 successions plus that 1. Baseline 7. Red.\n\nA baseline of exactly the engine's own census means the ratchet is satisfiable only by a project with zero skipped statements of its own. That is not a property any adopter can rely on, and the number of adopter statements the parser skips is not something the adopter chose.\n\n## Why the suggested remedies do not fit\n\nThe message names two, and the mismatch is that both address a *project* that grew a skipped class, not a *resync* that imported seven:\n\n- *Teach keel-parser the construct* — the 7 are the engine's own documented legacy successions in its own workflow files. An adopter cannot fix the engine's parser coverage as a precondition of adopting it.\n- *Raise the baseline in the same commit with the reason* — the file does not exist in the project until migrate writes it, and migrate writes `7`. To raise it the adopter would have to edit a file the resync just authored, inside a run that is atomic and reverts, then commit that edit as though the reason were theirs. The reason is not theirs; the 7 arrived with the engine.\n\n## Repro\n\n1. A project scaffolded from an older vintage, with at least one skipped statement in its own `.tracking/` files and no `.engine/contracts/parser-coverage-baseline.toml`.\n2. `keel gate guard parser-coverage` — passes with a warning naming the project's skipped statements.\n3. Commit or stash so `.tracking/` and `.engine/` are clean, then `keel migrate`.\n4. `parser-coverage` goes red at `project count + 7 > 7`, and the run rolls back.\n\nReproduced on `c592ef6+dirty`, `af5def6` and `ebac62f+dirty`; `.keel/update-attempts.toml` records reverts on 2026-09-08, 2026-09-14 and 2026-09-15.\n\n## Suggested fix\n\nOptions, roughly in order of how well each preserves what the ratchet is for:\n\n1. **Count and bound the two populations separately.** The engine's skipped statements are the engine's to ratchet down; the adopter's are the adopter's. One number over both means each side's number moves under the other.\n2. **Have the resync write the baseline at the observed post-write count**, with the reason stated in the file — the resync is the actor that made it necessary, which is exactly what the file's own instructions ask for, and it produces the visible diff the comment wants.\n3. **Scope the baseline to `.engine/` only**, and let a separate adopter-side baseline cover `.tracking/`.\n\nOption 1 or 2 keeps the control's intent, which is that new invisibility is loud. Option 3 is the smallest change but leaves adopter-side growth unbounded.\n";
        :>> saidBy = "williamweatherholtz"; :>> saidAt = "2026-09-18"; :>> channel = StatementChannel::github;
        :>> sourceUrl = "https://github.com/williamweatherholtz/keel/issues/90";
        :>> sourceTrust = SourceTrust::untrusted;
    }

    part st163 : Statement {
        :>> id = "801cee4b-9d00-40a8-936d-928b13d4be54";
        :>> title = "GH#89 [bug] activation-manifest resolves charteredBy against .engine/decisions/ but the resync deploys engine decisions to .engine/reference/decisions/ - migrate can never land downstream";
        :>> createdAt = "2026-09-18"; :>> createdBy = "claudeFable5";
        :>> text = "`activation-manifest` resolves `charteredBy` against `.engine/decisions/`, but the resync deploys engine decisions to `.engine/reference/decisions/`. In an adopting project the charter can therefore never resolve, and `keel migrate` reverts on its own output.\n\nSame class as #88: engine-shipped content validated against a path layout that only holds in this repository. Also blocks migrate, like #87.\n\n## What happens\n\n`keel migrate` in an adopting project writes 681 files, then its post-write gate fails and the whole run rolls back:\n\n```\nERROR activation.toml: charteredBy = ''d0226'' does not resolve - no\n      .engine/decisions/0226-*.sysml in this project, so the process set is\n      NOT chartered here (issue380/GH#56); re-run project-onboarding or\n      restore your own activation.toml\n[guard:activation-manifest] FAIL — 34 scanned, 0 warning(s), 1 violation(s)\nREVERTING: verified-green or byte-for-byte as before - there is no third state\nROLLED BACK: 681 written file(s) discarded\n```\n\nThe rollback is correct and clean. The problem is that the condition is unreachable by any action the adopting project can take.\n\n## Cause\n\n`charter_resolves` reads exactly one directory, with no recursion:\n\n`members/keel-model/src/onboard.rs:72`\n\n```rust\npub fn charter_resolves(root: &Path, charter: &str) -> bool {\n    let Some(num) = charter.strip_prefix('d').filter(|n| n.len() == 4 && n.chars().all(|c| c.is_ascii_digit())) else {\n        return false;\n    };\n    let prefix = format!(''{num}-'');\n    std::fs::read_dir(root.join(''.engine'').join(''decisions''))\n        .is_ok_and(|rd| rd.flatten().any(|e| e.file_name().to_string_lossy().starts_with(&prefix) && e.path().extension().is_some_and(|x| x == ''sysml'')))\n}\n```\n\nThe guard that calls it is at `members/keel-guards/src/enforcement.rs:1168`.\n\nBut the `engine-resync` step deploys engine decisions one level deeper. From `keel migrate --dry-run` in the adopting project:\n\n```\n.engine/reference/decisions/0226-keel-charters-its-own-process-set.sysml (1 edit(s))\n    add reference/decisions/0226-keel-charters-its-own-process-set.sysml\n```\n\nand it writes the manifest naming that decision:\n\n```\n.engine/contracts/activation.toml (1 edit(s))\n    add contracts/activation.toml\n```\n\nIn this repository the decisions live at `.engine/decisions/`, so the guard passes here and the mismatch is invisible upstream. In an adopting project `.engine/decisions/` holds *that project's own* decisions, so `read_dir` succeeds and finds no `0226-*.sysml`. The adopting project I hit this in has `0001`, `0002`, `0003` there, all its own.\n\n## Why the suggested remedies do not help\n\nThe error names two. Neither is reachable:\n\n- *Restore your own activation.toml from history* — the project has no `activation.toml` in history. Migrate is what creates it, as the dry-run shows (`add contracts/activation.toml`). There is nothing to restore.\n- *Re-run project-onboarding* — onboarding would have to write a `charteredBy` that resolves under the adopter's layout, which means writing a decision into `.engine/decisions/`. That is the project's own decision namespace, and `0226` would collide with or be mistaken for a project decision.\n\n## Repro\n\n1. Take a project scaffolded from an older engine vintage, with its own decisions in `.engine/decisions/` (mine holds `0001`–`0003`) and no `.engine/contracts/activation.toml`.\n2. Commit or stash so `.tracking/` and `.engine/` are clean.\n3. Run `keel migrate`.\n4. It writes, `activation-manifest` fails on the unresolvable charter, everything rolls back.\n\nReproduced three times, on three binaries: `c592ef6+dirty`, `af5def6`, `ebac62f+dirty`. Recorded in `.keel/update-attempts.toml` on 2026-09-08, 2026-09-14 and 2026-09-15, all `outcome = ''reverted''`, all `gate = ''guard''`.\n\n## Suggested fix\n\nResolve the charter wherever the resync actually puts engine decisions. Either search `.engine/reference/decisions/` in addition to `.engine/decisions/`, or have `charter_resolves` take the same path the resync writes to, so the two cannot drift again. A test that runs the guard against a *deployed* tree rather than this repository's tree would have caught it — the current `charter_must_resolve.rs` and `activation_round_trip_loses_nothing.rs` both exercise the authoring layout.\n\nWorth considering alongside #88, since the underlying defect is the same: a guard reading engine-shipped facts at authoring paths rather than deployed paths.\n";
        :>> saidBy = "williamweatherholtz"; :>> saidAt = "2026-09-18"; :>> channel = StatementChannel::github;
        :>> sourceUrl = "https://github.com/williamweatherholtz/keel/issues/89";
        :>> sourceTrust = SourceTrust::untrusted;
    }

    part st164 : Statement {
        :>> id = "ba5d754d-199d-4928-a3fb-e64b1d52b69c";
        :>> title = "GH#88 [control defect] guard:source-reference resolves ENGINE-shipped citations against the ADOPTER's workspace, so the resync can never pass downstream";
        :>> createdAt = "2026-09-18"; :>> createdBy = "claudeFable5";
        :>> text = "`guard:source-reference` (issue591) scans ENGINE-SHIPPED files and resolves their `file:line` citations against the ADOPTING project's workspace members. Those citations point at keel's own source, which no downstream project has, so the guard can never be satisfied there — and because `keel migrate` gates on the post-apply tree, it makes the engine resync permanently unreachable for any downstream project that happens to be a Rust workspace.\n\nBinary `keel 0.4.1`, build `0c131b7`. Observed on plotwright.\n\n## The two violations\n\n```\n$ keel gate guard source-reference .\nERROR .engine/processes/project-migration.sysml:15: cites `members/keel-process/src/migrate.rs:883-886`,\n      which resolves to no source file under a workspace member's src/ (issue591)\nERROR .engine/skills/project-migration/SKILL.md:10: cites `members/keel-process/src/migrate.rs:883-886`,\n      which resolves to no source file under a workspace member's src/ (issue591)\n[guard:source-reference] FAIL — 2 scanned, 0 warning(s), 2 violation(s)\n```\n\nBoth files are shipped by the engine. The citation in context is engine prose about the engine's own implementation:\n\n```\n// holding `keel-cli/Cargo.toml` as a self-build (migrate.rs:664-666), so THE ENGINE CANNOT MIGRATE\n```\n\n`members/keel-process/src/migrate.rs` is keel's workspace layout. The adopting project is a single `[package]` named `plotwright` with no `members/` directory and no `migrate.rs` — and should not have one. It is a murder-mystery plot tool.\n\n## Why it is invisible on a fresh tree\n\nA bare `keel init` passes, which is why this does not show up in the engine's own testing:\n\n```\n$ keel init . && keel gate guard source-reference .\n[guard:source-reference] PASS — 0 scanned, 0 warning(s), 0 violation(s)\n```\n\n**0 scanned.** The scaffold has no Cargo workspace, so the guard never activates. It only fires once the adopter is itself a Rust project — at which point it immediately fails on files the adopter did not write and cannot fix.\n\n## Why it is worse than a false positive\n\n`keel migrate` gates the post-apply tree and reverts on red (D0336). So:\n\n1. The resync rewrites `.engine/processes/project-migration.sysml` with the citation still in it — the engine ships it that way.\n2. The post-apply gate runs `source-reference`, which fails on that very file.\n3. 589 files roll back.\n\nThe adopter cannot fix it either, because `.engine` is the tool: any local edit is overwritten by the next resync, and the resync is the thing being blocked. On this project it is now the **last** blocker — every other post-apply failure has been worked through (untriaged auto-obligations, `sprint-closure`, and the project-owned `cli-reference` citations in `CLAUDE.md` and the two surviving contracts), and this is what remains.\n\n## Suggested fixes\n\n1. **Do not scan engine-shipped files for source citations at all.** `.engine/` prose describes the engine's implementation by construction; resolving it against the adopter's tree is a category error. Scan `.tracking/` and the project's own docs.\n2. Failing that, **resolve an `.engine/` citation against the engine's repo, not the adopter's**, or recognise a `members/…` prefix as engine-internal and skip it.\n3. Either way, the guard should distinguish ''cites a path in a tree it cannot see'' from ''cites a path that should exist here and does not''. Only the second is a defect in the project being gated.\n\nWorth noting the shape this shares with #68 and #87: three separate post-apply guards have now each independently made the resync unreachable, and in each case the failing condition was something the apply did not introduce and the adopter cannot remove. The pattern may be worth addressing directly — a post-apply gate that fails on anything other than a regression the apply caused will keep finding new ways to block.\n";
        :>> saidBy = "williamweatherholtz"; :>> saidAt = "2026-09-18"; :>> channel = StatementChannel::github;
        :>> sourceUrl = "https://github.com/williamweatherholtz/keel/issues/88";
        :>> sourceTrust = SourceTrust::untrusted;
    }

    part st165 : Statement {
        :>> id = "1866ba33-e516-4d8b-b402-c3eeb37d2e4d";
        :>> title = "GH#87 [bug] migrate is gated on the auto-obligation its own staleness produces, and the rollback DELETES that engine-authored record";
        :>> createdAt = "2026-09-18"; :>> createdBy = "claudeFable5";
        :>> text = "Two defects from one `keel migrate` run on plotwright, binary `keel 0.4.1` build `0c131b7`, project `.engine` at `b171cd7`. They compound: the first makes the resync unreachable in normal operation, and the second destroys evidence on the way out.\n\n## 1. The resync is gated on a condition the staleness itself keeps producing\n\nThe run rolled back with:\n\n```\nlast update attempt: 0.4.1 on 2026-09-18 REVERTED - guard failed:\n  ERROR obligation35c54864: untriaged — no #Resolves edge (D0077; link a resolving action or Decision)\n```\n\n`obligation35c54864` is not project content. It is an **engine-authored obligation** (D0176/K7), written automatically when the Stop hook's second red pass yields. Trace the cycle:\n\n1. `.engine` is stale, so `keel gate guard` is red (here: `cli-reference` 162, `cli-surface-declared` 133, `viewpoint-renderer` 14, `claude-surface-drift` 5).\n2. The turn gate cannot reach honest state, so the Stop hook yields and the engine records an obligation.\n3. A fresh obligation is untriaged by definition — nothing has resolved it yet.\n4. `keel migrate` gates on the post-apply tree, `guard:issues` fails on the untriaged obligation, and the whole resync reverts.\n5. `.engine` is still stale. Go to 1.\n\nSo the repair for the staleness is blocked by a record the staleness causes. On a project where an agent is working turn by turn, the window in which no untriaged obligation exists is a race — it lasts until the next red turn ends.\n\nThis is a distinct mechanism from #68 (ownership), and it bites *after* #68 is worked around. On this project both have now been hit in sequence: the first two attempts rolled back on `guard:ownership`, this one on an untriaged auto-obligation.\n\n**Suggested fix.** An engine-authored obligation should not gate the migration that would remove its cause. Either exclude auto-recorded obligations from the gate `migrate` runs, or — better — do not treat an obligation recorded *after* the pre-migrate baseline as a regression the apply introduced. The apply did not create it, and reverting 591 files cannot fix it.\n\nRelated: migrate already reasons about exactly these records on the way in, so the concept exists —\n\n```\ntolerated 1 uncommitted engine-authored obligation record(s) — additive, and\nseparable from migration state, so they do not make this tree ambiguous (issue324):\n  ?? .tracking/obligations/red-yield-35c54864.sysml\n```\n\nIt tolerates the record as separable at the start, then lets that same record fail the gate at the end. The two halves disagree.\n\n## 2. The rollback deletes the engine-authored obligation it declared separable\n\nWorse, and this is the part I would treat as the higher severity: **the file is gone.**\n\n```\n$ ls .tracking/obligations/\nred-yield-03358a97.sysml\nred-yield-f50f004c.sysml\n```\n\n`red-yield-35c54864.sysml` no longer exists, and `git status` does not list it as deleted because it was never committed. The rollback restored `.tracking/` wholesale to the pre-apply commit, which discarded an untracked file that migrate had, in its own words, just declared ''additive, and separable from migration state''.\n\nThe consequence is not cosmetic. The obligation was the record that a turn gate yielded while red — the engine's own audit trail of a control being bypassed, which D0176/K7 exists to capture precisely so it cannot be silent. The rollback erased it. `guard:issues` then reports PASS, and it reports PASS *because the evidence was destroyed*, not because anything was resolved.\n\nThere is also a self-defeating quality to it: the record whose untriaged state caused the revert was deleted by that same revert, so re-running migrate immediately afterwards would have succeeded — but only by having lost the fact.\n\n**Suggested fix.** If a file is separable enough to tolerate on the way in, it is separable enough to preserve on the way out. The rollback should restore only paths the apply actually wrote, rather than resetting `.tracking/` and `.engine/` to a commit; or it should stash and replace the tolerated records explicitly.\n\n## Why together\n\nEach alone is bad. Together they form a trap with a quiet exit: the migration fails because of a record, deletes that record, and reports a green `issues` guard afterwards. An operator who re-runs and succeeds would have no indication that a control-bypass record was silently dropped, and the `REVERTED` note in `keel show status` names the obligation by an id that no longer resolves to anything in the tree.\n";
        :>> saidBy = "williamweatherholtz"; :>> saidAt = "2026-09-18"; :>> channel = StatementChannel::github;
        :>> sourceUrl = "https://github.com/williamweatherholtz/keel/issues/87";
        :>> sourceTrust = SourceTrust::untrusted;
    }

    part st166 : Statement {
        :>> id = "dd9507cc-b286-4828-8d68-93c4250df50c";
        :>> title = "GH#86 [bug] record gate-result writes VerdictKind::proposed into a tree whose schema lacks it - the write API produces a file validate rejects, and it blocks all sprint ceremony";
        :>> createdAt = "2026-09-18"; :>> createdBy = "claudeFable5";
        :>> text = "`keel record gate-result` writes `VerdictKind::proposed` into a project whose `.engine/` schema does not declare that member, and `keel gate validate` then rejects the file the write API just produced. The write path is not vintage-aware: it emits values from the binary's own schema without checking what the project's engine copy can hold.\n\nBinary: `keel 0.4.1`, build `444333d`. Project `.engine/` vintage: build `b171cd7`.\n\n## Sequence\n\n```\n$ keel record gate-result --file .tracking/delivery/sprint4_...sysml /\n    --gate castPortsAndBeatNodesRefineGate --sha d80f13f --verdict pass /\n    --judged-by claudeOpus5 --judged-at 2026-09-18 --evidence-from refine-evidence.md\n143d24f9-0065-4fed-b113-27288ed89705\nnote: recorded proposed - an AI-judged pass on an examined method (demo/analyze/inspect) with no\n      replayable receipt is a proposal until a human judges it, and counts as done for nothing\n      meanwhile (D0312 B)\n```\n\nCorrect behaviour on its own terms — D0312 B downgrading an AI-judged `inspect` pass is the engine being right. Then:\n\n```\n$ keel gate validate .\nERROR: .tracking/delivery/sprint4_castPortsAndBeatNodes.sysml:28 — unknown member `proposed` in enum `VerdictKind`\n       hint: valid members: error, fail, inconclusive, pass\nERROR: .tracking/delivery/sprint4_castPortsAndBeatNodes.sysml:31 — unknown member `proposed` in enum `VerdictKind`\n       hint: valid members: error, fail, inconclusive, pass\n17 tracking file(s) validated — 0 parse error(s), 2 semantic diagnostic(s).\n```\n\nThe two schemas, same binary, different trees:\n\n```\n# this project, .engine at b171cd7\nenum def VerdictKind { pass; fail; inconclusive; error; }\n\n# tree freshly keel init-ed by 444333d\nenum def VerdictKind { pass; fail; inconclusive; error; proposed; }\n```\n\n## Why this is worse than an ordinary staleness symptom\n\nIt is not a stale *doc* or a stale command name. The write API actively produced an invalid tree, and it did so while reporting success. There is no verdict the operator chose here: `--verdict pass` was passed, the engine substituted `proposed` by policy, and the substituted value is one the project cannot represent.\n\n**It blocks all sprint ceremony.** Every autonomous gate in this project's sprint records is `method=inspect` or `method=analyze`, which is what D0017 and D0049 prescribe for them. So D0312 B applies to all of them, so every one of them writes `proposed`, so none can be recorded without failing validate. There is no way to run a sprint on this tree.\n\n**And the repair is the one that cannot run.** The fix is `keel migrate`, which on this project rolls back on `guard:ownership` (#68, where I added this project's occurrence). So a project can arrive at a state where the write API only emits invalid data and the only remedy is refused.\n\n## What I did locally, for the record\n\nAdded the single member to `.engine/schema/core/element.sysml`, matching byte-for-byte what the current engine ships:\n\n```\nenum def VerdictKind { pass; fail; inconclusive; error; proposed; }\n```\n\n`keel gate validate` then reports 17 files clean and `guard:ownership` passes. This is editing `.engine/`, which the project's own CLAUDE.md forbids, and it is a stopgap rather than a fix — the resync will make it redundant. I mention it because it is evidence that the gap is exactly one enum member, not a deep incompatibility.\n\n## Suggested fixes\n\n1. **Make the write path vintage-aware**: before emitting an enum value, check the project's schema declares it. If it does not, refuse with a message naming the member and the required engine version, rather than writing a file that will not validate. A refusal an operator can read beats a success they have to discover is a lie.\n2. **Degrade rather than break** where a policy substitution is involved: if D0312 B wants to downgrade a `pass` and the tree cannot hold `proposed`, that is a case for refusing the record and saying why, not for writing the unrepresentable value.\n3. More generally, this is an argument for the binary knowing the tree's vintage explicitly. #81 already notes that nothing is stamped and the vintage is inferred from content; a recorded engine version would let every write path make this check cheaply.\n";
        :>> saidBy = "williamweatherholtz"; :>> saidAt = "2026-09-18"; :>> channel = StatementChannel::github;
        :>> sourceUrl = "https://github.com/williamweatherholtz/keel/issues/86";
        :>> sourceTrust = SourceTrust::untrusted;
    }

    part st167 : Statement {
        :>> id = "f63d0c68-4701-486a-a526-b608a0634206";
        :>> title = "keel migrate is blocked in so many projects; migration should be smooth";
        :>> createdAt = "2026-09-18"; :>> createdBy = "claudeFable5";
        :>> text = "so many keep oprojects telling me keel migrate is blocked.  why?  migration should be smooth";
        :>> saidBy = "williamweatherholtz"; :>> saidAt = "2026-09-18"; :>> channel = StatementChannel::chat;
    }

    part st168 : Statement {
        :>> id = "6734d0cb-b6ee-41ed-84c8-1d4aa81d3fd5";
        :>> title = "Direction: make downstream projects whole";
        :>> createdAt = "2026-09-18"; :>> createdBy = "claudeFable5";
        :>> text = "continue, let's make downstream projects whole.";
        :>> saidBy = "williamweatherholtz"; :>> saidAt = "2026-09-18"; :>> channel = StatementChannel::chat;
    }

    part us118 : UserStory {
        :>> id = "77259c46-0be0-4d06-84d0-4cd0e34cae26";
        :>> title = "The resync never seeds a ratchet over the project's own corpus";
        :>> createdAt = "2026-09-18"; :>> createdBy = "claudeFable5";
        :>> asA = "keel adopter migrating for the first time";
        :>> iWant = "the resync to leave parser-coverage-baseline.toml absent when my project has none, so the count I adopt is one I measured";
        :>> soThat = "my first migration is not reverted by a ratchet describing a corpus that is not mine";
        :>> implication = ImplicationKind::bug;
        :>> triageNote = "Verified against this tree before triage, not taken from the report: migrate.rs step_engine_resync returns early only under is_project_owned_contract && dst.exists(), so a missing destination is planned from the shipped default, and .engine/contracts/parser-coverage-baseline.toml at HEAD carries skipped = 7 with a comment asking the number be adopted deliberately. The report is correct. Routed to issue610, resolved by dcRatchetOverTheProjectsCorpusIsNeverSeeded under D0520 (held, process-change); code authored by the peer session, verified and landed here.";
    }
    #DerivedFrom dependency from us118 to st162;

    part us119 : UserStory {
        :>> id = "5ba960df-62f9-437d-9a3a-9e8fbdbc2217";
        :>> title = "A shipped charter resolves where the resync deploys it";
        :>> createdAt = "2026-09-18"; :>> createdBy = "claudeFable5";
        :>> asA = "keel adopter whose .engine came from a resync";
        :>> iWant = "the activation manifest's charteredBy to resolve against .engine/reference/decisions/ as well as .engine/decisions/";
        :>> soThat = "the shipped charter is not red in every adopting tree";
        :>> implication = ImplicationKind::bug;
        :>> triageNote = "Verified against this tree before triage: onboard.rs:72 at HEAD joins .engine/decisions only, and a migrate dry run plans reference/decisions/0226-*.sysml, so the shipped charter lands where the resolver never looks. The report is correct; the two integration tests that should have caught it exercise the authoring layout only. Routed to issue611, resolved by dcCharterResolvesInBothDecisionDirectories under D0520 (held); code authored by the peer session, verified and landed here.";
    }
    #DerivedFrom dependency from us119 to st163;

    part us120 : UserStory {
        :>> id = "bd7058c1-c228-4628-924c-165e7e5f4efe";
        :>> title = "source-reference holds me to my own citations, not the engine's";
        :>> createdAt = "2026-09-18"; :>> createdBy = "claudeFable5";
        :>> asA = "keel adopter with a Rust workspace";
        :>> iWant = "guard source-reference to set aside living docs the engine shipped and read only the citations my project authored";
        :>> soThat = "a shipped doc citing keel's own source cannot red my tree, and my own stale citations still can";
        :>> implication = ImplicationKind::bug;
        :>> triageNote = "Verified against this tree before triage: surface.rs:228 is the guard only scope test and living_doc_files (:485) walks all of .engine/; the two cited docs are shipped by the embedded engine. The reporter is right that the scaffold 0 scanned is comfort rather than a pass, and right that the guard is doing its job on this repository - it went red on all three citations when the GH#90 diff moved check_preconditions by 25 lines. Routed to issue612, resolved by dcSourceReferenceReadsTheAdoptersOwnClaims under D0520 (held): shipped docs are outside the population in a non-self-build root.";
    }
    #DerivedFrom dependency from us120 to st164;

    part us121 : UserStory {
        :>> id = "4429aa63-0d44-4e61-9fba-cca13dc8bc30";
        :>> title = "A record migrate tolerates at the door survives the run";
        :>> createdAt = "2026-09-18"; :>> createdBy = "claudeFable5";
        :>> asA = "keel adopter whose agent yields red turns";
        :>> iWant = "an engine-authored obligation migrate tolerated as separable to neither fail the post-apply gate nor be deleted by the rollback";
        :>> soThat = "the migration that cures the staleness is not blocked by a record the staleness produced, and the K7 audit trail survives";
        :>> implication = ImplicationKind::bug;
        :>> triageNote = "Verified against this tree before triage: is_tolerable_obligation tolerates the record at the door, project_gate runs gate guard all whole, and restore runs git clean -fdq -- .tracking (migrate.rs:997 at HEAD), which deletes an untracked file. Both halves of the report are correct and the second is the graver: the K7 record was destroyed and the guard then passed for that reason. Of the two suggested fixes the narrow one is taken (discount violations naming a tolerated record; exclude tolerated paths from clean); judging only regressions against a pre-apply baseline would mask every pre-existing red under a stale engine. Routed to issue613, resolved by dcToleratedRecordsSurviveTheRun under D0522 (held).";
    }
    #DerivedFrom dependency from us121 to st165;

    part us122 : UserStory {
        :>> id = "e5269b83-f46f-4996-8ca9-da69a08d21e7";
        :>> title = "A write refuses a verdict member my tree's schema lacks";
        :>> createdAt = "2026-09-18"; :>> createdBy = "claudeFable5";
        :>> asA = "keel adopter running a newer binary than my .engine";
        :>> iWant = "record gate-result to refuse, naming the member and keel migrate, rather than write VerdictKind::proposed into a tree whose schema does not declare it";
        :>> soThat = "record never leaves my tree invalid and reporting success";
        :>> implication = ImplicationKind::bug;
        :>> triageNote = "Verified against this tree before triage: write.rs:625 proposed_tier returns the binary constant with no read of the tree schema; element.sysml:27 gained proposed at 24dbcfb3 on 2026-09-10 and tag v0.4.1 is b171cd7f of 2026-09-06, so a release-scaffolded tree lacks the member. The report is correct. Writing pass instead would fabricate the tier D0312 B exists to prevent, so the fix is a refusal that names the vintage and keel migrate; with D0520/D0522 landed that migrate succeeds. Routed to issue614, resolved by dcAWriteRefusesTheMemberTheTreesSchemaLacks under D0521 (held).";
    }
    #DerivedFrom dependency from us122 to st166;
    // Routing (github-intake step 3; D0264 untrusted: every routed story names a Decision among its
    // targets). D0520-D0522 are held for the human; the human direction is st167/st168.
    #Implicates dependency from us118 to issue610;
    #Implicates dependency from us118 to d0520;
    #Implicates dependency from us119 to issue611;
    #Implicates dependency from us119 to d0520;
    #Implicates dependency from us120 to issue612;
    #Implicates dependency from us120 to d0520;
    #Implicates dependency from us121 to issue613;
    #Implicates dependency from us121 to d0522;
    #Implicates dependency from us122 to issue614;
    #Implicates dependency from us122 to d0521;

}
