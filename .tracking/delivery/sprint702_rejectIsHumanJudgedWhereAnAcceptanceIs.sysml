// ProjectDeliveryS702 — Sprint 702: Resolve issue526 (High) through dcRejectIsHumanJudgedAtTheWriteAndTheRule: keel reject refuses an AI-kind or unregistered judge at every layer keel accept does - inside the write lock (refuse_ai_judgment in reject_decision_locked), in HUMAN_ONLY_WRITE_COMMANDS and HUMAN_AUTHORITY_COMMANDS, and in a rejectionAuthenticityRule the confirmation-authenticity guard reads beside the accepted one. CHANGE (CR): the rule and the command lists are process surfaces, so the change rides a co-committed safety-change Decision (D0209 cl.2), held proposed for the human. 2 pts.. EXECUTE. 2 pts.
package ProjectDeliveryS702 {
    private import EngineElement::*;
    private import EngineWork::*;
    private import EngineVerification::*;
    private import EngineRelationships::*;

    #CharteredBy dependency from rejectIsHumanJudgedWhereAnAcceptanceIsStory to d0470;

    part rejectIsHumanJudgedWhereAnAcceptanceIsStory : Story {
        :>> id = "201030ca-19fe-49e6-ab94-8088e5628b32";
        :>> title = "Sprint 702: Resolve issue526 (High) through dcRejectIsHumanJudgedAtTheWriteAndTheRule: keel reject refuses an AI-kind or unregistered judge at every layer keel accept does - inside the write lock (refuse_ai_judgment in reject_decision_locked), in HUMAN_ONLY_WRITE_COMMANDS and HUMAN_AUTHORITY_COMMANDS, and in a rejectionAuthenticityRule the confirmation-authenticity guard reads beside the accepted one. CHANGE (CR): the rule and the command lists are process surfaces, so the change rides a co-committed safety-change Decision (D0209 cl.2), held proposed for the human. 2 pts. (2 pts)";
        :>> createdAt = "2026-09-13"; :>> createdBy = "claudeFable5"; :>> kind = WorkKind::code; :>> priority = WorkPriority::p0; :>> owner = "claudeFable5"; :>> estimatedPoints = 2;
    }

    action def DeliveryRunS702 {
        action storyRejectIsHumanJudgedWhereAnAcceptanceIs;
        verification storyRejectIsHumanJudgedWhereAnAcceptanceIsDoD : Test { :>> id = "f5005808-d55d-41a4-8770-eec8e72d0f8f"; :>> method = VerificationMethod::test; :>> procedureText = "DELIVERED: (a) keel-cli/src/write.rs: reject_decision_locked calls refuse_ai_judgment(path, judged_by, 'rejecting a Decision') before reading the file; HUMAN_ONLY_WRITE_COMMANDS = [accept, reject, judge-set]; test reject_decision_refuses_ai_and_unregistered_judges (AI refused naming 'AI actor', unregistered refused, file byte-for-byte unchanged after both, a Person rejects and the file carries DecisionStatus::rejected and d2RejectR1). (b) keel-cli/src/view/control_structure.rs: HUMAN_AUTHORITY_COMMANDS = [accept, reject, judge-set]; the existing human_authority_commands_refuse_an_ai_actor test holds the two lists equal. (c) keel-cli/src/guards.rs: confirmation_authenticity iterates (confirmationAuthenticityRule, accepted, acceptance) and (rejectionAuthenticityRule, rejected, rejection), summing scanned and naming the verdict in each violation. (d) .engine/rules/rules.sysml: rejectionAuthenticityRule - subjectType Decision, predicate resultJudgedByHuman(Reject), appliesWhen whereStatus(rejected), blocking/block - with #JustifiedBy to the governing Decision. VERIFY (probe pair, D0388): known positive - the refuse_ai_judgment line in reject_decision_locked removed, the new test FAILS at 'an AI-kind judge must be refused'; known negative - the real tree, the test passes and accept_decision_refuses_ai_and_unregistered_judges and human_authority_commands_refuse_an_ai_actor still pass; clippy clean; gate guard --no-receipt names confirmation-authenticity PASS with the rule present (no NOT ADOPTED warning for rejectionAuthenticityRule)."; }
        // RAN: KEEL suite --touched: pass - 809 passed, 0 failed in 1128s; failing []; receipt .keel/metrics/touched-receipt.toml
        part storyRejectIsHumanJudgedWhereAnAcceptanceIsDoDR1 : TestResult { :>> id = "d77f8940-0d20-419b-8d5a-196d952aaaab"; :>> outcome = VerdictKind::pass; :>> judgedAgainst = "2a6abdc"; :>> judgedAt = "2026-09-13"; :>> judgedBy = "claudeFable5"; }
    }

    verification rejectIsHumanJudgedWhereAnAcceptanceIsRefineGate : Test { :>> id = "eae82b81-055b-43d8-986e-067db65c1f6f"; :>> title = "Sprint 702 refine gate (DoR)"; :>> createdAt = "2026-09-13"; :>> createdBy = "claudeFable5"; :>> method = VerificationMethod::inspect; :>> procedureText = "Chartered by issue526's governing Decision (this sprint's co-committed safety-change, proposed): an AI actor could record a human's rejection with nothing refusing it at the write, in the command lists or in the rule, while the reject command's synopsis claimed accept's channel rules. Two points: one call inside the lock, two list entries, one guard loop, one rule, one test. DoR: dcRejectIsHumanJudgedAtTheWriteAndTheRule ranks second on keel show whats-next after sprint 701's reorder placed it in the High band (D0052); the pair is the DoD's own, named before the patch was applied; the two rejected Decisions in the tree (d0376, d0463, grep DecisionStatus::rejected over .engine/decisions) each carry a RejectR1 judged by the human, so the new blocking rule evaluates over two subjects with zero violators and needs no backfill (migration skill gate 4 not engaged); the draft first claimed zero rejected Decisions from a grep over .tracking alone - the rule's own scanned count (keel gate rules: evaluated, 0 violations; guard confirmation-authenticity 460 = 458 accepted + 2 rejected) corrected it before commit."; }
    // RAN: KEEL gate validate . -> 805 tracking file(s) validated clean.; exit=0
    part rejectIsHumanJudgedWhereAnAcceptanceIsRefineGateR1 : TestResult { :>> id = "2c8e3acf-5c93-4d81-9c88-896b9ca22ffd"; :>> outcome = VerdictKind::proposed; :>> judgedAgainst = "2a6abdc"; :>> judgedAt = "2026-09-13"; :>> judgedBy = "claudeFable5"; }
    verification rejectIsHumanJudgedWhereAnAcceptanceIsStandupGate : Test { :>> id = "fbf65f49-d7c1-4d48-a766-d2be80426088"; :>> title = "Sprint 702 standup gate"; :>> createdAt = "2026-09-13"; :>> createdBy = "claudeFable5"; :>> method = VerificationMethod::inspect; :>> procedureText = "Order: wait for sprint 701's land to exit (no keel-cli/src or .engine edit while cargo runs, issue477); record the Decision from its draft (marker safety-change -> HELD proposed, D0337); apply patch_reject.py by path with the Decision id so the rule's #JustifiedBy names it; run the three named tests; run the D0388 pair by removing and restoring the refuse line; clippy; release build; copy to keel-serve.exe; gate validate, check-engine, guard --no-receipt (process-change guard sees the marker Decision in the diff); sprint record chartered by the Decision; verifier and recorder by agent type; commit CR: detached; read the CI conclusion back."; }
    // RAN: KEEL gate validate . -> 805 tracking file(s) validated clean.; exit=0
    part rejectIsHumanJudgedWhereAnAcceptanceIsStandupGateR1 : TestResult { :>> id = "0dcab9a5-3b61-4921-800d-2018257c2ff2"; :>> outcome = VerdictKind::proposed; :>> judgedAgainst = "2a6abdc"; :>> judgedAt = "2026-09-13"; :>> judgedBy = "claudeFable5"; }
    verification rejectIsHumanJudgedWhereAnAcceptanceIsImplementGate : Test { :>> id = "edd583a0-9717-4ff5-850f-ded262de003a"; :>> title = "Sprint 702 implement gate"; :>> createdAt = "2026-09-13"; :>> createdBy = "claudeFable5"; :>> method = VerificationMethod::test; :>> procedureText = "RAN: see the verifier's receipt for cargo test --release -p keel-cli --lib -- reject_decision_refuses accept_decision_refuses human_authority_commands, the probe pair, clippy and the gate set. Applied: python patch_reject.py <decision> -> patched write.rs, control_structure.rs, guards.rs, rules.sysml (every anchor asserted once)."; }
    // RAN: KEEL gate validate . -> 805 tracking file(s) validated clean.; exit=0
    part rejectIsHumanJudgedWhereAnAcceptanceIsImplementGateR1 : TestResult { :>> id = "7b402117-cae9-48e9-b085-fc251907d5ed"; :>> outcome = VerdictKind::pass; :>> judgedAgainst = "2a6abdc"; :>> judgedAt = "2026-09-13"; :>> judgedBy = "claudeFable5"; }
    verification rejectIsHumanJudgedWhereAnAcceptanceIsReviewGate : Test { :>> id = "be9a3705-5427-4137-b08b-92c39c1ea250"; :>> title = "Sprint 702 review gate — three passes per D0172"; :>> createdAt = "2026-09-13"; :>> createdBy = "claudeFable5"; :>> method = VerificationMethod::inspect; :>> procedureText = "Three passes (D0172). Correctness: refuse_ai_judgment is the same function accept, judge-set, rebind and confirmation results call, with the same short-circuit outside a model tree (unit-test scratch) and the same actors.sysml presence test - so reject gains exactly accept's guarantee, no more and no less; the call precedes the read so a refused rejection touches nothing. The rule predicate resultJudgedByHuman(suffix) resolves {name}{suffix}R1 and reject_decision writes {decision}RejectR1, so the rule reads the event the write produces. Honesty: the guard keeps its name confirmation-authenticity and adds the rejected branch under it rather than a new guard, because the control is one claim (a human verdict is human-judged) over two statuses; an absent rejectionAuthenticityRule warns NOT ADOPTED like the accepted one does, never silently passes. Scope: the serve endpoint (serve.rs:941) already required a registered Person at the transport layer; it now also meets the write-layer refusal, which is the layer that binds regardless of caller. The command-layer channel refusals (verdict_channel_refusal) are unchanged."; }
    // RAN: KEEL gate validate . -> 805 tracking file(s) validated clean.; exit=0
    part rejectIsHumanJudgedWhereAnAcceptanceIsReviewGateR1 : TestResult { :>> id = "136d3416-22e9-49be-9062-cb7dbb5cae65"; :>> outcome = VerdictKind::proposed; :>> judgedAgainst = "2a6abdc"; :>> judgedAt = "2026-09-13"; :>> judgedBy = "claudeFable5"; }
    verification rejectIsHumanJudgedWhereAnAcceptanceIsCloseOutGate : Test { :>> id = "2bf6d191-5262-4c9f-9ee1-6878ace3d2cc"; :>> title = "Sprint 702 closeOut gate (autonomous, D0049)"; :>> createdAt = "2026-09-13"; :>> createdBy = "claudeFable5"; :>> method = VerificationMethod::inspect; :>> procedureText = "Closes at the CR: commit that lands write.rs, control_structure.rs, guards.rs, rules.sysml and the marker Decision together: gate validate / check-engine / guard --no-receipt green over that tree; dcRejectIsHumanJudgedAtTheWriteAndTheRuleDoD carries a pass with the RAN receipt; issue526 is resolved by that pass; the Decision stays proposed until the human's word; the CI conclusion for the landing commit is read back as success."; }
    // RAN: KEEL gate validate . -> 805 tracking file(s) validated clean.; exit=0
    part rejectIsHumanJudgedWhereAnAcceptanceIsCloseOutGateR1 : TestResult { :>> id = "2de701c6-5891-4ba0-9ea3-3a9d3a6902d6"; :>> outcome = VerdictKind::proposed; :>> judgedAgainst = "2a6abdc"; :>> judgedAt = "2026-09-13"; :>> judgedBy = "claudeFable5"; }
    verification rejectIsHumanJudgedWhereAnAcceptanceIsRetroGate : Test { :>> id = "36d322ec-8668-4f11-9340-a01f7362276f"; :>> title = "Sprint 702 retro gate (autonomous, D0049)"; :>> createdAt = "2026-09-13"; :>> createdBy = "claudeFable5"; :>> method = VerificationMethod::analyze; :>> procedureText = "Finding: the control_structure test human_authority_commands_refuse_an_ai_actor holds every listed command to the write layer, but a command listed in neither list is invisible to it - issue526 sat there for five days. The structural fix is a test in the other direction: every CliCommand whose synopsis or family claims the human's verdict (accept, reject, judge-set today) must appear in HUMAN_AUTHORITY_COMMANDS; that is a claim about the CLI facts (D0271) held to code, the same shape as the write-path registry. Tracked as issue529 (resolver dcVerdictCommandsAreReadBackIntoTheAuthorityLists, Medium band), not fixed here (one clause per sprint, D0303). D0131 avoidable-issue scan: issue526 was avoidable at D0393 by reading reject's write path when its synopsis was given accept's words; no further item. Second finding: the refine text and D0470's context first said no Decision had ever been rejected, from a grep over .tracking when Decisions live in .engine/decisions; the rule this sprint adds scanned two (d0376, d0463) and so falsified the claim before commit. No item: no automated control reads a prose count, and the correction is D0151's - the check (here, the rule's scanned count) runs before the claim is written. Third finding: the VERIFIER's receipt read the touched run as MISMATCH because the test-verify skill's stems row (SKILL.md:126) predates the embedded init stem (touched.rs:16) that every changed .engine path contributes - a correct receipt over this sprint's rules.sysml change reported as dishonest. Tracked as issue530 (resolver dcTouchedReceiptStatesItsOwnAttribution, Medium band): the receipt states its own attribution so the reader compares against the receipt, not a re-derived rule."; }
    // RAN: KEEL gate validate . -> 805 tracking file(s) validated clean.; exit=0
    part rejectIsHumanJudgedWhereAnAcceptanceIsRetroGateR1 : TestResult { :>> id = "9559d22b-8fbe-4eef-82fd-89ef6395e6a1"; :>> outcome = VerdictKind::proposed; :>> judgedAgainst = "2a6abdc"; :>> judgedAt = "2026-09-13"; :>> judgedBy = "claudeFable5"; }
}
