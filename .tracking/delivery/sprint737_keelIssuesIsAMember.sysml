// ProjectDeliveryS737 — Sprint 737: the item and issue processes are a member - dcKeelIssuesIsAMember, the seventh D0479 extraction, chartered by D0480. github_ingest.rs leaves keel-cli/src and intake_write.rs leaves members/keel-write/src for members/keel-issues/src; the issue write (NewIssue, next_issue_number, record_issue, its test) is sliced out of write.rs into issue_write.rs and the open-issues, dispositions and intake views out of keel-view's view/mod.rs and view/staleness.rs into views.rs. Two descents make the member possible without a guard or a view in its dependency tree: the resolver predicate (declared_task_names, resolver_kind_holds) leaves keel-guards for keel_model::resolvers with re-exports at the old paths, and at_least_medium leaves keel-view for keel_model::queries. The severity and resolver checks that sat inline in main.rs become issue_write::triage_holds with the refusal text unchanged. keel-cli's lib.rs keeps every old path - view and write become wrapper modules that glob the member's module and add the sliced names - so no caller moved. D0508 (marked process-change, HELD) records the layering and reverses D0480's synopsis clause: the module home is computed, keel --help stays byte-identical.. EXECUTE. 8 pts.
package ProjectDeliveryS737 {
    private import EngineElement::*;
    private import EngineWork::*;
    private import EngineVerification::*;
    private import EngineRelationships::*;

    #CharteredBy dependency from keelIssuesIsAMemberStory to d0480;

    part keelIssuesIsAMemberStory : Story {
        :>> id = "c42524d3-ceca-41c1-bfeb-b703fa1be5a7";
        :>> title = "Sprint 737: the item and issue processes are a member - dcKeelIssuesIsAMember, the seventh D0479 extraction, chartered by D0480. github_ingest.rs leaves keel-cli/src and intake_write.rs leaves members/keel-write/src for members/keel-issues/src; the issue write (NewIssue, next_issue_number, record_issue, its test) is sliced out of write.rs into issue_write.rs and the open-issues, dispositions and intake views out of keel-view's view/mod.rs and view/staleness.rs into views.rs. Two descents make the member possible without a guard or a view in its dependency tree: the resolver predicate (declared_task_names, resolver_kind_holds) leaves keel-guards for keel_model::resolvers with re-exports at the old paths, and at_least_medium leaves keel-view for keel_model::queries. The severity and resolver checks that sat inline in main.rs become issue_write::triage_holds with the refusal text unchanged. keel-cli's lib.rs keeps every old path - view and write become wrapper modules that glob the member's module and add the sliced names - so no caller moved. D0508 (marked process-change, HELD) records the layering and reverses D0480's synopsis clause: the module home is computed, keel --help stays byte-identical. (8 pts)";
        :>> createdAt = "2026-09-17"; :>> createdBy = "claudeFable5"; :>> kind = WorkKind::code; :>> priority = WorkPriority::p0; :>> owner = "claudeFable5"; :>> estimatedPoints = 8;
    }

    action def DeliveryRunS737 {
        action storyKeelIssuesIsAMember;
        verification storyKeelIssuesIsAMemberDoD : Test { :>> id = "c95c3a23-c90d-467d-a225-66ee3f56fe67"; :>> method = VerificationMethod::test; :>> procedureText = "DELIVERED BACKLOG ITEMS: dcKeelIssuesIsAMember. DONE MEANS: members/keel-issues holds github_ingest.rs, intake_write.rs, issue_write.rs and views.rs under the member lint preamble, with a Cargo.toml naming keel-json, keel-schema, keel-model, keel-write and serde_json and no build.rs; keel-cli/src holds no github_ingest.rs, keel-write holds no intake_write.rs and no NewIssue/record_issue, keel-view holds no open_issues/dispositions/intake/at_least_medium; members/keel-model/src/resolvers.rs holds declared_task_names and resolver_kind_holds and keel-guards' lib.rs and issues.rs re-export them; keel-cli's lib.rs re-exports github_ingest, intake_write, the view and write wrapper modules and `issues`; main.rs's cmd_record_issue calls keel_cli::issues::issue_write::triage_holds and its two inline check blocks are gone; the root manifest lists members/keel-issues before keel-cli and keel-cli's manifest depends on it; scripts/extract_issues.py is the idempotent transform (dry-run default; 2 files moved with 14 crate:: references each kept or rewritten, 8 anchored slices conserved, 15 anchored edits in 12 staying files, 5 files written; re-run says already applied); cargo clippy --release --workspace --all-targets -D warnings clean; keel --help byte-identical to the pre-move render (cmp help_before737.txt help_after737.txt, 15089 bytes) and keel version's guard line unchanged (75: 66 hard-blocking, 9 warning-only); python scripts/modgraph.py --check and python scripts/module_home.py --probe hold. Known-positive, chosen before the tree is read (the DoD's own words): cargo tree -p keel-issues names no keel-process, keel-view, keel-guards or keel-suite and the member's code never names serve; touching members/keel-process/src/process_cmd.rs leaves keel-issues Fresh under cargo build --release --verbose while keel-process and keel-cli recompile; record_issue_refuses_a_non_resolver (2), federation (11, f7 is the GitHub ingest) and the member's 10 unit tests pass (pos737.py). Known-negative: a pub use keel_process::process_cmd planted in the member's lib.rs fails cargo check -p keel-issues naming the undeclared crate keel_process, lib.rs restored bytes and mtime on every path (neg737.py). The DoD's prose and its probe do not both hold at three points, and the probe is the contract (sprints 734-736): (1) 'depending on keel-view and below' - the member depends on keel-model and keel-write, not keel-view, because a dependency on keel-view is a dependency on every governance view and the Fresh probe would fail on an edit to view/mod.rs; (2) plan_cover and the resolution computation stay where their readers are (plan_cover is Decision acceptance in keel-guards; compute_issue_resolution is read by orient and the guards in keel-model); (3) 'the record verbs' CLI facts name the member in their synopsis' contradicts 'keel --help byte-identical' in the same DoD - help wins, D0508 reverses the D0480 clause with #SupersedeClause, and the module home stays computed (scripts/module_home.py, D0105). cli-surface-declared passes unchanged."; }
        // RAN: outcome=pass stopped_at=none
        part storyKeelIssuesIsAMemberDoDR1 : TestResult { :>> id = "7897e0c2-aa90-4f2c-aa4f-0cb7f4f29070"; :>> outcome = VerdictKind::pass; :>> judgedAgainst = "9e4e79c6"; :>> judgedAt = "2026-09-17"; :>> judgedBy = "claudeFable5"; }
    }

    verification keelIssuesIsAMemberRefineGate : Test { :>> id = "59d44b18-77de-4dfd-8d75-aa4a9e4dd218"; :>> title = "Sprint 737 refine gate (DoR)"; :>> createdAt = "2026-09-17"; :>> createdBy = "claudeFable5"; :>> method = VerificationMethod::inspect; :>> procedureText = "DoR: dcKeelIssuesIsAMember is the first line of keel show whats-next at 9e4e79c6 (sprint 736 landed, CI conclusion success). Chartered by D0480 (accepted) through its #CharteredBy edge; #DependsOn dcViewIsAMember, done. Sized 8 - two files moved with a codemod, eight anchored slices across five staying files (write.rs, view/mod.rs, view/staleness.rs, keel-guards lib.rs and issues.rs), two descents into keel-model, one new type (TriageRefusal) carrying the main.rs refusal text verbatim, two wrapper modules in keel-cli's lib.rs, one new member manifest, the D0388 pair as two scripts, and a marked Decision with a clause reversal. Not split: sprint-planning permits 8 and a split would land a member that owns half its processes. Two locked-path edits (members/keel-guards/src/lib.rs, issues.rs: each a slice replaced by a re-export of the same function) require the marked Decision D0508, HELD for the human; the sprint is not blocked on it - the code is the same predicate at a new home and the brief carries the question. Blocking dependencies: none."; }
    // RAN: outcome=pass stopped_at=none
    part keelIssuesIsAMemberRefineGateR1 : TestResult { :>> id = "29efb660-ae2f-451d-ab1d-bc5f765e7a29"; :>> outcome = VerdictKind::proposed; :>> judgedAgainst = "9e4e79c6"; :>> judgedAt = "2026-09-17"; :>> judgedBy = "claudeFable5"; }
    verification keelIssuesIsAMemberStandupGate : Test { :>> id = "cc961e8e-47db-4836-8634-ebbf683051e8"; :>> title = "Sprint 737 standup gate"; :>> createdAt = "2026-09-17"; :>> createdBy = "claudeFable5"; :>> method = VerificationMethod::inspect; :>> procedureText = "Owner claudeFable5. Blocker: none - 9e4e79c6 landed with CI success, no ladder or land is running. Order: (1) scripts/extract_issues.py: git mv the two files, rewrite crate:: paths through MODULE_MAP, slice the issue write, the three views, at_least_medium and the two guard predicates, write the member's Cargo.toml, lib.rs, views.rs and issue_write.rs (with TriageRefusal/triage_holds appended) and keel-model's resolvers.rs, edit the manifests, keel-cli's lib.rs wrappers, main.rs's two blocks, write.rs's reject_injected_output to pub, the import lines; dry-run reconciled, then --apply. (2) cargo build --release, clippy --workspace --all-targets, keel --help against help_before737.txt, keel version, cargo test on keel-issues, keel-model resolvers/queries, record_issue_refuses_a_non_resolver, federation, prose_flags_read_a_file, untrusted_taint; the three views render. (3) pos737/neg737; pair737.txt; modgraph --check; module_home --probe. (4) doc-sync (no living doc names the moved paths or a member list - the home is manifest-driven), sync-claude --check. (5) D0508 (marker process-change, --supersedes-clause d0480, HELD), the sprint with the retro filled, brief 43 through decision-surfacing (pending set changes); verifier with the pair file; recorder --owed 7; land; CI conclusion."; }
    // RAN: outcome=pass stopped_at=none
    part keelIssuesIsAMemberStandupGateR1 : TestResult { :>> id = "8ac8bcb6-fb4b-49f1-b64d-6dabcc43d379"; :>> outcome = VerdictKind::proposed; :>> judgedAgainst = "9e4e79c6"; :>> judgedAt = "2026-09-17"; :>> judgedBy = "claudeFable5"; }
    verification keelIssuesIsAMemberImplementGate : Test { :>> id = "bc6527cd-93f5-4a43-9825-f0bc5bbaedd4"; :>> title = "Sprint 737 implement gate"; :>> createdAt = "2026-09-17"; :>> createdBy = "claudeFable5"; :>> method = VerificationMethod::test; :>> procedureText = "The implement gate is the DoD's own probes plus the ladder: cargo build --release clean after two one-shot fixes the codemod now carries (the descended at_least_medium was sliced as a private fn and is published `#[must_use] pub`; views.rs's head imported HashSet that intake names fully qualified); cargo clippy --release --workspace --all-targets -- -D warnings Finished clean after two doc backticks in the member's lib.rs (template patched too); cmp help_before737.txt help_after737.txt byte-identical (15089 bytes); keel version guards line 75 (66 hard-blocking, 9 warning-only); cargo tree -p keel-issues: keel-json, keel-model, keel-schema, keel-write, serde_json, zero matches for keel-process/view/guards/suite; cargo test --release -p keel-issues 10 passed; -p keel-model --lib resolvers queries 7 passed; --test record_issue_refuses_a_non_resolver 2 passed; --test federation 11 passed; --test prose_flags_read_a_file 3 passed; --test untrusted_taint 2 passed; keel show open-issues/dispositions/intake render through the wrapper; python pos737.py PASS (after its serve check was narrowed to code lines - the member's own doc comment names serve.rs as what it does not depend on); python neg737.py PASS (cargo check rc 101 naming keel_process, lib.rs restored); python scripts/extract_issues.py re-run: already applied; python scripts/modgraph.py --check exit 0 (71 modules, 50 edges); python scripts/module_home.py --probe 0 failures; keel gate validate 852 clean; keel gate check-engine clean with D0508 in the tree."; }
    // RAN: outcome=pass stopped_at=none
    part keelIssuesIsAMemberImplementGateR1 : TestResult { :>> id = "4a132062-8c05-43c6-a683-2aed590f91bb"; :>> outcome = VerdictKind::pass; :>> judgedAgainst = "9e4e79c6"; :>> judgedAt = "2026-09-17"; :>> judgedBy = "claudeFable5"; }
    verification keelIssuesIsAMemberReviewGate : Test { :>> id = "a6f390e8-707f-491d-93af-a46bd8942412"; :>> title = "Sprint 737 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every moved test passes in its new crate (10 in keel-issues, the resolvers/queries tests in keel-model), every caller of the moved names resolves through a re-export or a wrapper module (main.rs, serve.rs, deck.rs, the tests - zero caller edits beyond cmd_record_issue's two blocks), the refusal text record_issue_refuses_a_non_resolver asserts is byte-equal through TriageRefusal's Display, and the binary's help and guard count are the pre-move ones. Honesty: the negative plants in the MEMBER's lib.rs and asserts the compiler names the crate the member must not know, not merely that the build fails; the positive touches a governance file and reads Fresh from cargo's own verbose line, and checks the dependency tree by cargo tree rather than by reading manifests. Scope: two locked-path files are in the diff (members/keel-guards/src/lib.rs and issues.rs - each a slice replaced by a re-export of the identical function now in keel-model), so D0508 carries the process-change marker and is co-committed HELD (D0209 cl.2); the process-change guard reads it. No .engine/processes, skills, hooks or CI yml edit."; }
    // RAN: outcome=pass stopped_at=none
    part keelIssuesIsAMemberReviewGateR1 : TestResult { :>> id = "8532052d-e2c1-4a16-b81e-3010acff2831"; :>> outcome = VerdictKind::proposed; :>> judgedAgainst = "9e4e79c6"; :>> judgedAt = "2026-09-17"; :>> judgedBy = "claudeFable5"; }
    verification keelIssuesIsAMemberCloseOutGate : Test { :>> id = "398eb750-6510-4236-b5d6-3d82172c20f3"; :>> title = "Sprint 737 closeOut gate (autonomous, D0049)"; :>> createdAt = "2026-09-17"; :>> createdBy = "claudeFable5"; :>> method = VerificationMethod::inspect; :>> procedureText = "Landed when the verifier's receipt reads DISCREPANCIES: NONE and its probe rung row names pair737.txt, the recorder's report passes check_report.py --owed 7, git status -sb is clean after keel land and gh run list names the landing commit with conclusion success. The DoD result is recorded against dcKeelIssuesIsAMemberDoD at that sha; D0508 is proposed and HELD (marker process-change: the keel-guards slices), so the authority queue's pending set changes and brief 43 is published once through decision-surfacing; D0480 stays in force with one clause reversed (#SupersedeClause, D0398). dcServeAndGithubAreMembers's #DependsOn edge to this item is satisfied when the DoD result lands."; }
    // RAN: outcome=pass stopped_at=none
    part keelIssuesIsAMemberCloseOutGateR1 : TestResult { :>> id = "8720498f-04eb-4c94-a35d-c1874ae52374"; :>> outcome = VerdictKind::proposed; :>> judgedAgainst = "9e4e79c6"; :>> judgedAt = "2026-09-17"; :>> judgedBy = "claudeFable5"; }
    verification keelIssuesIsAMemberRetroGate : Test { :>> id = "c4dbe939-6f17-44c5-a6af-5515c2bc6d02"; :>> title = "Sprint 737 retro gate (autonomous, D0049)"; :>> createdAt = "2026-09-17"; :>> createdBy = "claudeFable5"; :>> method = VerificationMethod::analyze; :>> procedureText = "Written at close-out, before the verifier is dispatched; avoidable issues scanned (issue011), each finding a tracked item or the reason it is not. (1) The DoD's prose contradicted its own probe three ways (keel-view dependency, plan_cover/resolution ownership, the synopsis clause vs byte-identical help) - the fourth sprint running (734-736) to read the probe as the contract. The pattern is now a rule with four instances: a member DoD's prose lists the modules a Decision named, and the layering the Fresh probe forces is discovered at the codemod. No new item - already tracked: d0508 records the rulings, and the next member DoDs (dcServeAndGithubAreMembers) are authored after this - their prose should name only the probe, and the Decision the probe decides. (2) The resolver predicate had to descend below the guards for the member to exist without them, and the two slices are locked-path edits, so this sprint's Decision is HELD while its code is on main - the third HELD Decision from an extraction (D0506 precedent). Not tracked: D0209 cl.2 is the control and it fired as designed; the human judges the boundary move, not the tree. (3) The codemod sliced at_least_medium as a private fn into a crate that reads it publicly, and views.rs's head over-imported; both caught at cargo build before --apply was re-run (migration skill gate 2) and the template carries both fixes. Not tracked: one-shot, the control (deny(warnings)) fired. (4) The positive probe's word-match for `serve` matched the member's own doc comment saying what it does not depend on; narrowed to code lines before the pair was handed to the verifier. Not tracked: a probe that reads prose as code is the probe's defect, fixed in the probe; the pair file is the record. (5) Three private `flag` helpers now sit in three crates (main.rs, keel-process currency.rs:47, keel-issues github_ingest.rs:94) - the same eight lines. No new item - already tracked by dcKeelCliIsThinDispatch: (declared, ready after the extractions) is the item that lifts argv reading to one place; a fourth copy is the trigger to declare one sooner. (6) cli-surface-declared and every CliCommand fact are unchanged - the module home is manifest-computed (module_home.py) and D0508 reverses the clause that would have made a synopsis a second home for it (D0105). Non-finding, recorded because the DoD asked for the opposite and the reversal is the sprint's one governance change beyond the layering. (7) The pre-bash hook and D0224 held: d0508.md, fill737.txt and the probes went through files; textpatch was once given a literal instead of a file path and refused with OSError - the Edit tool did the line. Non-finding. (8) The ladder ran three times for one verdict: the first stopped at guard on the retro phrase (fixed in the file), the second was launched by the verifier agent, which then polled the receipt in its own loop instead of running keel verify --wait and was killed by the harness watchdog with its detached child; the third, launched by the primary and waited on with the D0497 command, passed every rung (1070 s) - and keel verify --wait printed KILLED during touched in the same second the receipt turned pass. The second is the test-verify brief's step 4 not followed; the third is a race in wait(): the receipt is read before the liveness answer and never re-read after it. Tracked: issue592, resolver dcWaitRereadsBeforeKilled (added this sprint). The verifier's poll loop is not a new item: the brief already names the one command, and the stall is measured from the agent's own start (D0501)."; }
    // RAN: outcome=pass stopped_at=none
    part keelIssuesIsAMemberRetroGateR1 : TestResult { :>> id = "a76a4590-c480-48de-9c0a-55583753b8d7"; :>> outcome = VerdictKind::proposed; :>> judgedAgainst = "9e4e79c6"; :>> judgedAt = "2026-09-17"; :>> judgedBy = "claudeFable5"; }
}
