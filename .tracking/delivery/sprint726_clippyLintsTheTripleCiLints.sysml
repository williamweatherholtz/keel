// ProjectDeliveryS726 — Sprint 726: dcClippyLintsTheOtherHostsCfg, the correction for issue572 - sprint 725 landed green through every local clippy and CI's Linux clippy failed it on a #[cfg(not(windows))] body the Windows host never compiles. The D0476 ladder's clippy rung and the pre-commit hook lint the triple CI lints (x86_64-unknown-linux-gnu) a second time when the host is not it, and a host without that target's std is red naming the rustup remedy, never skipped. Beside it, dcSprintPurposeIsNotPrefixed, the correction for issue573 found while scaffolding this record: the fill's purpose may not restate the Sprint N: prefix the scaffold adds.. EXECUTE. 3 pts.
package ProjectDeliveryS726 {
    private import EngineElement::*;
    private import EngineWork::*;
    private import EngineVerification::*;
    private import EngineRelationships::*;

    #CharteredBy dependency from clippyLintsTheTripleCiLintsStory to d0495;

    part clippyLintsTheTripleCiLintsStory : Story {
        :>> id = "7bc1fe0f-577f-4d00-bffd-ed0a5a6b0f55";
        :>> title = "Sprint 726: dcClippyLintsTheOtherHostsCfg, the correction for issue572 - sprint 725 landed green through every local clippy and CI's Linux clippy failed it on a #[cfg(not(windows))] body the Windows host never compiles. The D0476 ladder's clippy rung and the pre-commit hook lint the triple CI lints (x86_64-unknown-linux-gnu) a second time when the host is not it, and a host without that target's std is red naming the rustup remedy, never skipped. Beside it, dcSprintPurposeIsNotPrefixed, the correction for issue573 found while scaffolding this record: the fill's purpose may not restate the Sprint N: prefix the scaffold adds. (3 pts)";
        :>> createdAt = "2026-09-15"; :>> createdBy = "claudeFable5"; :>> kind = WorkKind::code; :>> priority = WorkPriority::p0; :>> owner = "claudeFable5"; :>> estimatedPoints = 3;
    }

    action def DeliveryRunS726 {
        action storyClippyLintsTheTripleCiLints;
        verification storyClippyLintsTheTripleCiLintsDoD : Test { :>> id = "a0917fa6-4897-4294-af5a-7efd6225e3bc"; :>> method = VerificationMethod::test; :>> procedureText = "DELIVERED BACKLOG ITEMS: dcClippyLintsTheOtherHostsCfg, dcSprintPurposeIsNotPrefixed. DONE MEANS: keel verify's clippy rung runs cargo clippy --release --all-targets -- -D warnings for the host and, when the host triple is not x86_64-unknown-linux-gnu, again with --target x86_64-unknown-linux-gnu; the receipt's clippy rung row names both command lines; a host whose rustup target list --installed lacks the triple is a red rung naming rustup target add x86_64-unknown-linux-gnu. .githooks/pre-commit does the same for the workspace. The test-verify skill names the second command beside the first. The D0388 pair in verify.rs's unit tests: the pure control says lint-again for a non-CI host with the std installed, refuses naming the remedy for a non-CI host without it, and says once for the CI triple. And: keel record sprint --fill refuses a purpose beginning with Sprint <N>: before any write, naming scaffold.rs and the doubled title; a purpose merely containing the words is written; its pair in scaffold.rs's unit tests."; }
        // RAN: TOUCHED RECEIPT: outcome=pass passed=854 failed=0 stems=[init, scaffold, verify] lib=true head=6a493f4 runner=cargo-nextest 0.9.144
        part storyClippyLintsTheTripleCiLintsDoDR1 : TestResult { :>> id = "43294bc8-32b5-498f-be4f-11bbb71b32ca"; :>> outcome = VerdictKind::pass; :>> judgedAgainst = "6a493f4"; :>> judgedAt = "2026-09-16"; :>> judgedBy = "claudeFable5"; }
    }

    verification clippyLintsTheTripleCiLintsRefineGate : Test { :>> id = "e477ce7f-1ad7-4f60-9e16-6c92e8abbc91"; :>> title = "Sprint 726 refine gate (DoR)"; :>> createdAt = "2026-09-15"; :>> createdBy = "claudeFable5"; :>> method = VerificationMethod::inspect; :>> procedureText = "Chartered by D0495 (a process-change: the pre-commit hook is an enforcement surface, D0209 clause 2; held proposed for the human under D0337). Two backlog items, ranked first and second on the frontier (issue572 High, issue573 Low). 3 points: one rung gains a second command and a pure control with its pair, one hook step gains a branch, one skill sentence, and one refusal at the sprint write with its pair. The Linux std is installed on this host (rustup target add, 2026-09-15) and the second clippy took 1 m 41 s cold over keel-cli."; }
    // RAN: LADDER: keel-serve verify . --probe ... -> outcome=pass stopped_at=none validate=pass guard=pass clippy=pass probe=pass touched=pass
    part clippyLintsTheTripleCiLintsRefineGateR1 : TestResult { :>> id = "08bfe31a-7067-45c5-a4d1-9c86c2eff089"; :>> outcome = VerdictKind::proposed; :>> judgedAgainst = "6a493f4"; :>> judgedAt = "2026-09-16"; :>> judgedBy = "claudeFable5"; }
    verification clippyLintsTheTripleCiLintsStandupGate : Test { :>> id = "4f3bb7a1-21dc-40b5-960e-c3fbfd65e7c5"; :>> title = "Sprint 726 standup gate"; :>> createdAt = "2026-09-15"; :>> createdBy = "claudeFable5"; :>> method = VerificationMethod::inspect; :>> procedureText = "Owner claudeFable5. Blocker: none - keel-cli, keel-write and the hook only. The D0388 pair is stated before the tree is read: known-positive is the pure control asked about a non-CI host whose installed targets lack the Linux triple, which returns the refusal naming rustup target add; known-negative is the same control for a non-CI host with the triple installed, which returns lint-again, and for the CI triple itself, which returns once. Live check: the ladder's clippy rung over this tree reports both commands green in its row."; }
    // RAN: LADDER: keel-serve verify . --probe ... -> outcome=pass stopped_at=none validate=pass guard=pass clippy=pass probe=pass touched=pass
    part clippyLintsTheTripleCiLintsStandupGateR1 : TestResult { :>> id = "24b1cb9b-e42a-4990-8863-838beaafe9cb"; :>> outcome = VerdictKind::proposed; :>> judgedAgainst = "6a493f4"; :>> judgedAt = "2026-09-16"; :>> judgedBy = "claudeFable5"; }
    verification clippyLintsTheTripleCiLintsImplementGate : Test { :>> id = "4b7819cb-ebbb-4715-8e89-030e01dea9b7"; :>> title = "Sprint 726 implement gate"; :>> createdAt = "2026-09-15"; :>> createdBy = "claudeFable5"; :>> method = VerificationMethod::test; :>> procedureText = "verify.rs: CI_TRIPLE constant; other_host_lint(host_is_ci, installed) is the pure control returning Once, Again or Refused(remedy); Rung::Clippy runs the host clippy, then reads rustup target list --installed and runs the second clippy or fails 2 with the remedy on stderr; command_text names both lines. .githooks/pre-commit: after the workspace clippy, the host triple from rustc -vV; not the CI triple -> the target-installed test, then the second clippy or GATE CANNOT RUN with the remedy. test-verify SKILL.md step 1 names the second command; .claude copy via sync-claude. scaffold.rs: purpose_is_prefixed(number, purpose) is the pure control; sprint_filled returns Err naming it before sprint_with runs."; }
    // RAN: LADDER: keel-serve verify . --probe ... -> outcome=pass stopped_at=none validate=pass guard=pass clippy=pass probe=pass touched=pass
    part clippyLintsTheTripleCiLintsImplementGateR1 : TestResult { :>> id = "bcada364-8335-42a6-8fb7-dae1aeed3295"; :>> outcome = VerdictKind::pass; :>> judgedAgainst = "6a493f4"; :>> judgedAt = "2026-09-16"; :>> judgedBy = "claudeFable5"; }
    verification clippyLintsTheTripleCiLintsReviewGate : Test { :>> id = "e91e18a9-9cca-4319-8fdb-09eaf1ae4e59"; :>> title = "Sprint 726 review gate — three passes per D0172"; :>> createdAt = "2026-09-15"; :>> createdBy = "claudeFable5"; :>> method = VerificationMethod::inspect; :>> procedureText = "Verifier receipt only: keel gate validate, check-engine, guard --no-receipt, sync-claude --check, the verify ladder with --probe naming the verify.rs and scaffold.rs pair tests, run once. The recorder for this sprint is dispatched with --owed 9 (D0492): six gate results, the Story DoD, and the two backlog items' DoDs."; }
    // RAN: LADDER: keel-serve verify . --probe ... -> outcome=pass stopped_at=none validate=pass guard=pass clippy=pass probe=pass touched=pass
    part clippyLintsTheTripleCiLintsReviewGateR1 : TestResult { :>> id = "d48d0cef-f0e8-4a39-9e33-4651ca8e753f"; :>> outcome = VerdictKind::proposed; :>> judgedAgainst = "6a493f4"; :>> judgedAt = "2026-09-16"; :>> judgedBy = "claudeFable5"; }
    verification clippyLintsTheTripleCiLintsCloseOutGate : Test { :>> id = "1dcfbd5b-3c6d-4a1f-ba39-1663daa98f92"; :>> title = "Sprint 726 closeOut gate (autonomous, D0049)"; :>> createdAt = "2026-09-15"; :>> createdBy = "claudeFable5"; :>> method = VerificationMethod::inspect; :>> procedureText = "Landed when the verifier's receipt reads DISCREPANCIES: NONE, the recorder's report passes check_report.py --owed 9, keel show verification . --pending shows the nine results on the tree, and the CI conclusion on the landed head is success."; }
    // RAN: LADDER: keel-serve verify . --probe ... -> outcome=pass stopped_at=none validate=pass guard=pass clippy=pass probe=pass touched=pass
    part clippyLintsTheTripleCiLintsCloseOutGateR1 : TestResult { :>> id = "f3d2f0db-642b-46f5-8adf-391e6def3379"; :>> outcome = VerdictKind::proposed; :>> judgedAgainst = "6a493f4"; :>> judgedAt = "2026-09-16"; :>> judgedBy = "claudeFable5"; }
    verification clippyLintsTheTripleCiLintsRetroGate : Test { :>> id = "d0b3ed77-812c-4224-9f8b-73789a8f899b"; :>> title = "Sprint 726 retro gate (autonomous, D0049)"; :>> createdAt = "2026-09-15"; :>> createdBy = "claudeFable5"; :>> method = VerificationMethod::analyze; :>> procedureText = "Avoidable issues scanned (issue011): issue572 was found by CI after the push - the second instance of the local-gate-differs-from-CI class (issue453 first). The correction makes the local lint cover CI's triple; the class residual is every other CI-only difference (rust stable 1.98 on ubuntu vs 1.96 here - a lint added between the two versions is still CI's alone), stated here and not tracked: a toolchain pin is a CHANGE for a fork brief, not a sprint. issue573 (seventeen doubled sprint titles from the fill's purpose restating the scaffold's prefix) was found while scaffolding this sprint's record and is corrected in it; the seventeen titles are history and stay. While this sprint waited for its verifier, CI reported 6a493f4 red on a THIRD member of the same class: scripts/module_home.py --probe failed on a literal keel-cli/src anchor in facts.py, and the six ci-probe scripts have no local runner (issue574, Medium, resolver dcScriptProbesRunBeforeCommit: one discovery script both ci.yml and the pre-commit hook call). The anchor is fixed in this sprint's commit so its CI can be green; the runner is the next sprint's item."; }
    // RAN: LADDER: keel-serve verify . --probe ... -> outcome=pass stopped_at=none validate=pass guard=pass clippy=pass probe=pass touched=pass
    part clippyLintsTheTripleCiLintsRetroGateR1 : TestResult { :>> id = "6c88a0a9-9a6b-48c3-9754-e8aaa8ef98b0"; :>> outcome = VerdictKind::proposed; :>> judgedAgainst = "6a493f4"; :>> judgedAt = "2026-09-16"; :>> judgedBy = "claudeFable5"; }
}
