// ProjectDeliveryS749 — Sprint 749: The decision brief remembers the reader's draft per published set, not per title, so a note written for one brief never lands as the words on the next one's verdicts (issue659). EXECUTE. 2 pts.
package ProjectDeliveryS749 {
    private import EngineElement::*;
    private import EngineWork::*;
    private import EngineVerification::*;
    private import EngineRelationships::*;

    #CharteredBy dependency from briefDraftKeyIsThePublishedSetStory to d0359;
    #Delivers dependency from briefDraftKeyIsThePublishedSetStory to dcBriefDraftKeyIsThePublishedSet;

    part briefDraftKeyIsThePublishedSetStory : Story {
        :>> id = "99f39e0b-115e-4261-ba1d-c0bf54ea6b6b";
        :>> title = "Sprint 749: The decision brief remembers the reader's draft per published set, not per title, so a note written for one brief never lands as the words on the next one's verdicts (issue659) (2 pts)";
        :>> createdAt = "2026-09-19"; :>> createdBy = "claudeFable5"; :>> kind = WorkKind::code; :>> priority = WorkPriority::p0; :>> owner = "claudeFable5"; :>> estimatedPoints = 2;
    }

    action def DeliveryRunS749 {
        action storyBriefDraftKeyIsThePublishedSet;
        verification storyBriefDraftKeyIsThePublishedSetDoD : Test { :>> id = "597c6db6-44b3-49fb-b2ad-c378111a3c91"; :>> method = VerificationMethod::test; :>> procedureText = "DELIVERED BACKLOG ITEM: dcBriefDraftKeyIsThePublishedSet. DONE MEANS: the task's DoD passes as written - the page script keys the draft (chosen courses, the note) on the .page data-set attribute with no title fallback and restores nothing without one; check_templates --brief refuses a title-keyed draft store and stops counting a typed script block as reader prose, each with a self-test pair; the six-held builder carries the live verdict block forward (--carry) and the footer reads as a sentence; the standing brief is republished at the same URL with the six records intact and the note empty."; }
        // RAN: verify . --probe-from pair_749.txt -> outcome=pass stopped_at=none; validate=pass guard=pass clippy=pass probe=pass
        part storyBriefDraftKeyIsThePublishedSetDoDR1 : TestResult { :>> id = "6f1210b0-12fa-4eb2-b387-18ed0dabc061"; :>> outcome = VerdictKind::pass; :>> judgedAgainst = "59ebd752"; :>> judgedAt = "2026-09-19"; :>> judgedBy = "claudeFable5"; }
    }

    verification briefDraftKeyIsThePublishedSetRefineGate : Test { :>> id = "6d63ec71-96fb-4791-b3fc-a5d9f8b7bb87"; :>> title = "Sprint 749 refine gate (DoR)"; :>> createdAt = "2026-09-19"; :>> createdBy = "claudeFable5"; :>> method = VerificationMethod::inspect; :>> procedureText = "One backlog item, sized 2: a python-only change to the brief builder and the template checker, no Rust, no schema. Ready when the human's report ('I think comment section is messed up') is a tracked Issue with this task as its resolver and the mechanism is read from the live page source, not guessed."; }
    // RAN: verify . --probe-from pair_749.txt -> outcome=pass stopped_at=none; validate=pass guard=pass clippy=pass probe=pass
    part briefDraftKeyIsThePublishedSetRefineGateR1 : TestResult { :>> id = "96a05346-f3ef-4e20-b9b1-cf82b5c3aa26"; :>> outcome = VerdictKind::proposed; :>> judgedAgainst = "59ebd752"; :>> judgedAt = "2026-09-19"; :>> judgedBy = "claudeFable5"; }
    verification briefDraftKeyIsThePublishedSetStandupGate : Test { :>> id = "8cc9b6c3-8573-4d7a-bcc3-2c02fa67a3a6"; :>> title = "Sprint 749 standup gate"; :>> createdAt = "2026-09-19"; :>> createdBy = "claudeFable5"; :>> method = VerificationMethod::inspect; :>> procedureText = "Root cause read from the live artifact: the inherited tail script keys localStorage on document.title, identical on every brief. The fix is one key, two guards, one checker rule, one carry flag. The six records the human tapped are data to carry, never to rewrite."; }
    // RAN: verify . --probe-from pair_749.txt -> outcome=pass stopped_at=none; validate=pass guard=pass clippy=pass probe=pass
    part briefDraftKeyIsThePublishedSetStandupGateR1 : TestResult { :>> id = "7c2afcbe-7478-4fd4-a97c-5892e9766637"; :>> outcome = VerdictKind::proposed; :>> judgedAgainst = "59ebd752"; :>> judgedAt = "2026-09-19"; :>> judgedBy = "claudeFable5"; }
    verification briefDraftKeyIsThePublishedSetImplementGate : Test { :>> id = "10d71a19-00ad-4751-8733-ebb5542b8230"; :>> title = "Sprint 749 implement gate"; :>> createdAt = "2026-09-19"; :>> createdBy = "claudeFable5"; :>> method = VerificationMethod::test; :>> procedureText = "validate, check-engine and sync-claude --check clean; check_templates --self-test passes with the two new pairs; the previous live page is refused by the new rule (known positive); the rebuilt page is clean and its tail script parses under node."; }
    // RAN: verify . --probe-from pair_749.txt -> outcome=pass stopped_at=none; validate=pass guard=pass clippy=pass probe=pass
    part briefDraftKeyIsThePublishedSetImplementGateR1 : TestResult { :>> id = "51230263-2718-4dae-8a0d-e3ed1567150a"; :>> outcome = VerdictKind::pass; :>> judgedAgainst = "59ebd752"; :>> judgedAt = "2026-09-19"; :>> judgedBy = "claudeFable5"; }
    verification briefDraftKeyIsThePublishedSetReviewGate : Test { :>> id = "de0c95cd-c256-4271-b58e-96d6bb1bf49f"; :>> title = "Sprint 749 review gate — three passes per D0172"; :>> createdAt = "2026-09-19"; :>> createdBy = "claudeFable5"; :>> method = VerificationMethod::inspect; :>> procedureText = "The live page read back after publish: six records seq 1-6 present, the title key absent, the set key present with both guards, data-set naming the six ids at 59ebd752, footer ending in a sentence. The carried words stay the previous brief's note and are not cited under D0289."; }
    // RAN: verify . --probe-from pair_749.txt -> outcome=pass stopped_at=none; validate=pass guard=pass clippy=pass probe=pass
    part briefDraftKeyIsThePublishedSetReviewGateR1 : TestResult { :>> id = "dddfcbf6-95c2-46df-b896-e871955d4e55"; :>> outcome = VerdictKind::proposed; :>> judgedAgainst = "59ebd752"; :>> judgedAt = "2026-09-19"; :>> judgedBy = "claudeFable5"; }
    verification briefDraftKeyIsThePublishedSetCloseOutGate : Test { :>> id = "21d60000-36ff-4d50-8042-a93993024252"; :>> title = "Sprint 749 closeOut gate (autonomous, D0049)"; :>> createdAt = "2026-09-19"; :>> createdBy = "claudeFable5"; :>> method = VerificationMethod::inspect; :>> procedureText = "The task's DoD result is recorded from the receipts above; .keel/decision-page.toml records the fifty-fourth publish against 59ebd752 with the same six ids."; }
    // RAN: verify . --probe-from pair_749.txt -> outcome=pass stopped_at=none; validate=pass guard=pass clippy=pass probe=pass
    part briefDraftKeyIsThePublishedSetCloseOutGateR1 : TestResult { :>> id = "5ca2bc43-7c49-42ff-8c62-a1b947c1d8bd"; :>> outcome = VerdictKind::proposed; :>> judgedAgainst = "59ebd752"; :>> judgedAt = "2026-09-19"; :>> judgedBy = "claudeFable5"; }
    verification briefDraftKeyIsThePublishedSetRetroGate : Test { :>> id = "09bdaa77-8685-4fbd-8978-4d36d6671911"; :>> title = "Sprint 749 retro gate (autonomous, D0049)"; :>> createdAt = "2026-09-19"; :>> createdBy = "claudeFable5"; :>> method = VerificationMethod::analyze; :>> procedureText = "Two findings, avoidable issues scanned (issue011): the contaminated note on six verdicts was avoidable and its control landed here. Finding: check_templates counted a typed script block as reader prose for as long as the rule existed - no page had carried one until the verdict block. Control: markup_only strips every script and style element regardless of attributes, with a pair that puts the same words in a script and in a paragraph. Finding: a fresh brief inherits its tail script from the previous page byte-for-byte, so a defect in it rides every publish; the new rule refuses the one defect known, and the builder now asserts its rewrite happened; the tail becoming one authored source every builder reads is tracked as dcBriefTailIsAnAuthoredSource, added in this commit. The first finding needs no new item: its control (markup_only strips every script and style element) landed in this sprint."; }
    // RAN: retro at closeOut (2026-09-19), avoidable issues scanned (issue011); finding two tracked as dcBriefTailIsAnAuthoredSource added this commit; finding one's control landed this sprint
    part briefDraftKeyIsThePublishedSetRetroGateR1 : TestResult { :>> id = "156fb538-e6c1-4db2-8251-5488ea6fd181"; :>> outcome = VerdictKind::proposed; :>> judgedAgainst = "59ebd752"; :>> judgedAt = "2026-09-19"; :>> judgedBy = "claudeFable5"; }
}
