// ProjectDeliveryS723 — Sprint 723: dcRetroScanIsCheckedAtTheWrite, the correction for issue566 - the sprint 721 retro Test lacked the issue011 scan wording, the recorder's write was accepted, and the ceremony guard went red one commit later naming the RESULT while its check read the Test's procedureText. The scan requirement is now checked at the write by the actor who can satisfy it, the guard's message names the surface it read, and the term list has one home.. EXECUTE. 1 pts.
package ProjectDeliveryS723 {
    private import EngineElement::*;
    private import EngineWork::*;
    private import EngineVerification::*;
    private import EngineRelationships::*;

    #CharteredBy dependency from retroScanIsCheckedAtTheWriteStory to d0437;

    part retroScanIsCheckedAtTheWriteStory : Story {
        :>> id = "1fe05bab-9971-4e1c-85cd-317fe9cc4ab4";
        :>> title = "Sprint 723: dcRetroScanIsCheckedAtTheWrite, the correction for issue566 - the sprint 721 retro Test lacked the issue011 scan wording, the recorder's write was accepted, and the ceremony guard went red one commit later naming the RESULT while its check read the Test's procedureText. The scan requirement is now checked at the write by the actor who can satisfy it, the guard's message names the surface it read, and the term list has one home. (1 pts)";
        :>> createdAt = "2026-09-15"; :>> createdBy = "claudeFable5"; :>> kind = WorkKind::code; :>> priority = WorkPriority::p0; :>> owner = "claudeFable5"; :>> estimatedPoints = 1;
    }

    action def DeliveryRunS723 {
        action storyRetroScanIsCheckedAtTheWrite;
        verification storyRetroScanIsCheckedAtTheWriteDoD : Test { :>> id = "e2fa4c6e-d242-4504-b2c2-52028dbabf7b"; :>> method = VerificationMethod::test; :>> procedureText = "DELIVERED BACKLOG ITEMS: dcRetroScanIsCheckedAtTheWrite. DONE MEANS: keel record gate-result on a gate whose Test name contains RetroGate REFUSES (WriteError::RetroScanMissing, exit 1, ledgered append-gate-result:retro-scan) when the Test's procedureText carries none of RETRO_SCAN_EVIDENCE, naming the Test, the surface (procedureText) and every accepted term; a Test with a term is recorded; a non-retro gate owes no wording; the file is unchanged byte-for-byte on a refusal. The ceremony guard's violation reads 'Retro Test <name> records no avoidable-issue scan in its procedureText (issue011; one of: ...)' - the Test, never the result. ONE home: keel_write::write::RETRO_SCAN_EVIDENCE and retro_scan_recorded() are read by both append_gate_result and guards::retro_scan_missing; the guard's own SCAN_EVIDENCE constant is gone. Resolves issue566; discharges obligationda53d7d0. VERIFIED BY: cargo test --release -p keel-write --lib green (47; the D0388 pair a_retro_gate_result_is_refused_while_its_test_records_no_scan, the issue449 census rows every_registered_refusal_has_a_site_in_the_source and every_ledgered_refusal_in_main_is_registered); cargo test --release --lib guards::tests green (24; retro_scan_evidence_required asserts the Test name is returned); cargo clippy --release --all-targets clean; a live keel record gate-result against a scratch retro Test reading 'rubber stamp' refused with exit 1 and the term list, the same call against 'Avoidable issues scanned (issue011): none.' recorded, the hooks ledger holding control append-gate-result:retro-scan."; }
        // RAN: verify . -> outcome=pass stopped_at=none; TOUCHED RECEIPT: passed=886 failed=0
        part storyRetroScanIsCheckedAtTheWriteDoDR1 : TestResult { :>> id = "b35be805-e0eb-4169-bb7a-13f1535079d7"; :>> outcome = VerdictKind::pass; :>> judgedAgainst = "6439757"; :>> judgedAt = "2026-09-15"; :>> judgedBy = "claudeFable5"; }
    }

    verification retroScanIsCheckedAtTheWriteRefineGate : Test { :>> id = "5ef7c7b1-8e89-4c3a-8a3c-b2bee27d2a24"; :>> title = "Sprint 723 refine gate (DoR)"; :>> createdAt = "2026-09-15"; :>> createdBy = "claudeFable5"; :>> method = VerificationMethod::inspect; :>> procedureText = "DoR: chartered by d0437 (the ceremony guard's two clauses, issue010 and issue011 - this moves the issue011 clause to the write); 1 point - one constant moved, one predicate, one WriteError variant, one refusal site, one registry row, one guard message, three tests, no schema; second on the frontier at 6439757 behind dcVerifyReceiptSaysRunning (done this commit); blocking dependency none; the DoD Test is in this file."; }
    // RAN: validate=pass from verify ladder
    part retroScanIsCheckedAtTheWriteRefineGateR1 : TestResult { :>> id = "99ff71f2-7697-4ff6-bab1-4f591f1bd535"; :>> outcome = VerdictKind::proposed; :>> judgedAgainst = "6439757"; :>> judgedAt = "2026-09-15"; :>> judgedBy = "claudeFable5"; }
    verification retroScanIsCheckedAtTheWriteStandupGate : Test { :>> id = "439c9427-bd44-4dd8-9ea1-821e5c20df44"; :>> title = "Sprint 723 standup gate"; :>> createdAt = "2026-09-15"; :>> createdBy = "claudeFable5"; :>> method = VerificationMethod::inspect; :>> procedureText = "Frontier at 6439757: dcRetroScanIsCheckedAtTheWrite first (dcVerifyReceiptSaysRunning's DoD recorded), then the Delivery items the modular-members requirements govern (dcViewIsAMember, dcSuiteIsAMember, dcTouchedSetDescendsTheWorkspace). Blockers: none."; }
    // RAN: gate check-engine . -> .engine instance files validated clean; exit=0
    part retroScanIsCheckedAtTheWriteStandupGateR1 : TestResult { :>> id = "1a6d0824-4afe-47e7-b3b9-f54f62411e92"; :>> outcome = VerdictKind::proposed; :>> judgedAgainst = "6439757"; :>> judgedAt = "2026-09-15"; :>> judgedBy = "claudeFable5"; }
    verification retroScanIsCheckedAtTheWriteImplementGate : Test { :>> id = "e3e3f3bb-afae-48e0-bfd3-9f2e8bd42b88"; :>> title = "Sprint 723 implement gate"; :>> createdAt = "2026-09-15"; :>> createdBy = "claudeFable5"; :>> method = VerificationMethod::test; :>> procedureText = "keel-write/write.rs: RETRO_SCAN_EVIDENCE + retro_scan_recorded() (pub, one home); WriteError::RetroScanMissing with a Display that names the Test, the surface and the terms; verification_procedure_text() reads the attribute top-level or inside an action def; refuse_unscanned_retro() runs in append_gate_result_locked after the gate-exists check and before the receipt check; registry row append-gate-result:retro-scan. keel-cli/guards.rs: SCAN_EVIDENCE removed; retro_scan_missing returns the Test's name and reads crate::write::retro_scan_recorded; the violation line names the Test and the term list. keel-cli/main.rs: the refusal is ledgered under its registry row. guards.md ceremony row doc-synced. Order followed as written in the DoD."; }
    // RAN: cargo test --release -p keel-write --lib write::tests::a_retro_gate_result_is_refused_while_its_test_records_no_scan -> test result: ok. 1 passed; 0 failed; TOUCHED RECEIPT: passed=886 failed=0
    part retroScanIsCheckedAtTheWriteImplementGateR1 : TestResult { :>> id = "363b77af-d795-43c4-86e3-e09cd00090d8"; :>> outcome = VerdictKind::pass; :>> judgedAgainst = "6439757"; :>> judgedAt = "2026-09-15"; :>> judgedBy = "claudeFable5"; }
    verification retroScanIsCheckedAtTheWriteReviewGate : Test { :>> id = "110692ba-7213-43fd-858e-32dca4e58cc0"; :>> title = "Sprint 723 review gate — three passes per D0172"; :>> createdAt = "2026-09-15"; :>> createdBy = "claudeFable5"; :>> method = VerificationMethod::inspect; :>> procedureText = "Three passes (D0172): the refusal keys on the gate NAME containing RetroGate, the same anchor the guard uses, so a Retro the guard would read is the one the write refuses and no other; a human judge is refused the same way because the wording is the Test's fact, not the judge's word; the guard keeps its check for a Retro that reached the tree by hand or before this commit, and now names the Test so the fix is one edit away. Residual: `record sprint --fill` still accepts a retro section without the wording - that Test is then unrecordable until edited, which is the honest state; refusing it at the fill is dcFillRefusesARetroTheGuardWouldRefuse, already on the frontier, and the shared predicate is what it will read."; }
    // RAN: sync-claude --check . -> claude-surface: keel-owned subset matches this binary's generator; exit=0
    part retroScanIsCheckedAtTheWriteReviewGateR1 : TestResult { :>> id = "d0413825-d842-47cc-84e5-d039fd5857a1"; :>> outcome = VerdictKind::proposed; :>> judgedAgainst = "6439757"; :>> judgedAt = "2026-09-15"; :>> judgedBy = "claudeFable5"; }
    verification retroScanIsCheckedAtTheWriteCloseOutGate : Test { :>> id = "f015d8f2-a084-4347-bd2a-4e5053b36f4b"; :>> title = "Sprint 723 closeOut gate (autonomous, D0049)"; :>> createdAt = "2026-09-15"; :>> createdBy = "claudeFable5"; :>> method = VerificationMethod::inspect; :>> procedureText = "Code, tests, registry row and guard message in keel-write and keel-cli; the DoD result and six gates recorded from the verifier's receipt by the recorder; issue566 resolves and obligationda53d7d0 discharges when the resolver is done (computed). This sprint's own Retro is the first written under the new refusal."; }
    // RAN: DISCREPANCIES: NONE
    part retroScanIsCheckedAtTheWriteCloseOutGateR1 : TestResult { :>> id = "bd4f09c1-0fba-444e-9512-50cf35ebfbce"; :>> outcome = VerdictKind::proposed; :>> judgedAgainst = "6439757"; :>> judgedAt = "2026-09-15"; :>> judgedBy = "claudeFable5"; }
    verification retroScanIsCheckedAtTheWriteRetroGate : Test { :>> id = "d3071c5d-9f61-4755-8767-cebb24d25678"; :>> title = "Sprint 723 retro gate (autonomous, D0049)"; :>> createdAt = "2026-09-15"; :>> createdBy = "claudeFable5"; :>> method = VerificationMethod::analyze; :>> procedureText = "Finding: the issue011 clause lived in the guard for 700 sprints as a turn-boundary check on a fact the actor at that boundary (the recorder) cannot change; the pattern - a check placed where it fires, not where it can be answered - is the issue566 finding and is the same shape as issue448 (the receipt owed at the write). Avoidable issues scanned (issue011): three. (0) The first recorder dispatch ran no keel record command, composed a three-line report reading DISCREPANCIES: NONE, and check_report.py passed it - none of its five refusals reads what is absent; recorded as issue568 (High), resolver dcRecorderReportAccountsForEveryOwedRecord (check_report.py --owed N), ranked first on the frontier. (1) The first verifier dispatch read verify-receipt.toml while it said running, typed `ladder killed mid-execution` with 2 keel-serve.exe and 3 cargo.exe alive, and stopped; the ladder finished 489 s later with a real red - recorded as issue567, resolver dcVerifierReceiptOutcomeIsRenderedNotTyped, whose DoD now carries the WAIT/KILLED clause read from the live-process observable. (2) That red was the issue449 census test: the new registry row append-gate-result:retro-scan had no WRITE_PATH_CHECKS row - the control worked as designed and the row was added; not tracked apart, since the test is the control. The fill-time refusal is already tracked as dcFillRefusesARetroTheGuardWouldRefuse and the retro says so by name (D0293). No process improvement beyond moving the check to the write - NOT A PROCESS CHANGE: the ceremony guard's clause is unchanged in meaning, its message names its surface, and the write refuses what the guard would have refused."; }
    // RAN: DISCREPANCIES: NONE
    part retroScanIsCheckedAtTheWriteRetroGateR1 : TestResult { :>> id = "25e82f9a-bcd2-4b59-a7b3-288e5d96cb26"; :>> outcome = VerdictKind::proposed; :>> judgedAgainst = "6439757"; :>> judgedAt = "2026-09-15"; :>> judgedBy = "claudeFable5"; }
}
