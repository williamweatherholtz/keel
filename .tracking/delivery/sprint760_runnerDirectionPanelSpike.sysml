// ProjectDeliveryS760 — Sprint 760: The human asked on 2026-09-22 (st190) to critique the tool-owns-the-task runner direction with a panel, make an artifact, and make the case that it is the right direction. This sprint runs the adversarial-panel-review process (D0187) at its full nine-persona roster over the direction, revises the direction artifact after each round from the finding-to-resolution map, stops at the process's three-round limit with the irreducible residue handed to the human as held Decisions, publishes an executive brief with one tab per fork, and records the whole under D0542 with nothing built.. EXECUTE. 3 pts.
package ProjectDeliveryS760 {
    private import EngineElement::*;
    private import EngineWork::*;
    private import EngineVerification::*;
    private import EngineRelationships::*;

    #CharteredBy dependency from runnerDirectionPanelSpikeStory to d0542;
    #Delivers dependency from runnerDirectionPanelSpikeStory to dcRunnerDirectionPanelIsRecorded;

    part runnerDirectionPanelSpikeStory : Story {
        :>> id = "c9784829-3b64-4dea-891c-c2910e644ef6";
        :>> title = "Sprint 760: The human asked on 2026-09-22 (st190) to critique the tool-owns-the-task runner direction with a panel, make an artifact, and make the case that it is the right direction. This sprint runs the adversarial-panel-review process (D0187) at its full nine-persona roster over the direction, revises the direction artifact after each round from the finding-to-resolution map, stops at the process's three-round limit with the irreducible residue handed to the human as held Decisions, publishes an executive brief with one tab per fork, and records the whole under D0542 with nothing built. (3 pts)";
        :>> createdAt = "2026-09-22"; :>> createdBy = "claudeFable5"; :>> kind = WorkKind::code; :>> priority = WorkPriority::p0; :>> owner = "claudeFable5"; :>> estimatedPoints = 3;
    }

    action def DeliveryRunS760 {
        action storyRunnerDirectionPanelSpike;
        verification storyRunnerDirectionPanelSpikeDoD : Test { :>> id = "815b3c56-3446-4c1e-bec5-dd7b91338a72"; :>> method = VerificationMethod::test; :>> procedureText = "docs/reviews/runner-direction-panel-2026-09-22.md exists carrying the human's words verbatim, the four revisions of the direction artifact with their finding-to-resolution maps, the twenty-seven panelist reports verbatim, the round-by-round verdict table, the independence note verbatim and the disclosure of the panelist write; the brief built from brief_facts.json passes python scripts/check_templates.py --brief and is published as an artifact whose URL the review names, with the verdict first, one tab per held fork, two logic exhibits and a do-nothing course per tab and a falsifier per tab; the knowledge record .tracking/knowledge/runner-direction-panel-2026-09-22.sysml holds the D0196 replication text with a result per round; the two recurring findings are Issues with resolvers; the seven forks are held Decisions layered on D0542; keel gate validate, guard and check-engine are green on the committed tree."; }
        // RAN: python check of docs/reviews/runner-direction-panel-2026-09-22.md - LF, the human's words verbatim, the verdict table, Appendix 0 (three briefs), D1-D4, R1-R3 with nine reports per round, the independence note and the disclosure; check_templates.py --brief clean and the artifact published with its URL in the review header; knowledge record with three passing round results judgedAgainst f365cb7a; issue671 and issue672 with resolvers; D0543-D0549 held proposed and layered on D0542; validate, check-engine and guard green.
        part storyRunnerDirectionPanelSpikeDoDR1 : TestResult { :>> id = "a8df4aaa-2c8a-4fa0-b0fd-70567fe3a2a2"; :>> outcome = VerdictKind::pass; :>> judgedAgainst = "f365cb7a21cf0147a06d4c3c6b70e94e8007eacb"; :>> judgedAt = "2026-09-22"; :>> judgedBy = "claudeFable5"; }
    }

    verification runnerDirectionPanelSpikeRefineGate : Test { :>> id = "37fc1193-4f76-4381-98ae-199390f4e091"; :>> title = "Sprint 760 refine gate (DoR)"; :>> createdAt = "2026-09-22"; :>> createdBy = "claudeFable5"; :>> method = VerificationMethod::inspect; :>> procedureText = "The process existed and had run (2026-08-14 panel, 2026-08-21 production-readiness design, 2026-08-24 manager-inversion panel), so nothing was defined. Two refinements against those runs: the full nine-persona roster rather than four, because the artifact is a direction that reverses accepted clauses and the human asked to be convinced; and a computed tally over the reports rather than a hand count, so the verdict table is a script's output. The D0515 delivery requirement is met as in sprints 758 and 759: the deliverable is its own backlog item, dcRunnerDirectionPanelIsRecorded, whose DoD is the record's content. Sized 3 points: three rounds of nine parallel critics, four artifact revisions, eight Decisions, a review, a brief, a knowledge record."; }
    // RAN: grep -c 'action dc' .tracking/delivery/sprint758_agentHarnessLandscapeSpike.sysml (the spike shape reused) and .tracking/backlog.sysml read for dcRunnerDirectionPanelIsRecorded and its DoD, authored before the panel was dispatched; DoR: estimatedPoints 3, #CharteredBy d0542 and #Delivers dcRunnerDirectionPanelIsRecorded on the Story (sprint760 file lines 8-9), DoD in the fill, the full nine-persona roster chosen because the artifact reverses accepted clauses.
    part runnerDirectionPanelSpikeRefineGateR1 : TestResult { :>> id = "e8d31bb3-f00f-4602-a382-8a8e505d8e5b"; :>> outcome = VerdictKind::proposed; :>> judgedAgainst = "f365cb7a21cf0147a06d4c3c6b70e94e8007eacb"; :>> judgedAt = "2026-09-22"; :>> judgedBy = "claudeFable5"; }
    verification runnerDirectionPanelSpikeStandupGate : Test { :>> id = "9165509f-8665-446d-80b7-2a902048dd27"; :>> title = "Sprint 760 standup gate"; :>> createdAt = "2026-09-22"; :>> createdBy = "claudeFable5"; :>> method = VerificationMethod::inspect; :>> procedureText = "Three choices made before dispatch. Every panelist prompt carried the honesty rule verbatim (the persona is a lens, not a script), the repository root for verification with the instruction never to verify against the artifact, and the output contract with a minimal flip set. From round 2 each panelist received the digest of every prior position and an explicit invitation to rebut. And every panelist claim about keel's own code that the author used in a revision was re-read at its file and line before it entered the text - D0209 clause 5, D0182's clause, D0094's auth clause, D0192's acceptance words, claims.rs, queries.rs, launcher.rs, serve.rs, library.rs, claude_surface.rs. Risks named: same-model panelists are a rigor framing and the record says so; the tally regex was prose-shaped and undercounted round 2 until the facts pedant caught it (issue672)."; }
    // RAN: keel show whats-next . before dispatch (the human's st190 ask pre-empts the frontier, D0052); the three standup choices are in the gate text; every panelist claim about keel's own code used in a revision was re-read at its line before use: .engine/decisions/0209-adhere-not-invert.sysml:19 (clause 5), 0182:17, 0094 auth clause, 0192:26, members/keel-model/src/claims.rs:15 and 51-70, queries.rs:551-555 (repo_today is the commit date), members/keel-serve/src/launcher.rs:47-70 and serve.rs:1212, members/keel-process/src/library.rs:32, members/keel-write/src/claude_surface.rs:80-95; git status --porcelain after the disclosed panelist write matched the opening snapshot and git ls-files -v .claude/settings.json showed H.
    part runnerDirectionPanelSpikeStandupGateR1 : TestResult { :>> id = "34777140-bbc4-4091-ab57-5934838bd76e"; :>> outcome = VerdictKind::proposed; :>> judgedAgainst = "f365cb7a21cf0147a06d4c3c6b70e94e8007eacb"; :>> judgedAt = "2026-09-22"; :>> judgedBy = "claudeFable5"; }
    verification runnerDirectionPanelSpikeImplementGate : Test { :>> id = "9c1fe520-1923-426c-b86b-8e7dc846c44e"; :>> title = "Sprint 760 implement gate"; :>> createdAt = "2026-09-22"; :>> createdBy = "claudeFable5"; :>> method = VerificationMethod::test; :>> procedureText = "RAN three rounds of nine read-only critics in parallel, each round against a new revision of the direction artifact carrying its finding-to-resolution map: round 1 against revision 1 returned 2 ACCEPT / 7 OBJECT (3 BLOCKER, 47 MAJOR, 33 MINOR); revision 2 resolved every flip set; round 2 returned 0 / 9 (0, 36, 35) converging on six defects revision 2 introduced; revision 3 resolved them; round 3 returned 3 / 6 (0, 28, 27) with the residue named as forks; revision 4 landed every author-fixable round-3 item and named seven forks. Recorded D0542 (charter, accepted under standing consent) and D0543-D0549 (held: two SupersedeClause forks on D0209 and D0182, five forks), issue671 and issue672 with their resolver tasks. brief_facts.py computed every number on the page from the tree and the reports; build_panel_brief.py rendered seven tabs; check_templates.py --brief passed; the page was published. assemble760.py concatenated the header, the three briefs, the four revisions and the twenty-seven reports LF-only. The knowledge record was written with the Write tool."; }
    // RAN: python scratchpad/panel_tally.py 1, 2, 3 -> round 1: 2 accept / 7 object, 3 blocker 47 major 33 minor; round 2: 0 / 9, 0 36 35; round 3: 3 / 6, 0 28 27 (27 reports). keel record decision --from for d0542 (accepted under standing consent d0207) and d0543-d0549 (held: two SupersedeClause edges authored to d0209 and d0182; five forks). record issue x2 (issue671, issue672) with resolvers dcPanelistsAreDispatchedIntoAnIsolatedTree and dcPanelTallyReadsAMachineTrailer. python scratchpad/brief_facts.py then build_panel_brief.py -> runner_direction_verdict.html 7 tabs; python scripts/check_templates.py --brief -> brief contract: clean; published as an artifact. python scratchpad/assemble760.py -> docs/reviews/runner-direction-panel-2026-09-22.md LF-only. Knowledge record written with the Write tool with three round results judgedAgainst f365cb7a.
    part runnerDirectionPanelSpikeImplementGateR1 : TestResult { :>> id = "a7cc1965-c289-4d89-91f4-d9018f4856bc"; :>> outcome = VerdictKind::pass; :>> judgedAgainst = "f365cb7a21cf0147a06d4c3c6b70e94e8007eacb"; :>> judgedAt = "2026-09-22"; :>> judgedBy = "claudeFable5"; }
    verification runnerDirectionPanelSpikeReviewGate : Test { :>> id = "c242d5ad-2f35-4bf4-93e3-769d473ad294"; :>> title = "Sprint 760 review gate — three passes per D0172"; :>> createdAt = "2026-09-22"; :>> createdBy = "claudeFable5"; :>> method = VerificationMethod::inspect; :>> procedureText = "Three passes per D0172. Content: every panelist's every flip finding across three rounds is either resolved in the revision that followed, refuted with evidence, dropped with the word dropped, or carried to the human as a fork; the forks name both options and their costs in the human's terms. Structure: one H1, the verdict table computed, Appendix 0 with the three briefs fenced, D1-D4 the revisions, R1-R3 the reports, all headings demoted so the document has one H1; the brief passes the contract checker with its per-tab ceiling. Record: the DoD names its checks, D0542 says NOT A FORK and NOT A PROCESS CHANGE with reasons and names the forks as separate held Decisions, and the knowledge record's REPLICATION text can be followed by a stranger and names the round tallies from the script."; }
    // RAN: grep -n of headings in docs/reviews/runner-direction-panel-2026-09-22.md - one H1, the verdict table computed from panel_tally.py, Appendix 0 with three briefs fenced, D1-D4 the revisions, R1-R3 nine reports each; python scripts/check_templates.py --brief runner_direction_verdict.html -> clean; keel gate validate . -> 884 tracking file(s) validated clean; keel gate check-engine . -> validated clean; keel gate guard --no-receipt -> ALL PASS after two fixes the guards asked for: the seven forks gained a short title name, a RESEARCH line and a COST per option (judgment-request-quality), and the two resolver DoDs name their Issues (issues guard).
    part runnerDirectionPanelSpikeReviewGateR1 : TestResult { :>> id = "e43f26ec-a412-4154-9024-3fe9bc8e45be"; :>> outcome = VerdictKind::proposed; :>> judgedAgainst = "f365cb7a21cf0147a06d4c3c6b70e94e8007eacb"; :>> judgedAt = "2026-09-22"; :>> judgedBy = "claudeFable5"; }
    verification runnerDirectionPanelSpikeCloseOutGate : Test { :>> id = "5b3e9c92-2444-4db4-b73b-b12707c60f89"; :>> title = "Sprint 760 closeOut gate (autonomous, D0049)"; :>> createdAt = "2026-09-22"; :>> createdBy = "claudeFable5"; :>> method = VerificationMethod::inspect; :>> procedureText = "Delivered: the review, the brief and its URL, the knowledge record, D0542 accepted, D0543-D0549 held for the human, issue671 and issue672 with resolvers, dcRunnerDirectionPanelIsRecorded. Not delivered on purpose: no code, no spec file, no schema or process change; the direction stays a brainstorm until the human answers the forks. The answer to convince me is on the page: a direction that survived three rounds of verified objections with seven choices left that only the human can make."; }
    // RAN: git status --short lists the review, the knowledge record, decisions 0542-0549, sprint760, backlog.sysml, issues-claudeFable5.sysml, intake-2026-09-22.sysml; keel gate validate . exit 0; check-engine exit 0; guard --no-receipt exit 0. Delivered the review, the brief and its URL, the knowledge record, D0542 accepted, D0543-D0549 held, issue671 and issue672 with resolvers, dcRunnerDirectionPanelIsRecorded; nothing built, no spec file, the direction stays a brainstorm.
    part runnerDirectionPanelSpikeCloseOutGateR1 : TestResult { :>> id = "26a3721f-12fd-4be6-acb9-e0714c9c4a63"; :>> outcome = VerdictKind::proposed; :>> judgedAgainst = "f365cb7a21cf0147a06d4c3c6b70e94e8007eacb"; :>> judgedAt = "2026-09-22"; :>> judgedBy = "claudeFable5"; }
    verification runnerDirectionPanelSpikeRetroGate : Test { :>> id = "dcf8151c-4450-42d4-bca6-b919dd8f4cfa"; :>> title = "Sprint 760 retro gate (autonomous, D0049)"; :>> createdAt = "2026-09-22"; :>> createdBy = "claudeFable5"; :>> method = VerificationMethod::analyze; :>> procedureText = "Retro held; avoidable-issue scan over the sprint: two findings, both tracked. A read-only panelist wrote the repository root by accident and reversed it (issue671, resolver dcPanelistsAreDispatchedIntoAnIsolatedTree): the control was a sentence in a prompt, and the fix is dispatch into an isolated tree. The verdict tally undercounted a round because its regex read prose severities (issue672, resolver dcPanelTallyReadsAMachineTrailer): a count over prose is a stored answer that can disagree with what it summarises, and the fix is a machine trailer the script refuses without. This commit adds dcRunnerDirectionPanelIsRecorded, dcPanelistsAreDispatchedIntoAnIsolatedTree and dcPanelTallyReadsAMachineTrailer."; }
    // RAN: the retro text names dcRunnerDirectionPanelIsRecorded, dcPanelistsAreDispatchedIntoAnIsolatedTree and dcPanelTallyReadsAMachineTrailer, all added by this commit, and both findings are Issues 671 and 672 with those resolvers; keel gate guard --no-receipt -> ALL PASS with retro-backlog among the passes.
    part runnerDirectionPanelSpikeRetroGateR1 : TestResult { :>> id = "e6264ea7-7df5-4282-b481-c5a6ad5b9dfb"; :>> outcome = VerdictKind::proposed; :>> judgedAgainst = "f365cb7a21cf0147a06d4c3c6b70e94e8007eacb"; :>> judgedAt = "2026-09-22"; :>> judgedBy = "claudeFable5"; }
}
