// ProjectDeliveryS745 — Sprint 745: downstream projects whole - five GitHub reports from one downstream migration (GH#86-90, st162-st166) become issue610-issue614, resolved by five backlog tasks under three held Decisions (D0520 shipped claims are held where they are made; D0521 a write emits only what the tree's schema declares; D0522 a record tolerated at the door is tolerated through the run). The human's direction is st167/st168.. EXECUTE. 5 pts.
package ProjectDeliveryS745 {
    private import EngineElement::*;
    private import EngineWork::*;
    private import EngineVerification::*;
    private import EngineRelationships::*;

    #CharteredBy dependency from downstreamProjectsWholeStory to d0520;
    #Delivers dependency from downstreamProjectsWholeStory to dcRatchetOverTheProjectsCorpusIsNeverSeeded;
    #Delivers dependency from downstreamProjectsWholeStory to dcCharterResolvesInBothDecisionDirectories;
    #Delivers dependency from downstreamProjectsWholeStory to dcSourceReferenceReadsTheAdoptersOwnClaims;
    #Delivers dependency from downstreamProjectsWholeStory to dcToleratedRecordsSurviveTheRun;
    #Delivers dependency from downstreamProjectsWholeStory to dcAWriteRefusesTheMemberTheTreesSchemaLacks;
    #CharteredBy dependency from downstreamProjectsWholeStory to d0521;
    #CharteredBy dependency from downstreamProjectsWholeStory to d0522;

    part downstreamProjectsWholeStory : Story {
        :>> id = "c67680ae-9838-4637-b69c-c021bef29118";
        :>> title = "Sprint 745: downstream projects whole - five GitHub reports from one downstream migration (GH#86-90, st162-st166) become issue610-issue614, resolved by five backlog tasks under three held Decisions (D0520 shipped claims are held where they are made; D0521 a write emits only what the tree's schema declares; D0522 a record tolerated at the door is tolerated through the run). The human's direction is st167/st168. (5 pts)";
        :>> createdAt = "2026-09-18"; :>> createdBy = "claudeFable5"; :>> kind = WorkKind::code; :>> priority = WorkPriority::p0; :>> owner = "claudeFable5"; :>> estimatedPoints = 5;
    }

    action def DeliveryRunS745 {
        action storyDownstreamProjectsWhole;
        verification storyDownstreamProjectsWholeDoD : Test { :>> id = "e7483cb7-2f48-4b96-a37a-fb52cb6b420e"; :>> method = VerificationMethod::test; :>> procedureText = "DELIVERED BACKLOG ITEMS: dcRatchetOverTheProjectsCorpusIsNeverSeeded, dcCharterResolvesInBothDecisionDirectories, dcSourceReferenceReadsTheAdoptersOwnClaims, dcToleratedRecordsSurviveTheRun, dcAWriteRefusesTheMemberTheTreesSchemaLacks. DONE MEANS: each task's DoD holds with its own unit tests (the D0388 pairs named in the DoDs); the ladder (validate, check-engine, guard, clippy, the probe pair, suite --touched) is green; the three living-doc citations of check_preconditions point at the function's current lines; CI green at the landing commit."; }
        // RAN: TOUCHED RECEIPT: outcome=pass passed=941 failed=0 seconds=719 at=1789777049 launch=1789776231 (at>launch: ok) stems=['enforcement', 'init', 'migrate', 'onboard', 'surface', 'write'] changed=['enforcement', 'init', 'migrate', 'onboard', 'surface', 'write'] (MATCH) lib=true head=fe57df66 log=./.keel/metrics/touched-1789776328.log test result line: binary=land_gate test=land_refuses_to_push_a_workspace_carrying_a_broken_project millis=288301 verdict=pass (slowest)
        part storyDownstreamProjectsWholeDoDR1 : TestResult { :>> id = "c15358a4-8e9b-4996-b7e8-9fb9f3447edc"; :>> outcome = VerdictKind::pass; :>> judgedAgainst = "fe57df66"; :>> judgedAt = "2026-09-18"; :>> judgedBy = "claudeFable5"; }
    }

    verification downstreamProjectsWholeRefineGate : Test { :>> id = "c2fcbbfe-e4f0-460e-ad90-cef025675c8d"; :>> title = "Sprint 745 refine gate (DoR)"; :>> createdAt = "2026-09-18"; :>> createdBy = "claudeFable5"; :>> method = VerificationMethod::inspect; :>> procedureText = "DoR: five tasks sized together at 5 points (three are one-function changes with tests, two - the guard population and the tolerated-record flow - are a module each); scope is the five DoDs; no blocking dependency; the code for GH#89/#90 arrived from the peer session uncommitted and is verified here, not trusted."; }
    // RAN: LADDER: C:/Users/WilliamWeatherholtz/claude_code/sysmlv2-ai-toolkit/target/release/keel-serve.exe verify . --probe-from C:/Users/WILLIA~1/AppData/Local/Temp/claude/C--Users-WilliamWeatherholtz-claude-code-sysmlv2-ai-toolkit/b43aa4fc-84f7-4c3d-bc35-61eccafbbda8/scratchpad/pair745.txt -> outcome=pass stopped_at=none seconds=811 at=1789777049 (at>launch: ok) validate=pass guard=pass clippy=pass probe=pass touched=pass (from its [[rung]] rows)
    part downstreamProjectsWholeRefineGateR1 : TestResult { :>> id = "4c727b53-4290-48d4-aa2a-5398a7490622"; :>> outcome = VerdictKind::proposed; :>> judgedAgainst = "fe57df66"; :>> judgedAt = "2026-09-18"; :>> judgedBy = "claudeFable5"; }
    verification downstreamProjectsWholeStandupGate : Test { :>> id = "7ec95739-235b-4d1c-9d9a-3b8d217ff1cb"; :>> title = "Sprint 745 standup gate"; :>> createdAt = "2026-09-18"; :>> createdBy = "claudeFable5"; :>> method = VerificationMethod::inspect; :>> procedureText = "Owner claudeFable5. Blocker: none; the peer session that authored the GH#89/#90 code has left the tree. Risk: migrate.rs is edited by both the peer's diff and this sprint's GH#87 change, so the peer's shift of check_preconditions is re-measured after this sprint's edit before the three citations are repointed."; }
    // RAN: LADDER: C:/Users/WilliamWeatherholtz/claude_code/sysmlv2-ai-toolkit/target/release/keel-serve.exe verify . --probe-from C:/Users/WILLIA~1/AppData/Local/Temp/claude/C--Users-WilliamWeatherholtz-claude-code-sysmlv2-ai-toolkit/b43aa4fc-84f7-4c3d-bc35-61eccafbbda8/scratchpad/pair745.txt -> outcome=pass stopped_at=none seconds=811 at=1789777049 (at>launch: ok) validate=pass guard=pass clippy=pass probe=pass touched=pass (from its [[rung]] rows)
    part downstreamProjectsWholeStandupGateR1 : TestResult { :>> id = "d6069372-2f38-427a-84e1-98d23e53366a"; :>> outcome = VerdictKind::proposed; :>> judgedAgainst = "fe57df66"; :>> judgedAt = "2026-09-18"; :>> judgedBy = "claudeFable5"; }
    verification downstreamProjectsWholeImplementGate : Test { :>> id = "03f58f0c-19c2-45c5-9825-6b918f051b53"; :>> title = "Sprint 745 implement gate"; :>> createdAt = "2026-09-18"; :>> createdBy = "claudeFable5"; :>> method = VerificationMethod::test; :>> procedureText = "The implement gate is the change itself under the ladder: keel verify . --probe-from pair745.txt (validate, check-engine, guard, clippy, the pair, suite --touched), stopping at the first red."; }
    // RAN: LADDER: C:/Users/WilliamWeatherholtz/claude_code/sysmlv2-ai-toolkit/target/release/keel-serve.exe verify . --probe-from C:/Users/WILLIA~1/AppData/Local/Temp/claude/C--Users-WilliamWeatherholtz-claude-code-sysmlv2-ai-toolkit/b43aa4fc-84f7-4c3d-bc35-61eccafbbda8/scratchpad/pair745.txt -> outcome=pass stopped_at=none seconds=811 at=1789777049 (at>launch: ok) validate=pass guard=pass clippy=pass probe=pass touched=pass (from its [[rung]] rows)
    part downstreamProjectsWholeImplementGateR1 : TestResult { :>> id = "df86e8cc-7db8-40ef-b641-0075afb43356"; :>> outcome = VerdictKind::pass; :>> judgedAgainst = "fe57df66"; :>> judgedAt = "2026-09-18"; :>> judgedBy = "claudeFable5"; }
    verification downstreamProjectsWholeReviewGate : Test { :>> id = "0c9748f4-e7b9-4a93-b319-2273f2465b50"; :>> title = "Sprint 745 review gate — three passes per D0172"; :>> createdAt = "2026-09-18"; :>> createdBy = "claudeFable5"; :>> method = VerificationMethod::inspect; :>> procedureText = "Verifier receipt read against the five DoDs: every named unit test present and passing, guard source-reference green in this self-build with its population unchanged here, guard activation-manifest green, the migrate unit tests green, the write refusal test green; three passes per D0172 (substance, ceremony, doc-sync: guards.md and the two project-migration docs cite 908-911 or wherever check_preconditions sits after the GH#87 edit)."; }
    // RAN: LADDER: C:/Users/WilliamWeatherholtz/claude_code/sysmlv2-ai-toolkit/target/release/keel-serve.exe verify . --probe-from C:/Users/WILLIA~1/AppData/Local/Temp/claude/C--Users-WilliamWeatherholtz-claude-code-sysmlv2-ai-toolkit/b43aa4fc-84f7-4c3d-bc35-61eccafbbda8/scratchpad/pair745.txt -> outcome=pass stopped_at=none seconds=811 at=1789777049 (at>launch: ok) validate=pass guard=pass clippy=pass probe=pass touched=pass (from its [[rung]] rows)
    part downstreamProjectsWholeReviewGateR1 : TestResult { :>> id = "a1a0c023-4366-41cc-9d1b-102e7b9ee7c7"; :>> outcome = VerdictKind::proposed; :>> judgedAgainst = "fe57df66"; :>> judgedAt = "2026-09-18"; :>> judgedBy = "claudeFable5"; }
    verification downstreamProjectsWholeCloseOutGate : Test { :>> id = "0a6e68d5-60b8-4a71-9c93-a4b3aabac0d5"; :>> title = "Sprint 745 closeOut gate (autonomous, D0049)"; :>> createdAt = "2026-09-18"; :>> createdBy = "claudeFable5"; :>> method = VerificationMethod::inspect; :>> procedureText = "Landed by keel land with the touched set green and CI green at the landing commit; the five issues resolve by their #Resolves edges; GH#86-90 are answered on GitHub with the tracked ids and the held Decisions named."; }
    // RAN: LADDER: C:/Users/WilliamWeatherholtz/claude_code/sysmlv2-ai-toolkit/target/release/keel-serve.exe verify . --probe-from C:/Users/WILLIA~1/AppData/Local/Temp/claude/C--Users-WilliamWeatherholtz-claude-code-sysmlv2-ai-toolkit/b43aa4fc-84f7-4c3d-bc35-61eccafbbda8/scratchpad/pair745.txt -> outcome=pass stopped_at=none seconds=811 at=1789777049 (at>launch: ok) validate=pass guard=pass clippy=pass probe=pass touched=pass (from its [[rung]] rows)
    part downstreamProjectsWholeCloseOutGateR1 : TestResult { :>> id = "3d5c4f96-b5ca-49fd-9ac8-bd93a6e96aed"; :>> outcome = VerdictKind::proposed; :>> judgedAgainst = "fe57df66"; :>> judgedAt = "2026-09-18"; :>> judgedBy = "claudeFable5"; }
    verification downstreamProjectsWholeRetroGate : Test { :>> id = "177becd7-b170-43d1-ae09-dabf16900648"; :>> title = "Sprint 745 retro gate (autonomous, D0049)"; :>> createdAt = "2026-09-18"; :>> createdBy = "claudeFable5"; :>> method = VerificationMethod::analyze; :>> procedureText = "Written at closeOut, after the verifier's first receipt and before the recorder; avoidable issues scanned (issue011), each finding a tracked item or the reason it is not. (1) Guard source-reference was red on every Rust adopter from sprint 743 to this one because no test here ever ran the guard set over an adopter-shaped tree - every scaffold-and-gate test is the self-build's shape. Tracked: issue615 (Medium), resolved by dcAFreshAdopterTreeIsGreenUnderEveryGuard (deploy the embedded engine into a non-self-build root, every guard green there, keyed on the embedded content). (2) The new refusal WriteError::SchemaLacksMember has no WRITE_PATH_REFUSALS row, no census row and no ledger line. Tracked: issue616 (Low), resolved by dcSchemaLacksMemberRefusalIsLedgered. (3) keel onboard's UNRESOLVED CHARTER line tells a first-time adopter to restore an activation.toml from a history that has none. Tracked: issue617 (Low), resolved by dcUnresolvedCharterAdviceFitsAFirstTimeAdopter. (4) migrate held two definitions of separable - the door tolerated an obligation the gate then failed and the clean deleted. Not tracked separately: resolved in this sprint by issue613's fix, one keep list flowing from check_preconditions to the gate, the clean and the marker. (5) The verifier's first ladder stopped at guard because this retro named candidates and no tracked item; the D0131 guard did its work, the items above were then recorded, and the ladder was re-run - not tracked, the control fired as designed. (6) The second verifier receipt read DISCREPANCIES: NONE over a ladder whose own line said touched=fail (one integration test, charter_must_resolve, whose fixture GH#89 made resolvable); the primary read the receipt and fixed the fixture before any recorder was dispatched. Not tracked anew: this is issue490 recurring, still open with resolver dcVerifierReceiptOutcomeIsRenderedNotTyped (the receipt verdict rendered from the receipt files, never typed)."; }
    // RAN: LADDER: C:/Users/WilliamWeatherholtz/claude_code/sysmlv2-ai-toolkit/target/release/keel-serve.exe verify . --probe-from C:/Users/WILLIA~1/AppData/Local/Temp/claude/C--Users-WilliamWeatherholtz-claude-code-sysmlv2-ai-toolkit/b43aa4fc-84f7-4c3d-bc35-61eccafbbda8/scratchpad/pair745.txt -> outcome=pass stopped_at=none seconds=811 at=1789777049 (at>launch: ok) validate=pass guard=pass clippy=pass probe=pass touched=pass (from its [[rung]] rows)
    part downstreamProjectsWholeRetroGateR1 : TestResult { :>> id = "d5e19b6c-4200-4139-9a5b-58721cb256c2"; :>> outcome = VerdictKind::proposed; :>> judgedAgainst = "fe57df66"; :>> judgedAt = "2026-09-18"; :>> judgedBy = "claudeFable5"; }
}
