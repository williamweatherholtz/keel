// ProjectDeliveryS748 — Sprint 748: The four modules beside main.rs move to the members that own them (D0513, accepted): adherence.rs and history.rs, the two audits that re-derive the gate verdict from the git tree, become members/keel-guards/src files under the enforcement lock's directory prefix; cursor.rs (keel advance) and enroll.rs (keel enroll) become members/keel-process/src files; the keel-cli/src/adherence.rs entry is retired from GUARD_SOURCE_FILES and keel-cli's lib.rs re-exports the four at their old paths, so keel-cli/src holds main.rs and lib.rs only. One transform, scripts/extract_staying_modules.py, makes every move. EXECUTE.. EXECUTE. 3 pts.
package ProjectDeliveryS748 {
    private import EngineElement::*;
    private import EngineWork::*;
    private import EngineVerification::*;
    private import EngineRelationships::*;

    #CharteredBy dependency from fourStayingModulesAreMembersStory to d0513;
    #Delivers dependency from fourStayingModulesAreMembersStory to dcTheFourStayingModulesAreMembers;

    part fourStayingModulesAreMembersStory : Story {
        :>> id = "16bbd035-90a3-4b4b-93d0-0b67e1672fb6";
        :>> title = "Sprint 748: The four modules beside main.rs move to the members that own them (D0513, accepted): adherence.rs and history.rs, the two audits that re-derive the gate verdict from the git tree, become members/keel-guards/src files under the enforcement lock's directory prefix; cursor.rs (keel advance) and enroll.rs (keel enroll) become members/keel-process/src files; the keel-cli/src/adherence.rs entry is retired from GUARD_SOURCE_FILES and keel-cli's lib.rs re-exports the four at their old paths, so keel-cli/src holds main.rs and lib.rs only. One transform, scripts/extract_staying_modules.py, makes every move. EXECUTE. (3 pts)";
        :>> createdAt = "2026-09-19"; :>> createdBy = "claudeFable5"; :>> kind = WorkKind::code; :>> priority = WorkPriority::p0; :>> owner = "claudeFable5"; :>> estimatedPoints = 3;
    }

    action def DeliveryRunS748 {
        action storyFourStayingModulesAreMembers;
        verification storyFourStayingModulesAreMembersDoD : Test { :>> id = "5f741b88-77c6-4a42-a52e-a0fa812869c1"; :>> method = VerificationMethod::test; :>> procedureText = "DELIVERED BACKLOG ITEM: dcTheFourStayingModulesAreMembers. DONE MEANS: the task's DoD passes as written - ls keel-cli/src lists lib.rs and main.rs; is_enforcement_surface holds members/keel-guards/src/adherence.rs and history.rs locked and keel-cli/src/adherence.rs not; the moved test modules pass in their new crates (cargo test -p keel-guards --lib adherence:: history::, -p keel-process --lib cursor:: enroll::); keel --help byte-identical to the pre-move capture (cmp); keel version's guard line unchanged at 77; cargo clippy --release --workspace --all-targets -D warnings clean; scripts/modgraph.py --check, scripts/module_home.py --probe and scripts/verb_homes.py --check exit 0 and module_home names the four new homes; the transform is dry-run by default, --apply, idempotent (a second run reports already applied) and prints its reconciliation line; the known-negative - one constraint def removed from .engine/rules/guard-constraints.sysml in an unsigned commit of a scratch clone - is refused by keel audit adherence from its new crate naming guard:ceremony -> absent, exit 1; the doc-sync rides the commit (guards.md process-change row, the code registry's history.rs element, the two member lib.rs docs)."; }
        // RAN: keel suite --touched: pass - 929 passed in 991s
        part storyFourStayingModulesAreMembersDoDR1 : TestResult { :>> id = "52c65d2c-d6d0-4627-b872-f91cb9d930ed"; :>> outcome = VerdictKind::pass; :>> judgedAgainst = "8ab4ebef"; :>> judgedAt = "2026-09-19"; :>> judgedBy = "claudeFable5"; }
    }

    verification fourStayingModulesAreMembersRefineGate : Test { :>> id = "e48bd0de-a08f-44ab-b9a4-c347dc2028a8"; :>> title = "Sprint 748 refine gate (DoR)"; :>> createdAt = "2026-09-19"; :>> createdBy = "claudeFable5"; :>> method = VerificationMethod::inspect; :>> procedureText = "DoR: one task, 3 points - four whole-file git renames with nineteen crate:: path rewrites, one locked-constant edit and its test, two member lib.rs declarations, four re-exports, a doc row and a registry path, all through one transform. Charter d0513, accepted by the human on 2026-09-18 with process-change marked, so the process-change guard's lock on enforcement.rs and the guards member is discharged by this record (D0465). No blocking dependency: dcSharedHelpersDescendBelowTheVerbs passed at b93cb8de (sprint 740). The D0388 pair is two cargo test lines in pair748.txt, written before the tree was read: the lock test for the two new paths, and the audit's weakening-rank test in its new crate."; }
    // RAN: validate=pass
    part fourStayingModulesAreMembersRefineGateR1 : TestResult { :>> id = "176b4a17-9fa8-4b04-bcec-fa2741b68a18"; :>> outcome = VerdictKind::proposed; :>> judgedAgainst = "8ab4ebef"; :>> judgedAt = "2026-09-19"; :>> judgedBy = "claudeFable5"; }
    verification fourStayingModulesAreMembersStandupGate : Test { :>> id = "88aa47c5-2bbf-4d91-94b5-9ceb1fcbea93"; :>> title = "Sprint 748 standup gate"; :>> createdAt = "2026-09-19"; :>> createdBy = "claudeFable5"; :>> method = VerificationMethod::inspect; :>> procedureText = "Owner claudeFable5. Blocker: none. Risk: adherence.rs reads crate::workspace::discover, which is keel-git's projects::discover since sprint 740 and re-exported by keel-process - a member the guards sit below - so the rewrite targets keel_git::projects, never keel_process; the transform's table names that target and its reconciliation counts the two sites. A second risk: retiring the file entry from GUARD_SOURCE_FILES must unlock nothing - the file is under GUARD_SOURCE_DIRS by construction, and the lock test asserts both new paths locked in the same edit. The ladder runs detached; the verifier climbs it and writes the receipt."; }
    // RAN: validate=pass guard=pass
    part fourStayingModulesAreMembersStandupGateR1 : TestResult { :>> id = "fb321163-8409-44f1-8fe0-ceef13b90cdd"; :>> outcome = VerdictKind::proposed; :>> judgedAgainst = "8ab4ebef"; :>> judgedAt = "2026-09-19"; :>> judgedBy = "claudeFable5"; }
    verification fourStayingModulesAreMembersImplementGate : Test { :>> id = "ed2a97cd-4085-4f93-8381-199bba4e4eeb"; :>> title = "Sprint 748 implement gate"; :>> createdAt = "2026-09-19"; :>> createdBy = "claudeFable5"; :>> method = VerificationMethod::test; :>> procedureText = "The implement gate is the change itself under the ladder: keel verify . --probe-from pair748.txt (validate, check-engine, guard with 77, clippy, the pair, suite --touched), stopping at the first red; plus the scratch-clone known-negative run by the primary with the rebuilt binary and quoted in the DoD result."; }
    // RAN: validate=pass guard=pass clippy=pass
    part fourStayingModulesAreMembersImplementGateR1 : TestResult { :>> id = "d8f4540a-e72a-4fc8-86b5-cd7f02e99f51"; :>> outcome = VerdictKind::pass; :>> judgedAgainst = "8ab4ebef"; :>> judgedAt = "2026-09-19"; :>> judgedBy = "claudeFable5"; }
    verification fourStayingModulesAreMembersReviewGate : Test { :>> id = "2a6bdf01-0df1-4151-a85e-ded8fc049a41"; :>> title = "Sprint 748 review gate — three passes per D0172"; :>> createdAt = "2026-09-19"; :>> createdBy = "claudeFable5"; :>> method = VerificationMethod::inspect; :>> procedureText = "Verifier receipt read against the DoD: the lock test and the moved tests pass in their new crates; the pair's positive and negative each exit 0; validate, check-engine, guard, clippy, sync-claude --check clean; three passes per D0172 (substance: the four files in their members, the lock constant, the re-exports; ceremony: this record, the DoD result with its RAN receipt, the gates; doc-sync: guards.md, the code registry element, the member lib.rs docs, the transform's docstring)."; }
    // RAN: probe=pass touched=pass
    part fourStayingModulesAreMembersReviewGateR1 : TestResult { :>> id = "c2852aa3-4510-47a1-be58-e3ee264a5915"; :>> outcome = VerdictKind::proposed; :>> judgedAgainst = "8ab4ebef"; :>> judgedAt = "2026-09-19"; :>> judgedBy = "claudeFable5"; }
    verification fourStayingModulesAreMembersCloseOutGate : Test { :>> id = "2bbf5a1a-0b19-4f64-9b89-5a5dec228d8c"; :>> title = "Sprint 748 closeOut gate (autonomous, D0049)"; :>> createdAt = "2026-09-19"; :>> createdBy = "claudeFable5"; :>> method = VerificationMethod::inspect; :>> procedureText = "Landed by keel land with the touched set green and CI concluding success at the landing commit; scripts/verb_homes.py --check exits 0 so dcKeelCliIsThinDispatch's dependency is met, read from keel show whats-next."; }
    // RAN: outcome=pass passed=929 failed=0 seconds=991
    part fourStayingModulesAreMembersCloseOutGateR1 : TestResult { :>> id = "943b2a3a-b84f-485b-9a3b-cedd8a4325e9"; :>> outcome = VerdictKind::proposed; :>> judgedAgainst = "8ab4ebef"; :>> judgedAt = "2026-09-19"; :>> judgedBy = "claudeFable5"; }
    verification fourStayingModulesAreMembersRetroGate : Test { :>> id = "9a1b0b76-592a-4816-8e39-d26de6048748"; :>> title = "Sprint 748 retro gate (autonomous, D0049)"; :>> createdAt = "2026-09-19"; :>> createdBy = "claudeFable5"; :>> method = VerificationMethod::analyze; :>> procedureText = "Three findings, avoidable issues scanned (issue011). Finding 1: the first known-negative for keel audit adherence ran in a scratch clone whose checkout had failed (Filename too long at the scratchpad path); git commit -a there recorded 2122 deletions and the audit named every guard absent, exit 1 - a refusal that looked like the negative holding and was not; the diff stat was the only sign. Tracked: issue630 (Low) with resolver dcScratchCloneProbeAssertsItsPlant, both added by this commit - a probe helper that clones with core.longpaths, refuses a dirty clone, stages one path and prints the probe commit's stat before running anything. Finding 2: the task's DoD clause 'no module there exceeds 400 lines' is met only vacuously - keel-cli/src holds lib.rs and main.rs, and main.rs is 4509 lines; no new item, because dcKeelCliIsThinDispatch's DoD already owns main.rs's size and this sprint's DoD result says so rather than passing the clause silently. Finding 3: the pre-move --help capture came from the keel-serve.exe copy built at abe64e84 plus the uncommitted tree, code-identical to HEAD for the CLI surface; no item - the cmp against the post-move build is the check and it held byte-for-byte."; }
    // RAN: keel suite --touched: pass - 929 passed in 991s
    part fourStayingModulesAreMembersRetroGateR1 : TestResult { :>> id = "fa2a2023-004f-4a9d-837c-5778508edb9f"; :>> outcome = VerdictKind::proposed; :>> judgedAgainst = "8ab4ebef"; :>> judgedAt = "2026-09-19"; :>> judgedBy = "claudeFable5"; }
}
