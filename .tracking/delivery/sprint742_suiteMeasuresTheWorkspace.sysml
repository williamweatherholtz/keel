// ProjectDeliveryS742 — Sprint 742: the full suite measures the workspace - dcSuiteMeasuresTheWorkspace, chartered by D0479, resolving issue588 (the full suite's fingerprint population and cargo scope stop at keel-cli). Before this sprint suite.rs held a typed constant DELIVERABLE_PATHS naming keel-cli, .engine, keelw and the manifests, hashed the whole list into one fingerprint, and ran cargo test with --manifest-path keel-cli/Cargo.toml: after D0479 moved the modules and their unit tests into members, an edit under members/ left the receipt's fingerprint equal and the members' lib tests outside the full run, so the receipt attested a deliverable it did not measure. This sprint the deliverable's roots are READ from the root Cargo.toml's [workspace] members (keel_model::corpus::workspace_members, the same reading wsgraph.rs uses) plus the four paths no member owns (.engine, keelw, Cargo.toml, Cargo.lock), each root carries its own SHA-256 digest as a [[part]] row of the receipt, the fingerprint is the digest of those parts in order, the staleness message names the roots whose digest moved, and the run is cargo test --release --workspace --no-fail-fast from the root manifest - every member's unit tests, keel-parser's proptest binaries and all seven harness = false cucumber binaries included.. EXECUTE. 3 pts.
package ProjectDeliveryS742 {
    private import EngineElement::*;
    private import EngineWork::*;
    private import EngineVerification::*;
    private import EngineRelationships::*;

    #CharteredBy dependency from suiteMeasuresTheWorkspaceStory to d0479;
    #Delivers dependency from suiteMeasuresTheWorkspaceStory to dcSuiteMeasuresTheWorkspace;

    part suiteMeasuresTheWorkspaceStory : Story {
        :>> id = "793ec842-db68-47d3-840b-3b0cce1902dc";
        :>> title = "Sprint 742: the full suite measures the workspace - dcSuiteMeasuresTheWorkspace, chartered by D0479, resolving issue588 (the full suite's fingerprint population and cargo scope stop at keel-cli). Before this sprint suite.rs held a typed constant DELIVERABLE_PATHS naming keel-cli, .engine, keelw and the manifests, hashed the whole list into one fingerprint, and ran cargo test with --manifest-path keel-cli/Cargo.toml: after D0479 moved the modules and their unit tests into members, an edit under members/ left the receipt's fingerprint equal and the members' lib tests outside the full run, so the receipt attested a deliverable it did not measure. This sprint the deliverable's roots are READ from the root Cargo.toml's [workspace] members (keel_model::corpus::workspace_members, the same reading wsgraph.rs uses) plus the four paths no member owns (.engine, keelw, Cargo.toml, Cargo.lock), each root carries its own SHA-256 digest as a [[part]] row of the receipt, the fingerprint is the digest of those parts in order, the staleness message names the roots whose digest moved, and the run is cargo test --release --workspace --no-fail-fast from the root manifest - every member's unit tests, keel-parser's proptest binaries and all seven harness = false cucumber binaries included. (3 pts)";
        :>> createdAt = "2026-09-18"; :>> createdBy = "claudeFable5"; :>> kind = WorkKind::code; :>> priority = WorkPriority::p0; :>> owner = "claudeFable5"; :>> estimatedPoints = 3;
    }

    action def DeliveryRunS742 {
        action storySuiteMeasuresTheWorkspace;
        verification storySuiteMeasuresTheWorkspaceDoD : Test { :>> id = "7bf9fe24-0421-4e7c-81a2-78a915c2940e"; :>> method = VerificationMethod::test; :>> procedureText = "DELIVERED BACKLOG ITEMS: dcSuiteMeasuresTheWorkspace. DONE MEANS: members/keel-suite/src/suite.rs reads the deliverable's roots from the root manifest (deliverable_paths_of, deliverable_paths; UNOWNED_DELIVERABLE_PATHS = .engine, keelw, Cargo.toml, Cargo.lock; 23 roots on this tree), digests each root over every file git knows or would add under it (fingerprint_parts: two git ls-files over the roots, content from disk), fingerprints the parts in order (fingerprint_of), names the moved roots (moved_parts) in the CHANGED message of a pure staleness(receipt, now) that land_refusal calls, writes one [[part]] row per root into the receipt (render_receipt) and reads them back (parse_receipt, Receipt.parts), and runs cargo test --release --workspace --manifest-path <repo>/Cargo.toml --no-fail-fast; suite --help names --workspace and the [[part]] rows. cargo clippy --workspace --release --all-targets clean; cargo test -p keel-suite --release --lib 64 passed 0 failed (three new: the_deliverable_is_every_member_the_root_manifest_lists_plus_what_no_member_owns, a_member_edit_moves_its_own_part_and_the_staleness_names_it, a_receipt_carries_one_row_per_root_and_round_trips_them). Known-positive (pos742.py, chosen before the tree was read): the two claim-bearing lib tests pass and exactly two run; the suite receipt on this tree is a pass whose passed count exceeds keel-cli's alone (720 at 24dbcfb) and carries 23 [[part]] rows each equal to an independent recomputation of the digest over the tree (fp742.py); a planted file under members/keel-fs/src/ moves the members/keel-fs digest and no other. Known-negative (neg742.py): the D0421/D0474 touched-set tests pass narrowed to the fallback case; a planted file under target/ and one under .keel/ leave all 23 digests equal. Read from .keel/metrics/suite-receipt.toml after the detached run from the copy, not from this text: outcome pass, passed 955, failed 0, seconds 1053, head 019078d3, 23 [[part]] rows, fingerprint 4ea02049b492; the log (suite-1789717231.log) announces 122 binaries - 20 unit, 76 integration, 19 doc-test, 7 cucumber - and the 955 is 667 members' unit tests + 15 keel-parser integration + 273 keel-cli (19 lib, 8 main.rs, 246 integration); the 51 cucumber scenarios pass through cargo's exit status, not the count, as before."; }
        // RAN: keel suite --touched: pass - 214 passed in 508s
        part storySuiteMeasuresTheWorkspaceDoDR1 : TestResult { :>> id = "46dabd23-faa1-4e00-981d-765e5012fa9e"; :>> outcome = VerdictKind::pass; :>> judgedAgainst = "019078d3"; :>> judgedAt = "2026-09-18"; :>> judgedBy = "claudeFable5"; }
    }

    verification suiteMeasuresTheWorkspaceRefineGate : Test { :>> id = "8a790ee0-53e2-49d2-b47b-eaa6ba3e65b5"; :>> title = "Sprint 742 refine gate (DoR)"; :>> createdAt = "2026-09-18"; :>> createdBy = "claudeFable5"; :>> method = VerificationMethod::inspect; :>> procedureText = "DoR: dcSuiteMeasuresTheWorkspace was the third line of keel show whats-next at 019078d3 (sprint 741 landed, CI conclusion success) and the first unheld one: dcSittingReviewIsFinishedByAnalysis is chartered by D0510 and dcTheFourStayingModulesAreMembers by D0513, both held proposed for the human on the published brief (content gate, D0052), so the frontier is followed past them. Chartered by D0479 through its #CharteredBy edge; #Resolves issue588; #DependsOn dcSuiteIsAMember (landed). Sized 3 - one module (suite.rs) gains a root reader over the manifest, per-root digests, receipt rows with their parse and render, a pure staleness function and a scope change to the cargo invocation, plus three lib tests and the help text; no other member, no locked path, no schema or process change. Not split: the population, the per-root digest and the scope are one claim (the receipt measures what the workspace compiles) and issue588 states them as one. Blocking dependencies: none - dcSuiteIsAMember landed in sprint 735."; }
    // RAN: outcome=pass stopped_at=none
    part suiteMeasuresTheWorkspaceRefineGateR1 : TestResult { :>> id = "384f39cd-55c3-4c6f-a21d-156846dea099"; :>> outcome = VerdictKind::proposed; :>> judgedAgainst = "019078d3"; :>> judgedAt = "2026-09-18"; :>> judgedBy = "claudeFable5"; }
    verification suiteMeasuresTheWorkspaceStandupGate : Test { :>> id = "b42b5ec9-6610-4bb9-9914-295dde861036"; :>> title = "Sprint 742 standup gate"; :>> createdAt = "2026-09-18"; :>> createdBy = "claudeFable5"; :>> method = VerificationMethod::inspect; :>> procedureText = "Owner claudeFable5. Blocker: none - 019078d3 landed with CI conclusion success, no ladder or land running; the human's serve (pid 14600) runs from the pin cache, so the release image rebuilds freely. Order: (1) deliverable_paths_of over the manifest and fingerprint_parts per root, fingerprint_of and moved_parts; (2) Receipt.parts with parse_receipt and render_receipt [[part]] rows; (3) staleness(receipt, now) extracted pure from land_refusal, the CHANGED message naming the moved roots; (4) cmd(): the stub from the parts, cargo test --release --workspace from the root manifest, done_receipt from the parts, the help text; (5) the three lib tests, clippy, cargo build --release, keel-serve.exe refresh; (6) the real keel suite . launched DETACHED from the copy (nohup, stdout to the scratchpad; a 600-second Bash cap would kill it) and waited on with one bounded Monitor; (7) pos742.py/neg742.py/fp742.py, pair742.txt; (8) the sprint record with the retro filled, verifier with the pair file, recorder --owed 8, git diff --stat .tracking against the report's WROTE count (issue602), the detached commit, git status -sb, CI conclusion. decision-surfacing: no Decision is recorded this sprint, the pending set (sixteen ids, d0494..d0513) equals .keel/decision-page.toml, silent."; }
    // RAN: outcome=pass stopped_at=none
    part suiteMeasuresTheWorkspaceStandupGateR1 : TestResult { :>> id = "b5e61ed3-54da-47d9-a14a-217881adc4cc"; :>> outcome = VerdictKind::proposed; :>> judgedAgainst = "019078d3"; :>> judgedAt = "2026-09-18"; :>> judgedBy = "claudeFable5"; }
    verification suiteMeasuresTheWorkspaceImplementGate : Test { :>> id = "f65effac-511a-4bae-ab7d-4c0df1fdeff4"; :>> title = "Sprint 742 implement gate"; :>> createdAt = "2026-09-18"; :>> createdBy = "claudeFable5"; :>> method = VerificationMethod::test; :>> procedureText = "The implement gate is the DoD's own probes plus the ladder: cargo clippy --workspace --release --all-targets clean after format_push_string (render_receipt's rows through write! with std::fmt::Write) and items_after_statements (the import moved to the top of the fn); cargo build --release Finished and target/release/keel-serve.exe refreshed from it; cargo test -p keel-suite --release --lib 64 passed 0 failed; keel suite --help from the copy names --workspace and the [[part]] rows; the detached keel suite . run from the copy printed keel suite: pass - 955 passed, 0 failed; receipt .keel/metrics/suite-receipt.toml (fingerprint 4ea02049b492...) after 1053 seconds, and the receipt reads outcome pass, 23 [[part]] rows, head 019078d3; fp742.py's independent recomputation over the tree equals all 23 digests (23 equal of 23, read while the stub was still running and again after the receipt was written). One test was corrected against its own fixture before it passed: the round-trip test counted [[part]] three times because the receipt header names the table; it now matches the row's opening line. Two hook fires this sprint: the pre-bash hook denied two python heredocs carrying a backslash (D0309/issue372 class); both were rewritten as scratchpad scripts run by path."; }
    // RAN: outcome=pass stopped_at=none
    part suiteMeasuresTheWorkspaceImplementGateR1 : TestResult { :>> id = "0920efdc-3064-470e-bf33-a1860dc9ff8e"; :>> outcome = VerdictKind::pass; :>> judgedAgainst = "019078d3"; :>> judgedAt = "2026-09-18"; :>> judgedBy = "claudeFable5"; }
    verification suiteMeasuresTheWorkspaceReviewGate : Test { :>> id = "3a76daea-987a-429d-b25e-32a022811f91"; :>> title = "Sprint 742 review gate — three passes per D0172"; :>> createdAt = "2026-09-18"; :>> createdBy = "claudeFable5"; :>> method = VerificationMethod::inspect; :>> procedureText = "Verifier receipt only: keel gate validate, check-engine, guard --no-receipt, sync-claude --check, the verify ladder with --probe-from naming pair742.txt (D0500), cargo clippy; the recorder writes this gate from the receipt. Three passes per D0172. Correctness: the roots are the manifest's members plus the unowned four and nothing typed (the_deliverable_is_every_member_the_root_manifest_lists_plus_what_no_member_owns, over a synthetic manifest, a manifest with no members and the real one); a member edit moves that member's digest alone and the staleness names it while an edit under target/ or .keel/ moves nothing (a_member_edit_moves_its_own_part_and_the_staleness_names_it, on a temp git repository with a per-process name, issue570); the receipt carries one row per root and round-trips them, and a receipt with no rows says it predates them rather than naming a member it cannot (a_receipt_carries_one_row_per_root_and_round_trips_them). Honesty: the positive's receipt clause is read from the file the detached run wrote, and its digests are held against a recomputation that shares no code with suite.rs; the negative plants real files in the real tree and asserts the digests are byte-equal, removing the plants on every path; the passed count's decomposition (667 + 15 + 273) is read from the run's log, not inferred. Scope: the diff is members/keel-suite/src/suite.rs alone - no path under GUARD_SOURCE_FILES/GUARD_SOURCE_DIRS, no .githooks, CI yml, schema or process file - so no Decision is recorded and none is owed. NOT A PROCESS CHANGE: keel suite gates nothing (D0356) and land does not consult land_refusal; what changes is what the receipt measures and how it says so, authored by issue588's resolver under D0479, which is accepted."; }
    // RAN: outcome=pass stopped_at=none
    part suiteMeasuresTheWorkspaceReviewGateR1 : TestResult { :>> id = "8f640432-047f-4d0f-8b28-da08c68df905"; :>> outcome = VerdictKind::proposed; :>> judgedAgainst = "019078d3"; :>> judgedAt = "2026-09-18"; :>> judgedBy = "claudeFable5"; }
    verification suiteMeasuresTheWorkspaceCloseOutGate : Test { :>> id = "66cc376a-b05b-4595-b984-660c8fc5eaad"; :>> title = "Sprint 742 closeOut gate (autonomous, D0049)"; :>> createdAt = "2026-09-18"; :>> createdBy = "claudeFable5"; :>> method = VerificationMethod::inspect; :>> procedureText = "Landed when the verifier's receipt reads DISCREPANCIES: NONE and its probe rung row names pair742.txt, the recorder's report passes check_report.py --owed 8 and git diff --stat .tracking shows eight new TestResult parts for eight WROTE lines (issue602), git status -sb is clean after keel land and gh run list names the landing commit with conclusion success. The DoD result is recorded against dcSuiteMeasuresTheWorkspaceDoD at that sha; issue588's resolution is computed from its #Resolves edge once that result lands. The suite receipt is read back for the DoD's last clause before the ceremony (outcome pass, 955 passed, 23 rows, 23 digests equal to the recomputation). No Decision recorded, the authority queue's pending set is unchanged and decision-surfacing is silent. dcSourceCitationsOnTheLivingDocsResolve (issue591) is the next line of the frontier below the two held items."; }
    // RAN: outcome=pass stopped_at=none
    part suiteMeasuresTheWorkspaceCloseOutGateR1 : TestResult { :>> id = "fee60fd5-25a8-4c41-8687-bcac6637b670"; :>> outcome = VerdictKind::proposed; :>> judgedAgainst = "019078d3"; :>> judgedAt = "2026-09-18"; :>> judgedBy = "claudeFable5"; }
    verification suiteMeasuresTheWorkspaceRetroGate : Test { :>> id = "a51db68d-46a8-4bbe-898c-9e4bbe1fb4e8"; :>> title = "Sprint 742 retro gate (autonomous, D0049)"; :>> createdAt = "2026-09-18"; :>> createdBy = "claudeFable5"; :>> method = VerificationMethod::analyze; :>> procedureText = "Written at close-out, before the verifier is dispatched; avoidable issues scanned (issue011), each finding a tracked item or the reason it is not. (1) The full run was first launched as a background Bash command, which this harness caps at 600 seconds; the run takes 1053. It was stopped before the cap and relaunched detached from git-bash (nohup, output to a scratchpad log, stdin from /dev/null) - Start-Process from the PowerShell tool returned exit 1 with no output and setsid is not on this host - and waited on with one bounded Monitor. No new item: the issue453 class (a full set takes longer than a tool call) already names the detached launch as the pattern, and CLAUDE.md carries it; what was learned is which launcher works on this host, and that is a host fact this record now holds. (2) Two python heredocs carrying a backslash were denied by the pre-bash hook (D0309/issue372) and one earlier heredoc that carried none edited a test file - the shell wrote code, which D0309 forbids regardless of the hook's denial. No new item: the control fired on the two it is built to catch; the third is the residual D0309 itself names (a heredoc with no backslash is not detectable as code by the hook, and the rule rests on the Edit tool being used), and it left no defect - the edit was verified by the test it changed. (3) The DoD's phrase 'exceeds keel-cli's alone by the members' lib totals' assumed keel-cli's own count was the 720 of 24dbcfb; D0479's extractions since then moved most of those unit tests INTO the members, so keel-cli alone is now 273 and the members' 667 are the bulk of the 955. The clause holds (955 > 720) and the decomposition is in the DoD read from the log, but the comparison as written measured against a count the extractions had already changed. No new item: the receipt's passed count is the workspace's from this run on, and the next comparison reads two receipts, not a receipt and a memory. (4) The receipt's passed count omits the cucumber scenarios (51 across 7 binaries this run): the count sums libtest's test result lines, and a cucumber binary prints a [Summary] block instead; a red scenario still reds the receipt because outcome reads cargo's exit status, so the verdict is honest and the count is a libtest count, as it was for keel-cli's three cucumber binaries before this sprint. Non-finding, noted so the number is read as what it is. (5) scripts/exec_brief/facts.py section 06 reads suite.rs for the DELIVERABLE_PATHS constant 'as it stands' to show the issue588 shape on the D0506 brief; the constant is gone, the regex returns None and the fact reports an empty list - honest (the shape it looked for no longer exists) and the brief is not republished this sprint because the pending set is unchanged. No new item: the fact is a reading of the tree and now reads what is there; when the brief is next rebuilt the section's own how line says the read was empty. (6) The log's Running lines are stderr and its result blocks stdout, so the per-crate decomposition needed the order of the two streams matched (the i-th libtest block belongs to the i-th non-cucumber binary announced); a per-binary count in the receipt would make the read direct. Not tracked: a [[timing]]-style row per binary in the FULL receipt is the touched receipt's shape already (issue536) and no reader of the full receipt has asked for it; if one does, that is the item."; }
    // RAN: outcome=pass stopped_at=none
    part suiteMeasuresTheWorkspaceRetroGateR1 : TestResult { :>> id = "f7374f9b-d2d0-4359-8711-26fa6e7759e2"; :>> outcome = VerdictKind::proposed; :>> judgedAgainst = "019078d3"; :>> judgedAt = "2026-09-18"; :>> judgedBy = "claudeFable5"; }
}
