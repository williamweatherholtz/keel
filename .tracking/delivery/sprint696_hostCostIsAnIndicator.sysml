// ProjectDeliveryS696 — Sprint 696: Resolve issue442: the stop-hook p90 and the git-facts byte length become computed Indicators with declared triggers, so a host cost that was measured every fire and read by no one surfaces in keel show indicators and orient's burndown when it grows (D0389, D0333). EXECUTE; 2 pts; dcHookLatencyIsAnIndicator; the thresholds are D0468 (held).. EXECUTE. 2 pts.
package ProjectDeliveryS696 {
    private import EngineElement::*;
    private import EngineWork::*;
    private import EngineVerification::*;
    private import EngineRelationships::*;

    #CharteredBy dependency from hostCostIsAnIndicatorStory to d0468;

    part hostCostIsAnIndicatorStory : Story {
        :>> id = "581d056f-ce46-4b25-b5aa-2bd42c7e1331";
        :>> title = "Sprint 696: Resolve issue442: the stop-hook p90 and the git-facts byte length become computed Indicators with declared triggers, so a host cost that was measured every fire and read by no one surfaces in keel show indicators and orient's burndown when it grows (D0389, D0333). EXECUTE; 2 pts; dcHookLatencyIsAnIndicator; the thresholds are D0468 (held). (2 pts)";
        :>> createdAt = "2026-09-13"; :>> createdBy = "claudeFable5"; :>> kind = WorkKind::code; :>> priority = WorkPriority::p0; :>> owner = "claudeFable5"; :>> estimatedPoints = 2;
    }

    action def DeliveryRunS696 {
        action storyHostCostIsAnIndicator;
        verification storyHostCostIsAnIndicatorDoD : Test { :>> id = "9c9c5d76-9b34-41e2-acdd-ea2f5d9505c4"; :>> method = VerificationMethod::test; :>> procedureText = "DELIVERED: reports::metric_value answers hook_stop_p90_ms (pm::latency p90 over pm::recent_event_ms(root, 'stop', 25) - the last 25 stop fires of .keel/metrics/hooks.jsonl, nearest rank) and git_facts_bytes (gitfacts::cache_bytes: the file's length, 0 when absent), both before any model build. .tracking/indicators.sysml carries hookLatencyIndicator (ms) and gitFactsSizeIndicator (bytes), goal minimize, method computed, each informing d0389. indicator-triggers.toml declares above = 10000 for the hook and above = 8000000 for the cache with the work each surfaces named (issue520 / dcDecisionScaffoldingIndexesItsEdgesOnce; the one-head rule). keel show indicators lists both with a live value equal to an independent read of the same ledger and file; the D0388 pair holds in both surfaces; the guard set stays green; pm.rs carries a unit test for the sample window."; }
        // RAN: cargo test --release --lib pm::tests::the_recent_sample_is_the_last_n_fires_of_one_event -> 1 passed 0 failed; cargo clippy --release -p keel-cli --all-targets -- -D warnings -> exit 0; cargo build --release -> exit 0; keel show indicators . -> hookLatencyIndicator latest 14125.00 ms trigger above 10000 crossed true, gitFactsSizeIndicator latest 4069615.00 bytes trigger above 8000000 crossed false, equal to an independent python read of the same ledger and file (p90 14125, bytes 4069615); D0388 pair: thresholds 10000/4000000 -> both indicators in indicators.triggered AND orient.burndown.triggers, thresholds 20000/8000000 -> neither in either, contract restored byte-for-byte -> PAIR HOLDS; keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
        part storyHostCostIsAnIndicatorDoDR1 : TestResult { :>> id = "2b1a1379-59ea-4741-9038-b1ab806d3946"; :>> outcome = VerdictKind::pass; :>> judgedAgainst = "ce41db3"; :>> judgedAt = "2026-09-13"; :>> judgedBy = "claudeFable5"; }
    }

    verification hostCostIsAnIndicatorRefineGate : Test { :>> id = "c70355e7-7b95-465c-9742-2aebebb608de"; :>> title = "Sprint 696 refine gate (DoR)"; :>> createdAt = "2026-09-13"; :>> createdBy = "claudeFable5"; :>> method = VerificationMethod::inspect; :>> procedureText = "Chartered by D0468 (proposed, process-change marker: the trigger contract is a keystone-locked path, so the two thresholds are the co-committed marked Decision; the indicators gate nothing). Two points: two small readers, two metric keys, two items, two trigger sections, one unit test, one live pair. DoR: dcHookLatencyIsAnIndicatorDoD names both indicators, the direction and the pair. Not a fork: the DoD fixed the design; the threshold values are the judgment D0468 records with their anchors."; }
    // RAN: keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
    part hostCostIsAnIndicatorRefineGateR1 : TestResult { :>> id = "b97a5e76-2fd1-45a0-bebe-de5f8fad4669"; :>> outcome = VerdictKind::proposed; :>> judgedAgainst = "ce41db3"; :>> judgedAt = "2026-09-13"; :>> judgedBy = "claudeFable5"; }
    verification hostCostIsAnIndicatorStandupGate : Test { :>> id = "2ca3ef50-bbfa-4cf7-8aec-a72b6bf6ecd0"; :>> title = "Sprint 696 standup gate"; :>> createdAt = "2026-09-13"; :>> createdBy = "claudeFable5"; :>> method = VerificationMethod::inspect; :>> procedureText = "Order: read the live values independently first (scratch live.py over the ledger and the file: p90 14125 ms over the last 25 stop fires, 4 055 880 then 4 069 615 bytes) so the Rust has known values to match; patch pm.rs / gitfacts.rs / reports.rs / indicators.sysml / indicator-triggers.toml from one scripted edit with asserted anchors; cargo test the window, clippy -D warnings, release build, copy to the serve image; show indicators against the independent read; the D0388 pair with the contract restored byte-for-byte; D0468; sprint record; gates."; }
    // RAN: keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
    part hostCostIsAnIndicatorStandupGateR1 : TestResult { :>> id = "b99eb436-6903-4d3e-b5ee-fc3724751b97"; :>> outcome = VerdictKind::proposed; :>> judgedAgainst = "ce41db3"; :>> judgedAt = "2026-09-13"; :>> judgedBy = "claudeFable5"; }
    verification hostCostIsAnIndicatorImplementGate : Test { :>> id = "4e425e6f-e43c-495f-baf0-3fd12a573ad0"; :>> title = "Sprint 696 implement gate"; :>> createdAt = "2026-09-13"; :>> createdBy = "claudeFable5"; :>> method = VerificationMethod::test; :>> procedureText = "RAN: cargo test --release --lib pm::tests::the_recent_sample_is_the_last_n_fires_of_one_event -> 1 passed 0 failed (30 stop fires + 1 post-edit + 1 malformed line: the sample is the last 25 stop fires, first 6000 last 30000, the post-edit 99999 absent, p90 28000 = the 23rd of 25; last_n 0 and a missing ledger are empty). cargo clippy --release -p keel-cli --all-targets -- -D warnings -> exit 0 (first pass failed on too_long_first_doc_paragraph, indexing_slicing and the test import; fixed, re-run). cargo build --release -> exit 0, copied to keel-serve.exe. keel show indicators . -> hookLatencyIndicator latest 14125.00 ms, trigger above 10000 crossed true; gitFactsSizeIndicator latest 4069615.00 bytes, trigger above 8000000 crossed false; independent python over the same ledger and file: p90 14125, bytes 4069615 - equal. D0388 pair (scratch pair.py, contract restored and asserted equal to the declared text after): thresholds 10000 / 4000000 (below live) -> indicators.triggered and orient.burndown.triggers both list gitFactsSizeIndicator and hookLatencyIndicator; thresholds 20000 / 8000000 (above live) -> neither surface lists either; declared thresholds -> hookLatencyIndicator triggered in both surfaces, gitFactsSizeIndicator in neither. PAIR HOLDS. keel gate validate 796 clean; check-engine clean before the Decision (re-run at closeOut with D0468 in the tree)."; }
    // RAN: cargo test --release --lib pm::tests::the_recent_sample_is_the_last_n_fires_of_one_event -> 1 passed 0 failed; cargo clippy --release -p keel-cli --all-targets -- -D warnings -> exit 0; cargo build --release -> exit 0; keel show indicators . -> hookLatencyIndicator latest 14125.00 ms trigger above 10000 crossed true, gitFactsSizeIndicator latest 4069615.00 bytes trigger above 8000000 crossed false, equal to an independent python read of the same ledger and file (p90 14125, bytes 4069615); D0388 pair: thresholds 10000/4000000 -> both indicators in indicators.triggered AND orient.burndown.triggers, thresholds 20000/8000000 -> neither in either, contract restored byte-for-byte -> PAIR HOLDS
    part hostCostIsAnIndicatorImplementGateR1 : TestResult { :>> id = "427d98b0-2117-45b7-908e-f3f193659a43"; :>> outcome = VerdictKind::pass; :>> judgedAgainst = "ce41db3"; :>> judgedAt = "2026-09-13"; :>> judgedBy = "claudeFable5"; }
    verification hostCostIsAnIndicatorReviewGate : Test { :>> id = "7c9d32df-372f-4a8e-93cb-c7543c1d82de"; :>> title = "Sprint 696 review gate — three passes per D0172"; :>> createdAt = "2026-09-13"; :>> createdBy = "claudeFable5"; :>> method = VerificationMethod::inspect; :>> procedureText = "Three passes (D0172). Correctness: the two keys are read before Model::build, so the burndown's trigger loop (view/mod.rs) pays no model build for them and a tree whose model fails to build still reports its hook cost; the p90 is pm::latency's nearest rank, the one reading of a percentile in the binary (D0389), over a window the unit test pins at the last 25 of the named event only; the cache length is metadata, not a read, so the indicator costs nothing at 27 MB either. Honesty: the hook indicator TRIGGERS on the tree that declares it (14125 > 10000) and D0468 says so - the threshold was anchored on the figures issue441/issue442 were raised on, not chosen to sit under the live value; the ledger's phases say where the time goes (guard:decision-scaffolding, 13 of 14 fires past the receipt), which is issue520, tracked with its resolver before this record. Receipt-answered fires (183-389 ms, D0371) are in the sample at their real cost, so the number is the turn boundary as held, not the guard set's cost alone - the indicator's measures text says which. Scope: no guard changed, nothing gates on either indicator (D0088); the DoD on dcHookLatencyIsAnIndicator is not edited. Residual: the p90 over 25 fires moves with how many turns answer from the receipt - a session of small edits reads low, a session of .sysml edits reads high; that is the cost as paid, and a per-phase indicator (guards only) would be the next item if the human wants the guard set's own floor watched."; }
    // RAN: keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
    part hostCostIsAnIndicatorReviewGateR1 : TestResult { :>> id = "10a1c778-7864-42c6-b6d1-865bc139d48b"; :>> outcome = VerdictKind::proposed; :>> judgedAgainst = "ce41db3"; :>> judgedAt = "2026-09-13"; :>> judgedBy = "claudeFable5"; }
    verification hostCostIsAnIndicatorCloseOutGate : Test { :>> id = "897fe9e9-6124-406a-b354-1032040c01ef"; :>> title = "Sprint 696 closeOut gate (autonomous, D0049)"; :>> createdAt = "2026-09-13"; :>> createdBy = "claudeFable5"; :>> method = VerificationMethod::inspect; :>> procedureText = "Closes on gate validate, gate check-engine and gate guard --no-receipt ALL PASS over the tree holding D0468, this sprint, issue520 and its resolver; dcHookLatencyIsAnIndicatorDoD carries a pass with the RAN receipt; issue442 resolves through it (computed). D0468 stays proposed for the human; the thresholds are live whether or not it is accepted, because a trigger surfaces work and gates nothing - what acceptance binds is the numbers."; }
    // RAN: keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
    part hostCostIsAnIndicatorCloseOutGateR1 : TestResult { :>> id = "586134a7-d534-4bc0-8ae7-709e908be566"; :>> outcome = VerdictKind::proposed; :>> judgedAgainst = "ce41db3"; :>> judgedAt = "2026-09-13"; :>> judgedBy = "claudeFable5"; }
    verification hostCostIsAnIndicatorRetroGate : Test { :>> id = "0bb201a7-56a7-471e-ae71-b5c0ec4b8d8f"; :>> title = "Sprint 696 retro gate (autonomous, D0049)"; :>> createdAt = "2026-09-13"; :>> createdBy = "claudeFable5"; :>> method = VerificationMethod::analyze; :>> procedureText = "AVOIDABLE-ISSUE SCAN (D0131): the ledger read for this item showed one empirical thing beyond the DoD - guard:decision-scaffolding is the critical path of 13 of the last 14 stop fires that ran the guards (4645-12463 ms), and guards.rs decision_scaffolding re-reads every line of every file once per candidate Decision with a format! per line. Tracked as issue520 (Medium), resolver dcDecisionScaffoldingIndexesItsEdgesOnce: one pass collecting the inbound-edge targets into a set. An Issue, not a Decision: it is a measured defect of one guard (D0467's preference). Second finding: indicator-triggers.toml is a keystone-locked path, so declaring a threshold - indicator content that gates nothing - costs a marked Decision held for the human; no new item / already tracked - D0465 (held) is the path that would let an accepted charter authorise such an edit, and the fork on whether contract content under an accepted contract Decision needs its own marker is for that Decision's reading, not a new Issue."; }
    // RAN: keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
    part hostCostIsAnIndicatorRetroGateR1 : TestResult { :>> id = "58f469ea-b261-4c0d-a34d-7af39a08a66e"; :>> outcome = VerdictKind::proposed; :>> judgedAgainst = "ce41db3"; :>> judgedAt = "2026-09-13"; :>> judgedBy = "claudeFable5"; }
}
