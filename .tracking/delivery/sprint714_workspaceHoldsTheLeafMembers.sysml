// ProjectDeliveryS714 — Sprint 714: the first extraction of the D0479 modularity pass - dcWorkspaceHoldsTheLeafMembers. The six leaf modules of keel-cli (the modules with fan-out zero or one in the computed module graph) become workspace members under members/: keel-git (gitx), keel-perf (perf), keel-json (json, color), keel-actor (actor, device), keel-schema (schema, cli_facts, cli_surface, control_defects, embedded), keel-github (github). keel-cli re-exports each under its old module path so no caller changes and the CLI surface is byte-identical. The touched set (D0421) and the content key (D0474) learn the members/ prefix in the same commit so a member edit still names its tests and stales its receipt.. EXECUTE. 5 pts.
package ProjectDeliveryS714 {
    private import EngineElement::*;
    private import EngineWork::*;
    private import EngineVerification::*;
    private import EngineRelationships::*;

    #CharteredBy dependency from workspaceHoldsTheLeafMembersStory to d0479;

    part workspaceHoldsTheLeafMembersStory : Story {
        :>> id = "975e9f91-68b5-4ffa-b001-ad718462c420";
        :>> title = "Sprint 714: the first extraction of the D0479 modularity pass - dcWorkspaceHoldsTheLeafMembers. The six leaf modules of keel-cli (the modules with fan-out zero or one in the computed module graph) become workspace members under members/: keel-git (gitx), keel-perf (perf), keel-json (json, color), keel-actor (actor, device), keel-schema (schema, cli_facts, cli_surface, control_defects, embedded), keel-github (github). keel-cli re-exports each under its old module path so no caller changes and the CLI surface is byte-identical. The touched set (D0421) and the content key (D0474) learn the members/ prefix in the same commit so a member edit still names its tests and stales its receipt. (5 pts)";
        :>> createdAt = "2026-09-14"; :>> createdBy = "claudeFable5"; :>> kind = WorkKind::code; :>> priority = WorkPriority::p0; :>> owner = "claudeFable5"; :>> estimatedPoints = 5;
    }

    action def DeliveryRunS714 {
        action storyWorkspaceHoldsTheLeafMembers;
        verification storyWorkspaceHoldsTheLeafMembersDoD : Test { :>> id = "b05e91b4-e96f-423b-88b9-f5c880184873"; :>> method = VerificationMethod::test; :>> procedureText = "The DoD is dcWorkspaceHoldsTheLeafMembersDoD in the backlog, verbatim; this sprint's result is recorded against it. Known-positive: after a whitespace-only edit to keel-cli/src/main.rs, cargo build --release -p keel-git --verbose shows every crate Fresh; after an edit to members/keel-git/src/gitx.rs, keel-cli rebuilds and keel-json stays Fresh. Known-negative: the touched set passes under keel land, keel --help is byte-identical to the render before the move, and no crate:: reference inside a member names a module outside it."; }
        // RAN: // RAN: DoD for dcWorkspaceHoldsTheLeafMembers (D0479) at 396f13f (2026-09-14). cargo build --release from the root: Finished release in 1m 39s, workspace of keel-parser + six members + keel-cli. DoD known-positives (probes.txt): after a whitespace-only edit to keel-cli/src/main.rs, cargo build --release -p keel-git --verbose printed Fresh keel-perf, Fresh keel-git, Finished in 0.13s; after a comment appended to members/keel-git/src/gitx.rs, cargo build --release --verbose printed Compiling keel-git, Compiling keel-cli, and Fresh for keel-perf, keel-json, keel-github, keel-schema, keel-actor (3m 11s). Known-negatives: keel --help byte-identical to the pre-move keel-land.exe render (cmp, 14593 bytes); probe_pair.py neg exits 0 (no member reaches outside itself via crate::) and exits 1 with a planted crate::perf:: line; the D0388 pair ran inside the ladder. keel verify . --probe pos,neg: validate pass, guard pass (75 guards, 0 violations), clippy pass (cargo clippy --release --workspace --all-targets, exit 0), probe pass, touched pass - keel suite --touched: 851 passed in 704s under cargo-nextest 0.9.144, changed modules [actor, cli_facts, cli_surface, color, contentkey, control_defects, device, embedded, github, gitx, init, json, perf, schema, touched], the member-lib invocation ran (touched log rows keel-git gitx::tests::*, keel-github github::*, 81 tests over the non-cli members); every rung green in 710 s; receipt .keel/metrics/verify-receipt.toml. Member unit suites: keel-actor 11, keel-git 4, keel-github 12, keel-json 6, keel-perf 2, keel-schema 14 passed; keel-cli touched/contentkey 22 passed.
        part storyWorkspaceHoldsTheLeafMembersDoDR1 : TestResult { :>> id = "4dddd131-a23a-44e8-959e-82a60742339d"; :>> outcome = VerdictKind::pass; :>> judgedAgainst = "396f13f"; :>> judgedAt = "2026-09-14"; :>> judgedBy = "claudeFable5"; }
    }

    verification workspaceHoldsTheLeafMembersRefineGate : Test { :>> id = "400ce631-3ba5-4b68-bc9c-7ad055a8d6e8"; :>> title = "Sprint 714 refine gate (DoR)"; :>> createdAt = "2026-09-14"; :>> createdBy = "claudeFable5"; :>> method = VerificationMethod::inspect; :>> procedureText = "DoR: the item is the head of the ready frontier (keel show whats-next), chartered by D0479 (accepted) through its #CharteredBy edge, sized 5 (six members, one re-export layer, the touched-set bridge, and the registry paths that move). Blocking dependencies: none - the leaves reference nothing above them except gitx -> perf (leaf to leaf) and schema -> collect_sysml, which schema takes over as its own walk."; }
    // RAN: // RAN: DoR at 396f13f (2026-09-14). Charter: #CharteredBy workspaceHoldsTheLeafMembersStory -> d0479 (crateSplitsIntoGranularMembers, status accepted at 0479-crateSplitsIntoGranularMembers.sysml:15). Frontier: keel show whats-next . lists dcWorkspaceHoldsTheLeafMembers first (then dcReadyHonoursItemDependencies, dcGuardsViewOrientCycleIsBroken, dcModelAndWriteAreMembers). estimatedPoints = 5 (record sprint 714 --points 5): six members, one re-export layer, the touched-set and content-key bridge, the registry paths that move. Blocking dependencies: none - the leaves reference nothing above them except gitx -> perf (leaf to leaf) and schema -> collect_sysml, which keel-schema takes over as its own walk (schema.rs sysml_files). DoD: dcWorkspaceHoldsTheLeafMembersDoD in the backlog, verbatim.
    part workspaceHoldsTheLeafMembersRefineGateR1 : TestResult { :>> id = "138249db-84c7-4f52-b6ab-c7bcae8f606c"; :>> outcome = VerdictKind::proposed; :>> judgedAgainst = "396f13f"; :>> judgedAt = "2026-09-14"; :>> judgedBy = "claudeFable5"; }
    verification workspaceHoldsTheLeafMembersStandupGate : Test { :>> id = "9ab4f955-ad00-43e5-b992-8a4e454b211e"; :>> title = "Sprint 714 standup gate"; :>> createdAt = "2026-09-14"; :>> createdBy = "claudeFable5"; :>> method = VerificationMethod::inspect; :>> procedureText = "Order: members/ crates with Cargo.toml and src/lib.rs declaring the moved modules; root Cargo.toml lists them; keel-cli/Cargo.toml depends on them; lib.rs re-exports (pub use keel_git::gitx;); embedded.rs and schema.rs include_dir paths gain one more ..; touched.rs module_stem / is_unattributed_source / the untracked and no-base ls-files accept members/<crate>/src; contentkey::is_code accepts members/ and keel-parser/; the member libs' unit tests run with the lib whenever the lib is in the set; code-registry filePaths follow the files (ceGitSpawn edited by its owner, ceActorProvenance superseded by a new element - D0108); then cargo build, the DoD probes, keel verify."; }
    // RAN: // RAN: Standup at 396f13f (2026-09-14). Order followed as written: members/<crate>/{Cargo.toml,src/lib.rs} for keel-perf, keel-git, keel-json, keel-actor, keel-schema, keel-github (extract.py: git mv of the 12 modules, manifests inherit version/edition/rust-version/license from the workspace); root Cargo.toml members list (Cargo.toml:2-10); keel-cli/Cargo.toml depends on all six; lib.rs re-exports at their old paths (keel-cli/src/lib.rs:28-31, 59, 63, 73, 83-84, 88, 102); embedded.rs and schema.rs include_dir paths gain one more `..`; schema.rs takes its own sysml_files walk in place of crate::collect_sysml; touched.rs source_rel (touched.rs:81) accepts members/<crate>/src, workspace_members (:701) and member_libs (:711) read the manifests, run_member_libs (:846) runs every member's --lib whenever lib is in the set; contentkey::is_code accepts members/ and keel-parser/ (contentkey.rs:46-47); code-registry: ceGitSpawn filePath edited (mine), ceActorProvenanceMember added + #Supersede to ceActorProvenance (claudeOpus5's, D0108). Deviations: four member unit tests keyed on `..` from the crate dir broke and were repointed at the checkout root (gitx.rs, github.rs x2, cli_surface.rs); the build skill's layout paragraph is a locked file, so D0484 (process-change, held) rides the commit.
    part workspaceHoldsTheLeafMembersStandupGateR1 : TestResult { :>> id = "cdf21454-0134-4114-9c81-6151696c6b6a"; :>> outcome = VerdictKind::proposed; :>> judgedAgainst = "396f13f"; :>> judgedAt = "2026-09-14"; :>> judgedBy = "claudeFable5"; }
    verification workspaceHoldsTheLeafMembersImplementGate : Test { :>> id = "e05c1299-d8a6-4877-aaf1-ad21ea27ee11"; :>> title = "Sprint 714 implement gate"; :>> createdAt = "2026-09-14"; :>> createdBy = "claudeFable5"; :>> method = VerificationMethod::test; :>> procedureText = "The implement gate is the DoD's own probes plus the ladder: cargo build --release from the workspace root; the known-positive Fresh reads; keel --help diff; the crate:: grep; keel verify . (validate, guard, clippy, D0388 pair, suite --touched) green."; }
    // RAN: // RAN: Implement at 396f13f (2026-09-14). cargo build --release from the root: Finished release in 1m 39s, workspace of keel-parser + six members + keel-cli. DoD known-positives (probes.txt): after a whitespace-only edit to keel-cli/src/main.rs, cargo build --release -p keel-git --verbose printed Fresh keel-perf, Fresh keel-git, Finished in 0.13s; after a comment appended to members/keel-git/src/gitx.rs, cargo build --release --verbose printed Compiling keel-git, Compiling keel-cli, and Fresh for keel-perf, keel-json, keel-github, keel-schema, keel-actor (3m 11s). Known-negatives: keel --help byte-identical to the pre-move keel-land.exe render (cmp, 14593 bytes); probe_pair.py neg exits 0 (no member reaches outside itself via crate::) and exits 1 with a planted crate::perf:: line; the D0388 pair ran inside the ladder. keel verify . --probe pos,neg: validate pass, guard pass (75 guards, 0 violations), clippy pass (cargo clippy --release --workspace --all-targets, exit 0), probe pass, touched pass - keel suite --touched: 851 passed in 704s under cargo-nextest 0.9.144, changed modules [actor, cli_facts, cli_surface, color, contentkey, control_defects, device, embedded, github, gitx, init, json, perf, schema, touched], the member-lib invocation ran (touched log rows keel-git gitx::tests::*, keel-github github::*, 81 tests over the non-cli members); every rung green in 710 s; receipt .keel/metrics/verify-receipt.toml. Member unit suites: keel-actor 11, keel-git 4, keel-github 12, keel-json 6, keel-perf 2, keel-schema 14 passed; keel-cli touched/contentkey 22 passed.
    part workspaceHoldsTheLeafMembersImplementGateR1 : TestResult { :>> id = "c3522eb4-e9e0-4594-a798-d0657d3d0b9f"; :>> outcome = VerdictKind::pass; :>> judgedAgainst = "396f13f"; :>> judgedAt = "2026-09-14"; :>> judgedBy = "claudeFable5"; }
    verification workspaceHoldsTheLeafMembersReviewGate : Test { :>> id = "97565b62-28c8-4412-83b1-21ca6fdffce3"; :>> title = "Sprint 714 review gate — three passes per D0172"; :>> createdAt = "2026-09-14"; :>> createdBy = "claudeFable5"; :>> method = VerificationMethod::inspect; :>> procedureText = "Three passes (D0172). Correctness: every pub item the rest of keel-cli used is reachable at its old path; the include_dir paths resolve to the same trees (embedded::ENGINE_DIR and schema::SCHEMA_DIR read .engine from members/keel-schema/../../). Honesty: a member edit contributes its stems to the touched set and moves the code key - checked by the touched.rs unit tests for the members/ prefix, both directions. Scope: nothing above the leaves moved; guards.rs, view, orient, write untouched apart from imports the compiler required."; }
    // RAN: // RAN: Review at 396f13f (2026-09-14), three passes (D0172). Correctness: cargo build --release from the root is green and keel --help from the rebuilt binary is byte-identical to the render of target/release/keel-land.exe built before the move (cmp, 14593 bytes both); every pub item keel-cli used is reachable at its old path (probe_pair.py pos: all 12 member modules re-exported from keel-cli/src/lib.rs); embedded::ENGINE_DIR and schema::SCHEMA_DIR resolve .engine from members/keel-schema/../.. (include_dir paths in embedded.rs and schema.rs), and keel-schema's 14 unit tests over that tree pass. Honesty: a member edit contributes its stems and moves the code key - touched.rs unit tests for source_rel over members/<crate>/src (a_stem_is_the_module_a_path_names) and contentkey tests is_code('members/keel-git/src/gitx.rs') / is_code('keel-parser/src/lexer.rs') pass (cargo test -p keel-cli --lib -- touched contentkey: 22 passed); the live touched run at this tree attributed [actor, cli_facts, cli_surface, color, contentkey, control_defects, device, embedded, github, gitx, json, perf, schema, touched]. Scope: nothing above the leaves moved; guards.rs, view, orient, write untouched; the only non-mechanical edits are the four tests repointed at the checkout root and schema.rs's own sysml_files walk. Finding carried to the retro: `keel record decision` swallowed --depends-on and wrote D0484 edgeless (issue551, dcRecordRefusesAnUnknownFlag); the edge was authored by hand.
    part workspaceHoldsTheLeafMembersReviewGateR1 : TestResult { :>> id = "03312dde-a085-4b15-8ffa-0e0263a9a9a2"; :>> outcome = VerdictKind::proposed; :>> judgedAgainst = "396f13f"; :>> judgedAt = "2026-09-14"; :>> judgedBy = "claudeFable5"; }
    verification workspaceHoldsTheLeafMembersCloseOutGate : Test { :>> id = "323d6d72-d0c4-425e-8ffd-ce58e59ceb07"; :>> title = "Sprint 714 closeOut gate (autonomous, D0049)"; :>> createdAt = "2026-09-14"; :>> createdBy = "claudeFable5"; :>> method = VerificationMethod::inspect; :>> procedureText = "Close-out at the landing commit after the CI conclusion reads success: git status -sb level with origin, gh run conclusion, the DoD result recorded against dcWorkspaceHoldsTheLeafMembersDoD at that sha."; }
    // RAN: // RAN: CloseOut at 87085d2 (2026-09-14). git status -sb: ## main...origin/main, level with origin, clean. gh run list --limit 1 --json conclusion,status,headSha: 87085d2 completed success (D0420: the conclusion field). keel land in the post-commit hook: 67 touched binaries selected, 702 passed in 468s, pushed main -> origin attempt 1/3, landed. The DoD result against dcWorkspaceHoldsTheLeafMembersDoD and the story result carry sha 396f13f and bind to 87085d2, the commit that landed them (dcResultBindsToItsLandingCommit). D0484 (buildSkillNamesTheMembers, process-change) rode the commit and stays proposed for the human.
    part workspaceHoldsTheLeafMembersCloseOutGateR1 : TestResult { :>> id = "bcf91e29-5dca-4ee7-a118-f132a20b94e2"; :>> outcome = VerdictKind::proposed; :>> judgedAgainst = "87085d2"; :>> judgedAt = "2026-09-14"; :>> judgedBy = "claudeFable5"; }
    verification workspaceHoldsTheLeafMembersRetroGate : Test { :>> id = "eeb9c590-375c-4d10-b840-0e488a0acecf"; :>> title = "Sprint 714 retro gate (autonomous, D0049)"; :>> createdAt = "2026-09-14"; :>> createdBy = "claudeFable5"; :>> method = VerificationMethod::analyze; :>> procedureText = "Retro: avoidable issues scanned; what the extraction found that the plan did not predict. (1) Four member unit tests keyed on a fixed `..` from the crate directory (gitx.rs, github.rs twice, cli_surface.rs) and broke the moment the module sat two levels down; each now resolves the checkout root (git rev-parse or the first ancestor holding .git) - fixed inside dcWorkspaceHoldsTheLeafMembers, no new item. (2) A keel-parser edit contributes no module stem to the touched set - issue550, added in this commit, resolved by dcTouchedSetDescendsTheWorkspace (D0481). (3) `git checkout -- FILE` after `git mv` plus an unstaged edit restored the index copy and silently undid the keel_perf:: patch; the D0388 known-negative grep caught it before the build - no new item, the probe pair is the control that fired. (4) keel record decision accepted --depends-on and wrote D0484 with no edge, exit 0 - issue551, added in this commit, resolved by dcRecordRefusesAnUnknownFlag (new backlog item, same commit); the edge was authored by hand."; }
    // RAN: // RAN: Retro at 87085d2 (2026-09-14). Avoidable issues scanned: (1) and (3) below were avoidable, (2) and (4) were latent defects the extraction exposed. Findings, each with the item that carries it: (1) four member unit tests keyed on a fixed .. from the crate directory (gitx.rs, github.rs twice, cli_surface.rs) and broke two levels down; each now resolves the checkout root - fixed inside dcWorkspaceHoldsTheLeafMembers, no new item. (2) a keel-parser edit contributes no touched-set stem - issue550, added in 87085d2, resolved by dcTouchedSetDescendsTheWorkspace (D0481). (3) git checkout -- FILE after git mv plus an unstaged edit restored the index copy and silently undid the keel_perf:: patch; the D0388 known-negative grep caught it before the build - no new item, the probe pair is the control that fired. (4) keel record decision accepted --depends-on and wrote D0484 with no edge, exit 0 - issue551, added in 87085d2, resolved by dcRecordRefusesAnUnknownFlag (new backlog item, same commit); the edge was authored by hand. Unpredicted by the plan: the locked build skill paragraph needed its own marked Decision, D0484 (process-change, held), because the sprint's charter D0479 is unmarked and the D0465 clause (dcAcceptedCharterAuthorisesTheLockedEdit, delivered by sprint 693) covers only a sprint chartered by an accepted MARKED Decision; no new item - the later D0479 extractions that touch the same paragraph ride D0484 once it is accepted, and D0484's consequences clause names the fix if the friction recurs. Measured: full ladder 710s (touched 704s, 851 tests); the land re-ran 702 in 468s after the ceremony writes (D0474 skip held for the non-self-reading set).
    part workspaceHoldsTheLeafMembersRetroGateR1 : TestResult { :>> id = "126b7f3d-8160-4316-bae8-a36ebb075d74"; :>> outcome = VerdictKind::proposed; :>> judgedAgainst = "87085d2"; :>> judgedAt = "2026-09-14"; :>> judgedBy = "claudeFable5"; }
}
