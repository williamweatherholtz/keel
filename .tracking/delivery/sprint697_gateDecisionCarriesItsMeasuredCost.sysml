// ProjectDeliveryS697 — Sprint 697: Resolve issue444's recurrence class: a proposed process-change Decision that names the land or push path prices itself with a MEASURED: token or decision-scaffolding names it, so a gate is never asked for at a fixture's price again (D0421 said seconds; the first live set cost 528 s). EXECUTE; 2 pts; dcGateDecisionCarriesItsMeasuredCost; the rule is D0469 (held, inert until accepted).. EXECUTE. 2 pts.
package ProjectDeliveryS697 {
    private import EngineElement::*;
    private import EngineWork::*;
    private import EngineVerification::*;
    private import EngineRelationships::*;

    #CharteredBy dependency from gateDecisionCarriesItsMeasuredCostStory to d0469;

    part gateDecisionCarriesItsMeasuredCostStory : Story {
        :>> id = "db62c2aa-ba15-4a59-ad1b-42aa4004c0d0";
        :>> title = "Sprint 697: Resolve issue444's recurrence class: a proposed process-change Decision that names the land or push path prices itself with a MEASURED: token or decision-scaffolding names it, so a gate is never asked for at a fixture's price again (D0421 said seconds; the first live set cost 528 s). EXECUTE; 2 pts; dcGateDecisionCarriesItsMeasuredCost; the rule is D0469 (held, inert until accepted). (2 pts)";
        :>> createdAt = "2026-09-13"; :>> createdBy = "claudeFable5"; :>> kind = WorkKind::code; :>> priority = WorkPriority::p0; :>> owner = "claudeFable5"; :>> estimatedPoints = 2;
    }

    action def DeliveryRunS697 {
        action storyGateDecisionCarriesItsMeasuredCost;
        verification storyGateDecisionCarriesItsMeasuredCostDoD : Test { :>> id = "19e1fa62-1154-42f5-9955-e7d9e177fdb9"; :>> method = VerificationMethod::test; :>> procedureText = "DELIVERED: keel-cli/src/guards.rs decision_scaffolding carries the D0469 clause - armed only when acceptance_kind finds a HUMAN acceptance of d0469 - over the pure core unmeasured_path_decisions: every PROPOSED #ProspectiveChange Decision whose decision field names one of PATH_WORDS (land, push, refuse, gate; whole word, any case) and whose rationale lacks MEASURED: is a WARNING naming the Decision and the words. The D0388 trio is the unit test unmeasured_path_tests (known positive named; D0421's corrected shape and a no-path-words Decision silent; an accepted Decision not read; inflections not the words). guards.md's decision-scaffolding row states the clause. D0469 is recorded with the process-change marker and carries its own MEASURED: token. The guard set stays green on the tree with the Decision co-committed."; }
        // RAN: cargo test --release --lib guards::unmeasured_path_tests -> 1 passed 0 failed (D0388 trio: proposed Decision with land/push/refuse and no token NAMED; D0421's corrected shape with MEASURED: silent; no path words silent; accepted Decision not read; landing/pushed/gateway/refuses not the words; Land/PUSH any case named); first run failed on the fixture saying refuses - corrected to the whole word; cargo clippy --release -p keel-cli --all-targets -- -D warnings -> exit 0; cargo build --release -> exit 0, copied to keel-serve.exe; cost pair on host 0F3DGVX25193H7: gate guard --no-receipt before the clause 7.6 s median (7.2/7.6/10.4), with it 7.3 s median (6.5/7.3/7.8), inert clause inside the noise; live mirror: on acceptance the guard would name d0467 (gate) and no other proposed marked Decision; keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it)
        part storyGateDecisionCarriesItsMeasuredCostDoDR1 : TestResult { :>> id = "b714db63-91fc-45c2-8215-fe02a52f119b"; :>> outcome = VerdictKind::pass; :>> judgedAgainst = "61bb6a9"; :>> judgedAt = "2026-09-13"; :>> judgedBy = "claudeFable5"; }
    }

    verification gateDecisionCarriesItsMeasuredCostRefineGate : Test { :>> id = "6669c794-5f1c-4c30-b1c6-0d85126bd8e8"; :>> title = "Sprint 697 refine gate (DoR)"; :>> createdAt = "2026-09-13"; :>> createdBy = "claudeFable5"; :>> method = VerificationMethod::inspect; :>> procedureText = "Chartered by D0469 (proposed, process-change marker - the edit is guard source, a keystone-locked path under D0209 clause 2, so the co-committed marked Decision is the charter). Two points: one pure function, one call site, one unit test, one doc row, one Decision, one timed pair. DoR: dcGateDecisionCarriesItsMeasuredCostDoD fixes the words, the token, the tier (WARN) and the trio. Not a fork: the DoD fixed the design; the one reading this sprint made - the four words exactly, not their inflections - is recorded in D0469's rationale with the live consequence it has (d0467 named on acceptance)."; }
    // RAN: keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it)
    part gateDecisionCarriesItsMeasuredCostRefineGateR1 : TestResult { :>> id = "2938552f-c710-4f8d-925b-782cec4b7a51"; :>> outcome = VerdictKind::proposed; :>> judgedAgainst = "61bb6a9"; :>> judgedAt = "2026-09-13"; :>> judgedBy = "claudeFable5"; }
    verification gateDecisionCarriesItsMeasuredCostStandupGate : Test { :>> id = "7c4a9364-fab9-401d-98e6-f08486ef7d7d"; :>> title = "Sprint 697 standup gate"; :>> createdAt = "2026-09-13"; :>> createdBy = "claudeFable5"; :>> method = VerificationMethod::inspect; :>> procedureText = "Order: mirror the rule in python over the live proposed marked Decisions first (five proposed: d0376, d0461, d0463, d0467, d0468; one names a path word - d0467, gate) so the Rust has a known live consequence to state; patch guards.rs from one scripted edit with asserted anchors; cargo test the trio, clippy -D warnings, release build, copy to the serve image; time gate guard before/after on the same tree (three runs each, alternating) for D0469's own MEASURED: token; record D0469; doc row; gates; sprint record."; }
    // RAN: keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it)
    part gateDecisionCarriesItsMeasuredCostStandupGateR1 : TestResult { :>> id = "685931da-cd97-4752-b706-d9511490f6c4"; :>> outcome = VerdictKind::proposed; :>> judgedAgainst = "61bb6a9"; :>> judgedAt = "2026-09-13"; :>> judgedBy = "claudeFable5"; }
    verification gateDecisionCarriesItsMeasuredCostImplementGate : Test { :>> id = "3f567238-0c12-49e1-93c8-3bf85ce66e69"; :>> title = "Sprint 697 implement gate"; :>> createdAt = "2026-09-13"; :>> createdBy = "claudeFable5"; :>> method = VerificationMethod::test; :>> procedureText = "RAN: cargo test --release --lib guards::unmeasured_path_tests -> 1 passed 0 failed (first run failed on the FIXTURE: the positive said 'refuses', not one of the four words - the fixture was corrected to say 'refuse' and a negative now carries 'refuses' among the non-words, so the exact-word reading is pinned rather than assumed). cargo clippy --release -p keel-cli --all-targets -- -D warnings -> exit 0 (first pass: doc_markdown on 'DoD' in a doc comment; reworded). cargo build --release -> exit 0, copied to keel-serve.exe. Cost pair (scratch cost.py, host 0F3DGVX25193H7): keel gate guard --no-receipt, binary before the clause 7.6 s median (7.2 / 7.6 / 10.4), binary holding it 7.3 s median (6.5 / 7.3 / 7.8) - the inert clause is inside the noise. Live mirror (scratch mirror.py): WOULD WARN on acceptance = d0467 (gate). keel gate guard on the tree BEFORE D0469 was recorded: process-change FAIL naming keel-cli/src/guards.rs with no co-committed marked Decision - the expected red, cleared by recording D0469 (re-run at closeOut)."; }
    // RAN: cargo test --release --lib guards::unmeasured_path_tests -> 1 passed 0 failed (D0388 trio: proposed Decision with land/push/refuse and no token NAMED; D0421's corrected shape with MEASURED: silent; no path words silent; accepted Decision not read; landing/pushed/gateway/refuses not the words; Land/PUSH any case named); first run failed on the fixture saying refuses - corrected to the whole word; cargo clippy --release -p keel-cli --all-targets -- -D warnings -> exit 0; cargo build --release -> exit 0, copied to keel-serve.exe; cost pair on host 0F3DGVX25193H7: gate guard --no-receipt before the clause 7.6 s median (7.2/7.6/10.4), with it 7.3 s median (6.5/7.3/7.8), inert clause inside the noise; live mirror: on acceptance the guard would name d0467 (gate) and no other proposed marked Decision
    part gateDecisionCarriesItsMeasuredCostImplementGateR1 : TestResult { :>> id = "eadcff83-05f2-4b41-9672-27294929d0b8"; :>> outcome = VerdictKind::pass; :>> judgedAgainst = "61bb6a9"; :>> judgedAt = "2026-09-13"; :>> judgedBy = "claudeFable5"; }
    verification gateDecisionCarriesItsMeasuredCostReviewGate : Test { :>> id = "76edc2ed-cbc5-44a7-a259-664f27e8b26d"; :>> title = "Sprint 697 review gate — three passes per D0172"; :>> createdAt = "2026-09-13"; :>> createdBy = "claudeFable5"; :>> method = VerificationMethod::inspect; :>> procedureText = "Three passes (D0172). Correctness: the clause reads proposed-ness through acceptance_kind, the one reading of 'accepted' the taint walk and the charter guard already use, so a Decision cannot be proposed to one guard and accepted to another; the field reader is compound_decisions' pattern (first `key = '` in the part block to the next quote) - Decision fields here hold no literal double quote, and a title containing `decision = '` would misread, which is the same exposure compound_decisions has carried since D0303 without a hit; the word split is ASCII-alphanumeric so `gate,` `gate.` and `(gate)` match and `gateway` does not. Honesty: the rule as decided names d0467 on acceptance for 'not a gate' - a false positive of the word test, stated in D0469 rather than dodged by narrowing the words to fit the tree (the D0388 class); the armed path's cost is NOT measured, because arming needs the acceptance, and D0469 says which ledger phase will hold the figure and which indicator surfaces it. Scope: the guard's verdicts on the current tree are byte-identical before and after (the clause is inert: same 316 warnings, same one process-change violation before the Decision); no schema, hook or CI change; the DoD text is untouched."; }
    // RAN: keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it)
    part gateDecisionCarriesItsMeasuredCostReviewGateR1 : TestResult { :>> id = "2ba17c4b-5f7e-4b6a-8701-f7e699174b39"; :>> outcome = VerdictKind::proposed; :>> judgedAgainst = "61bb6a9"; :>> judgedAt = "2026-09-13"; :>> judgedBy = "claudeFable5"; }
    verification gateDecisionCarriesItsMeasuredCostCloseOutGate : Test { :>> id = "c754d8b2-cd48-48d9-b821-eb48094f0e1e"; :>> title = "Sprint 697 closeOut gate (autonomous, D0049)"; :>> createdAt = "2026-09-13"; :>> createdBy = "claudeFable5"; :>> method = VerificationMethod::inspect; :>> procedureText = "Closes on gate validate, gate check-engine and gate guard --no-receipt ALL PASS over the tree holding D0469, the guards.rs clause, the doc row and this sprint; dcGateDecisionCarriesItsMeasuredCostDoD carries a pass with the RAN receipt; issue444 already resolves through dcTouchedCostIsMeasuredNotQuoted - this item is the control behind that correction (D0047). D0469 stays proposed for the human; until then the clause runs and emits nothing."; }
    // RAN: keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it)
    part gateDecisionCarriesItsMeasuredCostCloseOutGateR1 : TestResult { :>> id = "3cda3cff-0db9-4641-b616-df92cf10cb58"; :>> outcome = VerdictKind::proposed; :>> judgedAgainst = "61bb6a9"; :>> judgedAt = "2026-09-13"; :>> judgedBy = "claudeFable5"; }
    verification gateDecisionCarriesItsMeasuredCostRetroGate : Test { :>> id = "c505a94d-fa70-4f1c-980a-d752c499fe8a"; :>> title = "Sprint 697 retro gate (autonomous, D0049)"; :>> createdAt = "2026-09-13"; :>> createdBy = "claudeFable5"; :>> method = VerificationMethod::analyze; :>> procedureText = "AVOIDABLE-ISSUE SCAN (D0131): the fixture failure was mine, not the code's - I wrote the positive with the inflection the real Decision uses ('refuses') while the rule reads the four words exactly; the test caught it before the build, which is what the trio is for, and the reading is now stated in the Decision, the doc row and the fixture. No new Issue: the exposure it points at - inflections of the four words are not matched - is D0469's declared what-would-change-it (a fifth word with an anchor), not a defect. Second observation, empirical: gate guard on this tree runs 6.5-10.4 s per invocation, all of it the existing guard set; that is issue520's territory (tracked, resolver dcDecisionScaffoldingIndexesItsEdgesOnce), no new item. Third, at the commit: pre-commit working-tree-eol FAILED on the delegated brief agent's scripts/exec_brief/build_2026_09_13_host_cost_thresholds.py (457 CRLF line ends against eol=lf, issue478) and aborted the commit; the bytes were rewritten to LF and the guard set re-run ALL PASS. The control fired where it is meant to and the defect is already tracked with that control - no new item; the delegate-writes-CRLF shape is the same class as the receipt the guard row already names."; }
    // RAN: keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it); retro consequence acted on (D0311): the retro naming issue520 again raised dcDecisionScaffoldingIndexesItsEdgesOnce to computed class High (recurrence 2) and priority-inversion rose 269 -> 300; the item was moved from the tail of EngineBuild to the head of the frontier (line multiset and byte length conserved), keel show whats-next reads it first, inversions 266
    part gateDecisionCarriesItsMeasuredCostRetroGateR1 : TestResult { :>> id = "b8d75ec7-714d-4c49-964d-e390713a8c91"; :>> outcome = VerdictKind::proposed; :>> judgedAgainst = "61bb6a9"; :>> judgedAt = "2026-09-13"; :>> judgedBy = "claudeFable5"; }
}
