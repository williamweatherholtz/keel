// ProjectDeliveryS709 — Sprint 709: Resolve issue542 through dcCiNextestExcludesEveryCustomHarness: CI concluded failure at 1e2ed25 and again at 593147c because ci.yml and release.yml mirror the nextest / cargo-test split by hand from keel-cli's manifest alone, and keel-parser declares four more harness = false cucumber binaries (lexer_bdd, parser_bdd, semantic_bdd, spec_compat_bdd) that cargo nextest run --workspace tries to --list and cannot (exit 104 before one test runs). sprint707's retro looked at exactly this drift and dismissed it. The pain: main is red for two commits on a cause no local check could see - keel suite --touched is scoped to -p keel-cli and never meets those binaries. The fix is the split naming all seven; the control is a guard that derives the expected split from every workspace member's manifest and reads both workflows at every gate, so a new cucumber binary in any crate fails on this machine before it fails on ubuntu. Chartered by D0475 (process-change, accepted by the human 2026-09-14), whose runner this is. 2 pts.. EXECUTE. 2 pts.
package ProjectDeliveryS709 {
    private import EngineElement::*;
    private import EngineWork::*;
    private import EngineVerification::*;
    private import EngineRelationships::*;

    #CharteredBy dependency from ciNextestExcludesEveryCustomHarnessStory to d0475;

    part ciNextestExcludesEveryCustomHarnessStory : Story {
        :>> id = "4786a33a-1b6b-418b-b4dc-088399768cff";
        :>> title = "Sprint 709: Resolve issue542 through dcCiNextestExcludesEveryCustomHarness: CI concluded failure at 1e2ed25 and again at 593147c because ci.yml and release.yml mirror the nextest / cargo-test split by hand from keel-cli's manifest alone, and keel-parser declares four more harness = false cucumber binaries (lexer_bdd, parser_bdd, semantic_bdd, spec_compat_bdd) that cargo nextest run --workspace tries to --list and cannot (exit 104 before one test runs). sprint707's retro looked at exactly this drift and dismissed it. The pain: main is red for two commits on a cause no local check could see - keel suite --touched is scoped to -p keel-cli and never meets those binaries. The fix is the split naming all seven; the control is a guard that derives the expected split from every workspace member's manifest and reads both workflows at every gate, so a new cucumber binary in any crate fails on this machine before it fails on ubuntu. Chartered by D0475 (process-change, accepted by the human 2026-09-14), whose runner this is. 2 pts. (2 pts)";
        :>> createdAt = "2026-09-14"; :>> createdBy = "claudeFable5"; :>> kind = WorkKind::code; :>> priority = WorkPriority::p0; :>> owner = "claudeFable5"; :>> estimatedPoints = 2;
    }

    action def DeliveryRunS709 {
        action storyCiNextestExcludesEveryCustomHarness;
        verification storyCiNextestExcludesEveryCustomHarnessDoD : Test { :>> id = "5c26ce7c-80fd-4c12-8718-cc2f2859368c"; :>> method = VerificationMethod::test; :>> procedureText = "Resolves issue542. ci.yml and release.yml exclude every harness = false [[test]] target of every workspace member from cargo nextest run and run each under cargo test -p <its crate> --test <name>; guard custom-harness-routed (guards.rs) derives that set from the root manifest's [workspace] members and each member's manifest through touched::custom_harness_tests, and per workflow that runs nextest fails on a declared binary the nextest line does not exclude or no cargo test line for its crate runs, and on a routed name no manifest declares; it is in GUARD_NAMES and the dispatch, catalogued in .engine/docs/guards.md, and bound to EHZ5 in control-map.sysml. D0388 pair, chosen before the tree is read: known-positive - the split text as committed at 1e2ed25 against the seven declared names exactly keel-parser's four as missing; known-negative - a split naming all seven under their crates drifts on neither count, and the real workflows as committed pass the guard with two scanned. touched.rs's comments no longer say three. CI for the landing commit concludes success - the first since 1e2ed25."; }
        // RAN: INCONCLUSIVE, not a pass: every local clause holds and one clause cannot yet be read. Local - cargo test --release --lib -- custom_harness_routed 3 passed 0 failed (known-positive the_split_of_1e2ed25_names_keel_parsers_four_cucumber_binaries_as_missing names exactly keel-parser::lexer_bdd parser_bdd semantic_bdd spec_compat_bdd; known-negative a_split_naming_every_declared_binary_under_its_crate_is_clean; this_workspace_declares_seven_and_both_workflows_route_them scanned 2, no violations); keel gate guard --no-receipt . -> [guard:custom-harness-routed] PASS - 2 scanned; control-map-reconciled PASS 27; doc-guard-count PASS 4; keel version guards 75; clippy -D warnings exit 0; grep -c three keel-cli/src/touched.rs comments now say keel-cli's three and name the guard. UNREAD - the DoD clause CI for the landing commit concludes success: this result is written before the landing commit exists, because sprint-closure holds this story unstamped while sprint 710 shares the commit; the pass or fail is recorded after gh run list --json conclusion is read for that commit (D0420), never before (sprint707).
        part storyCiNextestExcludesEveryCustomHarnessDoDR1 : TestResult { :>> id = "a79efeec-8e1a-461c-a258-bebe6f1816c5"; :>> outcome = VerdictKind::inconclusive; :>> judgedAgainst = "593147c"; :>> judgedAt = "2026-09-14"; :>> judgedBy = "claudeFable5"; }
        // RAN: ci-run id=34841977614 workflow=ci - CI for 838f75f (the landing commit; 6281526's own land failed the identity unit test and did not push) concluded success: gh run list --limit 1 --json conclusion,status,headSha -> success/completed/838f75f9. Job rust, step `test` = success; that step runs `cargo nextest run --workspace --release --no-fail-fast -E 'not (binary(cli_bdd) | ... | binary(spec_compat_bdd))'` then `cargo test --release -p keel-cli --no-fail-fast --test cli_bdd --test orient_bdd --test write_bdd` then `cargo test --release -p keel-parser --no-fail-fast --test lexer_bdd --test parser_bdd --test semantic_bdd --test spec_compat_bdd` (ci.yml:36-38). Every local clause of R1 still holds at 838f75f: `keel verify .` climbed validate / guard (ALL PASS, custom-harness-routed PASS 2 scanned) / clippy / touched (821 passed in 895 s) before the commit. This R2 replaces R1's UNREAD clause with the read (D0420).
        part storyCiNextestExcludesEveryCustomHarnessDoDR2 : TestResult { :>> id = "7e6e4992-e024-4c6c-ae8d-acec049bb9d2"; :>> outcome = VerdictKind::pass; :>> judgedAgainst = "838f75f"; :>> judgedAt = "2026-09-14"; :>> judgedBy = "claudeFable5"; }
    }

    verification ciNextestExcludesEveryCustomHarnessRefineGate : Test { :>> id = "a763a005-d363-42ae-bac4-19d907acbfbd"; :>> title = "Sprint 709 refine gate (DoR)"; :>> createdAt = "2026-09-14"; :>> createdBy = "claudeFable5"; :>> method = VerificationMethod::inspect; :>> procedureText = "Chartered by D0475, accepted by the human 2026-09-14 with the process-change marker; a guard is an enforcement change and the CI yml is an enforcement surface (D0209 cl.2), authorised by this co-committed record (D0465). Two points: two yml edits, one guard with its unit pair and three registration homes (names, dispatch, catalogue, control map), one comment sweep - the sprint-planning table puts a validator at 2. DoR: dcCiNextestExcludesEveryCustomHarness ranks first on keel show whats-next once sprint708's item is stamped; the pair is the DoD's own; the local touched run cannot exercise the fix (it is -p keel-cli), so the closing evidence is the CI conclusion itself."; }
    // RAN: D0475 accepted 2026-09-14 with the process-change marker (keel show authority-queue lists no d0475 row); this record co-committed (D0465); points 2 per the sprint-planning table (a validator); keel show whats-next line 1 is dcCiNextestExcludesEveryCustomHarness after sprint708's item was stamped at 593147c; the DoD carries its own D0388 pair; the local touched run is -p keel-cli (touched.rs:821-835) so the CI conclusion is the closing evidence
    part ciNextestExcludesEveryCustomHarnessRefineGateR1 : TestResult { :>> id = "65328e5d-6b1e-44a6-b918-56d30a63ffde"; :>> outcome = VerdictKind::proposed; :>> judgedAgainst = "593147c"; :>> judgedAt = "2026-09-14"; :>> judgedBy = "claudeFable5"; }
    verification ciNextestExcludesEveryCustomHarnessStandupGate : Test { :>> id = "b58a1978-6af7-4125-8595-a9caaa9a607f"; :>> title = "Sprint 709 standup gate"; :>> createdAt = "2026-09-14"; :>> createdBy = "claudeFable5"; :>> method = VerificationMethod::inspect; :>> procedureText = "Order: the sprint record first (process-change is red until it exists, D0465); the guard function, its helpers and the unit pair into guards.rs, GUARD_NAMES and the dispatch; the guards.md row and the control-map part with its EHZ5 edge; the two yml edits and the comments in ci.yml, release.yml and touched.rs; cargo build --release, copy to keel-serve.exe, cargo test --release --lib -- custom_harness_routed, clippy -D warnings; keel gate guard --no-receipt with the new guard PASS 2 scanned; the guard run against the 1e2ed25 split text is the unit known-positive, the real tree the known-negative; gate results and the DoD result; one CR: commit detached; keel-land; git status -sb and the CI conclusion read back - success is the closing fact, and it is read, not assumed."; }
    // RAN: Order followed as written: sprint record first (record sprint 709 ... --charter d0475 --points 2 --fill fill709.md); guard custom_harness_routed + workspace_custom_harnesses + custom_harness_split + custom_harness_drift into guards.rs after env_names, GUARD_NAMES 74->75, dispatch arm; guards.md row after cli-reference; control-map part gCustomHarnessRouted id fb52dd3d-a1a3-4f85-b5f4-ea5e564f01a2 + dependency to ehz5; ci.yml and release.yml nextest expression names seven binary() terms and a cargo test -p keel-parser line runs lexer_bdd parser_bdd semantic_bdd spec_compat_bdd; comments in ci.yml release.yml touched.rs say seven; one deviation: the derived set is sorted by (crate, binary) because the root manifest lists keel-parser before keel-cli and the unit test read the set in a fixed order
    part ciNextestExcludesEveryCustomHarnessStandupGateR1 : TestResult { :>> id = "4fe8ee9b-58d9-4eac-befc-0db2fcc64144"; :>> outcome = VerdictKind::proposed; :>> judgedAgainst = "593147c"; :>> judgedAt = "2026-09-14"; :>> judgedBy = "claudeFable5"; }
    verification ciNextestExcludesEveryCustomHarnessImplementGate : Test { :>> id = "baf21040-3c07-4cdb-83bb-f6747848e324"; :>> title = "Sprint 709 implement gate"; :>> createdAt = "2026-09-14"; :>> createdBy = "claudeFable5"; :>> method = VerificationMethod::test; :>> procedureText = "The implement gate holds when: cargo test --release --lib -- custom_harness_routed passes the three unit tests; cargo clippy --release --all-targets -- -D warnings exits 0; keel gate guard --no-receipt . reports custom-harness-routed PASS with 2 scanned and ALL PASS overall; keel version counts one more guard than at 593147c; guard control-map-reconciled and doc-guard-count stay PASS. Its evidence quotes those commands' own lines."; }
    // RAN: cargo test --release --lib -- custom_harness_routed -> test result: ok. 3 passed; 0 failed (the_split_of_1e2ed25_names_keel_parsers_four_cucumber_binaries_as_missing, a_split_naming_every_declared_binary_under_its_crate_is_clean, this_workspace_declares_seven_and_both_workflows_route_them); cargo clippy --release --all-targets -- -D warnings -> Finished, exit=0 (after four indexing-may-panic lints in custom_harness_split were rewritten as zip pairs); keel gate guard --no-receipt . -> [guard:custom-harness-routed] PASS - 2 scanned, 0 warning(s), 0 violation(s); [guard:control-map-reconciled] PASS - 27 scanned; [guard:doc-guard-count] PASS - 4 scanned; keel version --json guards 75 (74 at 593147c); the only FAIL in that run is sprint-closure on this sprint's own unstamped story, which this record set discharges
    part ciNextestExcludesEveryCustomHarnessImplementGateR1 : TestResult { :>> id = "d8d8feb4-0ee0-42c2-b721-ab0913aa476c"; :>> outcome = VerdictKind::pass; :>> judgedAgainst = "593147c"; :>> judgedAt = "2026-09-14"; :>> judgedBy = "claudeFable5"; }
    verification ciNextestExcludesEveryCustomHarnessReviewGate : Test { :>> id = "fcb5933b-64da-4fee-8862-5a486e8b8787"; :>> title = "Sprint 709 review gate — three passes per D0172"; :>> createdAt = "2026-09-14"; :>> createdBy = "claudeFable5"; :>> method = VerificationMethod::inspect; :>> procedureText = "Three passes (D0172). Correctness: the expected set is derived from the manifests, never typed - adding a cucumber binary to any member changes the expectation without touching the guard; both directions are checked (declared-but-unrouted and routed-but-undeclared) because a renamed binary leaves the old name in the split. Honesty: the guard states its text-level limitation in its doc comment as gate-environment-parity does; the CI conclusion is read from gh run list --json conclusion, never from a wrapper's exit (D0420). Scope: the local touched runner stays -p keel-cli - the four keel-parser binaries are CI's to run, as they were under cargo test --workspace before D0475, and the fix restores exactly that coverage."; }
    // RAN: Correctness: workspace_custom_harnesses reads Cargo.toml [workspace] members and each member manifest through touched::custom_harness_tests - nothing typed; custom_harness_drift returns (missing, stale) and the unit pair exercises both directions including a renamed binary left in the split (stale keel-cli::old_bdd, ?::old_bdd). Honesty: the guard doc comment states the text-level limitation (binary(x) on the nextest line, -p and --test on the cargo test line) as gate-environment-parity does; the CI conclusion will be read from gh run list --json conclusion (D0420), and this sprint's story is stamped inconclusive until it is. Scope: touched.rs code unchanged, comments only; the local runner stays -p keel-cli
    part ciNextestExcludesEveryCustomHarnessReviewGateR1 : TestResult { :>> id = "e5af4be6-50cc-42d7-8e23-5bda9ec63356"; :>> outcome = VerdictKind::proposed; :>> judgedAgainst = "593147c"; :>> judgedAt = "2026-09-14"; :>> judgedBy = "claudeFable5"; }
    verification ciNextestExcludesEveryCustomHarnessCloseOutGate : Test { :>> id = "a1b21562-8adf-4f7c-9d8f-13736901ad31"; :>> title = "Sprint 709 closeOut gate (autonomous, D0049)"; :>> createdAt = "2026-09-14"; :>> createdBy = "claudeFable5"; :>> method = VerificationMethod::inspect; :>> procedureText = "Closes at the CR: commit that lands the two workflows, the guard with its registrations, the comments and this record together: keel-land runs the touched set from that commit (guards.rs changed, so the binaries keyed on it rerun; the rest are skipped at their observed keys, D0474); gate validate / check-engine / guard --no-receipt green over that tree with the new guard counted; dcCiNextestExcludesEveryCustomHarnessDoD carries a pass; the CI conclusion for the landing commit, read from gh run list --json conclusion after the run completes, is success; git status -sb shows main level with origin. The closeOut result is recorded AFTER that read, not before it (sprint707 recorded success before CI had run)."; }
    // RAN: PASS at 838f75f, with one deviation from the clause's letter stated: the clause names the CR: commit that lands the workflows and the guard - 6281526 - but that commit's own keel-land ran the touched set (889 s) and FAILED every_guard_has_a_constraint_def_identity on the guard's missing fourth registration home, so it never pushed and CI never ran on it (issue545). The landing commit is 838f75f, one line of guard-constraints.sysml later: keel-land ran the touched set from it (receipt outcome pass, runner cargo-nextest 0.9.144, green binaries skipped at their observed keys, D0474); `keel verify .` before it: validate pass, guard ALL PASS with 75 guards counted, clippy pass, touched 821 passed in 895 s; dcCiNextestExcludesEveryCustomHarnessDoD carries a pass at 838f75f (R1, ci-run receipt); CI conclusion for 838f75f read AFTER completion via `gh run list --limit 1 --json conclusion,status,headSha` -> success; `git status -sb` -> ## main...origin/main, level. Recorded after the read, not before (the sprint707 fault).
    part ciNextestExcludesEveryCustomHarnessCloseOutGateR1 : TestResult { :>> id = "44a97962-2249-4831-ab7e-34a43fcdafff"; :>> outcome = VerdictKind::proposed; :>> judgedAgainst = "838f75f"; :>> judgedAt = "2026-09-14"; :>> judgedBy = "claudeFable5"; }
    verification ciNextestExcludesEveryCustomHarnessRetroGate : Test { :>> id = "90cedc65-ea38-4518-be9b-c2ae3a6eeaec"; :>> title = "Sprint 709 retro gate (autonomous, D0049)"; :>> createdAt = "2026-09-14"; :>> createdBy = "claudeFable5"; :>> method = VerificationMethod::analyze; :>> procedureText = "Avoidable issues scanned; findings are tracked items, not prose. The class here is a hand-mirrored expectation beside a computable one, in a workflow file: the retro asks where else a workflow or hook restates by hand what a manifest or the binary already knows, and each such place found becomes an Issue with a resolver, not a line here. Finding one, met while recording this sprint's predecessor: the ceremony guard's order reader counted only pass and proposed, so sprint708's honestly FAILED closeOut read as unrecorded and its Retro as out of turn - the reader is the guard's own, not orient's (D0437), and the fix is tracked as issue544, resolved by dcCeremonyOrderCountsAFailedGateAsRecorded in sprint 710."; }
    // RAN: Avoidable issues scanned at 838f75f. Class in the clause (a workflow or hook restating by hand what a manifest or binary knows): grep -n for harness, --test and binary( over .github/workflows/*.yml and .githooks/* - the only hand-mirrored lists are the two the guard now derives and compares (ci.yml:36-38, release.yml), no new item. Finding one, named in the clause: issue544 / dcCeremonyOrderCountsAFailedGateAsRecorded, delivered in sprint 710 (closed at 838f75f). Finding two, from this sprint's own land: the guard passed gate validate, check-engine, guard --no-receipt and the fast tier registered in three of its four homes, and the fourth (D0195 clause 1, guard-constraints.sysml) is checked only by a unit test that ran 889 s into keel-land - tracked as issue545 (Medium) with resolver dcGuardIdentityIsCheckedAtTheGate, ranked after dcEvidenceGoesThroughAFile. Finding three: the D0476 ladder existed and was not climbed before 6281526; it was climbed before 838f75f and every rung was green in 964 s - no new item, the control exists and this names the recurrence to count. Finding four: `--evidence` spans with backticks in sprint 708's implement evidence were executed by the shell (issue543) - resolver dcEvidenceGoesThroughAFile, in sprint 711, whose first use of --evidence-from is this record and its siblings.
    part ciNextestExcludesEveryCustomHarnessRetroGateR1 : TestResult { :>> id = "56e263cb-b384-4146-863e-6525b1cec356"; :>> outcome = VerdictKind::proposed; :>> judgedAgainst = "838f75f"; :>> judgedAt = "2026-09-14"; :>> judgedBy = "claudeFable5"; }
}
