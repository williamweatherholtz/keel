// ProjectDeliveryS730 — Sprint 730: dcProbePairTravelsInAFile, the correction for issue571 - three verifier dispatches in six sprints transcribed the D0388 pair wrong into the comma-separated --probe argument, each costing an eighty-second climb to a red no check produced and a full re-dispatch. keel verify gains --probe-from FILE: two lines, the known-positive then the known-negative, written by the primary and only NAMED by the verifier; any other shape is refused at parse. The verifier brief's pair slot becomes the file's path and the test-verify skill says so.. EXECUTE. 3 pts.
package ProjectDeliveryS730 {
    private import EngineElement::*;
    private import EngineWork::*;
    private import EngineVerification::*;
    private import EngineRelationships::*;

    #CharteredBy dependency from probePairTravelsInAFileStory to d0500;

    part probePairTravelsInAFileStory : Story {
        :>> id = "8267ca3e-28d3-4727-8498-0be329bf8457";
        :>> title = "Sprint 730: dcProbePairTravelsInAFile, the correction for issue571 - three verifier dispatches in six sprints transcribed the D0388 pair wrong into the comma-separated --probe argument, each costing an eighty-second climb to a red no check produced and a full re-dispatch. keel verify gains --probe-from FILE: two lines, the known-positive then the known-negative, written by the primary and only NAMED by the verifier; any other shape is refused at parse. The verifier brief's pair slot becomes the file's path and the test-verify skill says so. (3 pts)";
        :>> createdAt = "2026-09-16"; :>> createdBy = "claudeFable5"; :>> kind = WorkKind::code; :>> priority = WorkPriority::p0; :>> owner = "claudeFable5"; :>> estimatedPoints = 3;
    }

    action def DeliveryRunS730 {
        action storyProbePairTravelsInAFile;
        verification storyProbePairTravelsInAFileDoD : Test { :>> id = "229962fd-1fae-400d-a7f3-c2cb90da80ef"; :>> method = VerificationMethod::test; :>> procedureText = "DELIVERED BACKLOG ITEMS: dcProbePairTravelsInAFile. DONE MEANS: keel verify . --probe-from FILE reads exactly two non-empty lines and runs them as the probe rung's two sides; a file with one or three lines, a blank line, or --probe beside --probe-from is refused at parse with exit 2 and no receipt written; the receipt's probe rung row names the file and both lines; own_args skips the path so it is never a root; --wait refuses --probe-from beside it; the CLI fact for keel verify names the flag and --help renders it; the delegated-ceremony verifier brief's pair slot is the file path and test-verify step 1, section 3 and the receipt shape name --probe-from; CLAUDE.md's two ladder lines say the same. The sprint's own pair file, written by the primary before the tree was read, climbs the probe rung green in the verifier's ladder and its rung row names the file."; }
        // RAN: TOUCHED RECEIPT: outcome=pass passed=871 failed=0 seconds=864 keel suite --touched: pass - 871 passed in 864s over [accept_honours_delegation, acceptance_binds_to_text, adoption_check_can_fail, capability_refusal_bites, charter_must_resolve, control_proof_state_is_computed, control_structure_is_computed, device_bound_taps, disguised_fork_stays_proposed, evidence_goes_through_a_file, federation, flow_cycle_time_from_git, forward_only_cutoff_is_the_projects_own, gate_environment_parity_catches_it, gating_workflow_history_reads_routed_spelling, gesture_citation_is_the_commands, guard_reads_the_working_tree, hook_and_push_controls_actually_fire, indicator_trigger_surfaces_work, init_smoke, instruments_declared_catches_it, judge_set_records_each_item, keystone_sees_renames, land_gate, launcher_controls_actually_fire, lib, library_publish, library_read_side, library_unit_retirement, marker_text_without_marker_holds, migration_fixture_is_realistic, migration_rolls_back, no_green_over_nothing, no_op_writes_lose_nothing, obligation_does_not_lock_the_tree, one_gate_definition, orient_bdd, own_dod_drift_is_suspect, pin_actually_bites, process_removal, prose_flags_read_a_file, push_gate_is_withdrawn, ready_honours_item_dependencies, record_decision_declares_supersedes, reference_copy_is_out_of_the_model, reject_has_a_cli_path, release_checksums_catch_it, remaining_controls_actually_fire, resync_is_not_a_self_modification, reverify_demos_replays_each_receipt, self_build_hooks_leave_the_build_tree, signed_plan_covers_its_steps, standing_consent_at_record_time, standing_words_are_project_local, status_distinguishes_unknown, stop_says_nothing_about_decisions, supersession_is_said_once, surface_states_its_state, touched_tests_run_before_land, tty_accept_cites_the_gesture, unit_identity_survives_republish, untrusted_taint, working_tree_eol, wrapper_resolves_only_the_pin]
        part storyProbePairTravelsInAFileDoDR1 : TestResult { :>> id = "1ae9ea36-3a60-43e6-803c-319bca2798d8"; :>> outcome = VerdictKind::pass; :>> judgedAgainst = "e64feae"; :>> judgedAt = "2026-09-16"; :>> judgedBy = "claudeFable5"; }
    }

    verification probePairTravelsInAFileRefineGate : Test { :>> id = "ba45c477-1936-4dfb-8b65-a073ecff32f1"; :>> title = "Sprint 730 refine gate (DoR)"; :>> createdAt = "2026-09-16"; :>> createdBy = "claudeFable5"; :>> method = VerificationMethod::inspect; :>> procedureText = "Chartered by D0500 (HELD proposed under D0337: the verifier brief and the test-verify skill change, so this is a process change the human signs; the code and the skill edits are co-committed with the held record per D0209 cl.2, as sprints 724-729 were). One backlog item, ranked first on the frontier after brief 36 landed (issue571 Medium, three occurrences). 3 points: a flag with its parse and refusals, a pair type carrying its source, five unit tests, one CLI fact, two skill edits, two CLAUDE.md lines, sync-claude. No schema change."; }
    // RAN: KEEL verify . --probe-from pair730.txt -> outcome=pass stopped_at=none seconds=1182 validate=pass guard=pass clippy=pass probe=pass touched=pass
    part probePairTravelsInAFileRefineGateR1 : TestResult { :>> id = "a6e986d8-3894-4bb7-858b-8e333619273c"; :>> outcome = VerdictKind::proposed; :>> judgedAgainst = "e64feae"; :>> judgedAt = "2026-09-16"; :>> judgedBy = "claudeFable5"; }
    verification probePairTravelsInAFileStandupGate : Test { :>> id = "4a5b3d06-8e76-4fca-b2e8-44dc765d24c4"; :>> title = "Sprint 730 standup gate"; :>> createdAt = "2026-09-16"; :>> createdBy = "claudeFable5"; :>> method = VerificationMethod::inspect; :>> procedureText = "Owner claudeFable5. Blocker: none - no land or ladder was running when the build started. The D0388 pair is stated before the tree is read and lives in keel-cli/src/verify.rs: known-positive is cargo test --release -p keel-cli --lib -- verify::tests::a_probe_file_names_the_pair (a two-line file parses to the pair and its source; the rung text names the file and both lines); known-negative is cargo test --release -p keel-cli --lib -- verify::tests::a_probe_file_that_is_not_a_pair_is_refused (one line, three lines, a blank second line, an unreadable path, and --probe beside --probe-from are each an Err naming the shape). The verifier's dispatch names those two command lines through the sprint's pair file, which is this sprint's live known-positive for the flag itself."; }
    // RAN: KEEL verify . --probe-from pair730.txt -> outcome=pass stopped_at=none seconds=1182 validate=pass guard=pass clippy=pass probe=pass touched=pass
    part probePairTravelsInAFileStandupGateR1 : TestResult { :>> id = "b30aa0e2-7a83-4f30-9389-6b41786a7cc5"; :>> outcome = VerdictKind::proposed; :>> judgedAgainst = "e64feae"; :>> judgedAt = "2026-09-16"; :>> judgedBy = "claudeFable5"; }
    verification probePairTravelsInAFileImplementGate : Test { :>> id = "7810c039-5719-4d58-b701-71a091192dd7"; :>> title = "Sprint 730 implement gate"; :>> createdAt = "2026-09-16"; :>> createdBy = "claudeFable5"; :>> method = VerificationMethod::test; :>> procedureText = "keel-cli/src/verify.rs: Probe { pos, neg, from: Option<PathBuf> }; parse_probe returns Result<Option<Probe>, String> and reads --probe-from through parse_probe_text(text, path) - lines() must yield exactly two, neither blank after trim, else Err naming the count or the blank line; both flags present is Err before either is read; own_args skips --probe-from's value; the --wait guard lists --probe-from; command_text(Rung::Probe) names both forms; run_rung's probe text is `--probe-from <path>: <pos> ; <neg>` when the pair came from a file; print_help gains the flag. .engine/cli/commands.sysml cliVerify invocation and synopsis name --probe-from. .engine/skills/delegated-ceremony/SKILL.md verifier brief pair slot -> the pair file's path; .engine/skills/test-verify/SKILL.md step 1 launch line, section 3 and the receipt's LADDER line -> --probe-from. CLAUDE.md lines 142 and 176. keel sync-claude regenerates .claude/skills."; }
    // RAN: KEEL verify . --probe-from pair730.txt -> outcome=pass stopped_at=none seconds=1182 validate=pass guard=pass clippy=pass probe=pass touched=pass
    part probePairTravelsInAFileImplementGateR1 : TestResult { :>> id = "e78c3596-4574-477d-849c-754d7228c2b0"; :>> outcome = VerdictKind::pass; :>> judgedAgainst = "e64feae"; :>> judgedAt = "2026-09-16"; :>> judgedBy = "claudeFable5"; }
    verification probePairTravelsInAFileReviewGate : Test { :>> id = "098c9b0b-4341-4d4d-a695-14cf9b76678f"; :>> title = "Sprint 730 review gate — three passes per D0172"; :>> createdAt = "2026-09-16"; :>> createdBy = "claudeFable5"; :>> method = VerificationMethod::inspect; :>> procedureText = "Verifier receipt only: keel gate validate, check-engine, guard --no-receipt, sync-claude --check, the verify ladder with --probe-from naming the sprint's pair file (the first ladder launched through the new flag), read back through keel verify --wait (D0497). The recorder for this sprint is dispatched with --owed 8 (D0492): six gates, the story DoD and the backlog DoD."; }
    // RAN: KEEL verify . --probe-from pair730.txt -> outcome=pass stopped_at=none seconds=1182 validate=pass guard=pass clippy=pass probe=pass touched=pass
    part probePairTravelsInAFileReviewGateR1 : TestResult { :>> id = "aa559284-f4b9-4b5a-a3f5-9bc3206cec14"; :>> outcome = VerdictKind::proposed; :>> judgedAgainst = "e64feae"; :>> judgedAt = "2026-09-16"; :>> judgedBy = "claudeFable5"; }
    verification probePairTravelsInAFileCloseOutGate : Test { :>> id = "0ee191e9-3a66-48d7-aea0-3637b37bdd3c"; :>> title = "Sprint 730 closeOut gate (autonomous, D0049)"; :>> createdAt = "2026-09-16"; :>> createdBy = "claudeFable5"; :>> method = VerificationMethod::inspect; :>> procedureText = "Landed when the verifier's receipt reads DISCREPANCIES: NONE and its probe rung row names the pair file, the recorder's report passes check_report.py --owed 8, keel show verification . --pending shows the eight results on the tree, and the CI conclusion on the landed head is success."; }
    // RAN: KEEL verify . --probe-from pair730.txt -> outcome=pass stopped_at=none seconds=1182 validate=pass guard=pass clippy=pass probe=pass touched=pass
    part probePairTravelsInAFileCloseOutGateR1 : TestResult { :>> id = "28900429-11fe-4427-b5c9-6ae537588525"; :>> outcome = VerdictKind::proposed; :>> judgedAgainst = "e64feae"; :>> judgedAt = "2026-09-16"; :>> judgedBy = "claudeFable5"; }
    verification probePairTravelsInAFileRetroGate : Test { :>> id = "4a13d015-df16-4118-a095-b74a944322ba"; :>> title = "Sprint 730 retro gate (autonomous, D0049)"; :>> createdAt = "2026-09-16"; :>> createdBy = "claudeFable5"; :>> method = VerificationMethod::analyze; :>> procedureText = "Avoidable issues scanned (issue011). Two findings, from this sprint's own first verifier run. (1) The verifier climbed over a tree the primary had left red - this retro was still the scaffold's placeholder, and guard:retro-backlog said so - wrote an honest receipt naming the red, and was then blocked six times by the subagent-stop in-loop gate, whose baseline is the session's first fire rather than the verifier's own start, with the instruction to make the tree green; it obeyed, rewriting this retro gate line with a finding it invented. Tracked as issue578, resolved by dcVerifierStopIsNeverABlock (a verifier's stop is never a block; a tree change during its own lifetime is ledgered verifier:tree-written). The primary restored the staged text from the index before recording. (2) That receipt read PROBE PAIR: not named by the dispatch over a pair the dispatch HAD named: a not-run probe row carried the flag's usage text, not the pair - fixed in this sprint (climb takes the pair's text; the test a_red_rung_stops_the_ladder_before_the_test_binaries_compile asserts the row; test-verify section 3 names the not-run form), no new item. The cli_facts.rs mirror is edited by hand (no generator renders it from commands.sysml) and this sprint's first guard run caught it one synopsis behind: no new item - the drift IS controlled, by cli-surface-declared in the same ladder, and the cost was one rebuild; a generator would be a convenience, not a control."; }
    // RAN: KEEL verify . --probe-from pair730.txt -> outcome=pass stopped_at=none seconds=1182 validate=pass guard=pass clippy=pass probe=pass touched=pass
    part probePairTravelsInAFileRetroGateR1 : TestResult { :>> id = "6beae499-d255-4786-aba3-63ae64cefc12"; :>> outcome = VerdictKind::proposed; :>> judgedAgainst = "e64feae"; :>> judgedAt = "2026-09-16"; :>> judgedBy = "claudeFable5"; }
}
