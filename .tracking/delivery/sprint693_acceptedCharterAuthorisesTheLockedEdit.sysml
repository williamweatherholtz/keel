// ProjectDeliveryS693 — Sprint 693: Work dcAcceptedCharterAuthorisesTheLockedEdit (issue517): the process-change keystone gains a second authorising source - a co-committed sprint record whose #CharteredBy names a marked Decision the human has ACCEPTED - so a process change held for the human (D0337) can be applied in the commit that does the work once accepted. CHANGE under D0465 (#SafetyChange, held proposed, rides this commit as the first source). 2 pts.. EXECUTE. 2 pts.
package ProjectDeliveryS693 {
    private import EngineElement::*;
    private import EngineWork::*;
    private import EngineVerification::*;
    private import EngineRelationships::*;

    #CharteredBy dependency from acceptedCharterAuthorisesTheLockedEditStory to d0465;

    part acceptedCharterAuthorisesTheLockedEditStory : Story {
        :>> id = "28b96b43-aac4-4381-9d26-b00d9d2aa9f6";
        :>> title = "Sprint 693: Work dcAcceptedCharterAuthorisesTheLockedEdit (issue517): the process-change keystone gains a second authorising source - a co-committed sprint record whose #CharteredBy names a marked Decision the human has ACCEPTED - so a process change held for the human (D0337) can be applied in the commit that does the work once accepted. CHANGE under D0465 (#SafetyChange, held proposed, rides this commit as the first source). 2 pts. (2 pts)";
        :>> createdAt = "2026-09-13"; :>> createdBy = "claudeFable5"; :>> kind = WorkKind::code; :>> priority = WorkPriority::p0; :>> owner = "claudeFable5"; :>> estimatedPoints = 2;
    }

    action def DeliveryRunS693 {
        action storyAcceptedCharterAuthorisesTheLockedEdit;
        verification storyAcceptedCharterAuthorisesTheLockedEditDoD : Test { :>> id = "69a1a0a8-13e2-4628-82c1-352c16a03fd2"; :>> method = VerificationMethod::test; :>> procedureText = "DELIVERED BACKLOG ITEMS: dcAcceptedCharterAuthorisesTheLockedEdit. Done means keystone_violations in keel-cli/src/guards.rs passes on either source; accepted_charters reads every changed .tracking/delivery/*.sysml, resolves each #CharteredBy target in the owning project's .engine/decisions, and admits only has_process_marker AND acceptance_kind == Human; the pass carries one warning naming the Decision and the sprint file; staged_marked_decision (workspace gate) accepts the same source; the refusal names both paths; the D0388 pair is a unit test (positive human-accepted marked charter; negatives auto-accepted, proposed, unmarked; prose #CharteredBy inside a string is not an edge); guards.md's process-change row states the second path; the live pair holds on this tree."; }
        // RAN: cargo test -p keel-cli --lib keystone -> 3 passed 0 failed; cargo clippy -p keel-cli --release -- -D warnings -> Finished; cargo build --release -> exit 0, keel-serve.exe version build eda9647+dirty; LIVE with 0465 file out of tree: sprint692 chartered by d0460 -> [guard:process-change] PASS 1 warning naming d0460 and the sprint file; chartered by d0465 (proposed) -> FAIL 1 violation naming both paths
        part storyAcceptedCharterAuthorisesTheLockedEditDoDR1 : TestResult { :>> id = "6e412220-e68b-462b-9be3-4638d0f01809"; :>> outcome = VerdictKind::pass; :>> judgedAgainst = "eda9647"; :>> judgedAt = "2026-09-13"; :>> judgedBy = "claudeFable5"; }
    }

    verification acceptedCharterAuthorisesTheLockedEditRefineGate : Test { :>> id = "d2c00818-2b24-4bdd-a49d-bd08017812e8"; :>> title = "Sprint 693 refine gate (DoR)"; :>> createdAt = "2026-09-13"; :>> createdBy = "claudeFable5"; :>> method = VerificationMethod::inspect; :>> procedureText = "Chartered by D0465. Two points: one guard function, four helpers, one unit test, a doc row, a live pair. DoR: issue517 recorded with #Resolves from the item; the DoD names the live VERIFY (PASS with the accepted charter, FAIL with a proposed one); acceptance_kind and has_process_marker already exist in guards.rs, so the second source composes what the guard already reads. Not a fork: the alternative (touch the accepted Decision's file so it counts as changed) is an edit made to satisfy a guard - the class the lock exists to refuse - and D0465 says so."; }
    part acceptedCharterAuthorisesTheLockedEditRefineGateR1 : TestResult { :>> id = "7c9bc2e7-974d-4138-8db8-97bbd373972a"; :>> outcome = VerdictKind::proposed; :>> judgedAgainst = "eda9647"; :>> judgedAt = "2026-09-13"; :>> judgedBy = "claudeFable5"; }
    verification acceptedCharterAuthorisesTheLockedEditStandupGate : Test { :>> id = "a9737cc3-a1b8-4d48-8df7-ef3559db6e4d"; :>> title = "Sprint 693 standup gate"; :>> createdAt = "2026-09-13"; :>> createdBy = "claudeFable5"; :>> method = VerificationMethod::inspect; :>> procedureText = "Order: read keystone_violations and its callers (process_change, staged_marked_decision); write charter_targets (line-anchored edge parse), is_authorising_charter, is_sprint_record, accepted_charters; thread the charters through keystone_violations and add the warning line in process_change; extend the refusal; write the unit test with the D0388 pair; update guards.md; cargo test keystone, clippy -D warnings, cargo build --release, refresh keel-serve.exe; live pair against sprint 692's file with D0465's own file moved out of the tree so only the second source can pass; record."; }
    part acceptedCharterAuthorisesTheLockedEditStandupGateR1 : TestResult { :>> id = "5c7bc794-0e97-467d-9499-725f5c415b63"; :>> outcome = VerdictKind::proposed; :>> judgedAgainst = "eda9647"; :>> judgedAt = "2026-09-13"; :>> judgedBy = "claudeFable5"; }
    verification acceptedCharterAuthorisesTheLockedEditImplementGate : Test { :>> id = "77fdfd16-4dff-4b90-9b86-9e365f41c44f"; :>> title = "Sprint 693 implement gate"; :>> createdAt = "2026-09-13"; :>> createdBy = "claudeFable5"; :>> method = VerificationMethod::test; :>> procedureText = "keel-cli/src/guards.rs: charter_targets, is_authorising_charter, is_sprint_record, accepted_charters added before keystone_violations; keystone_violations(changed, decision_texts, charters) passes when marked || !charters.is_empty(); process_change computes accepted_charters(root, read) and pushes the warning 'locked edit authorised by dNNNN, a marked Decision the human accepted, cited as the charter of the co-committed sprint record FILE (D0465)'; staged_marked_decision ORs the same source; keystone_selftest calls gained the empty third argument; new test keystone_accepts_a_human_accepted_marked_charter_and_nothing_weaker. .engine/docs/guards.md process-change row states TWO authorising sources. RAN: cargo test -p keel-cli --lib keystone -> 3 passed, 0 failed (test exit 0); cargo clippy -p keel-cli --release -- -D warnings -> Finished (clippy exit 0); cargo build --release -> build exit 0; keel-serve.exe version -> build commit eda9647+dirty, guards 73. LIVE: with 0465's file moved out of the tree and sprint692 chartered by d0460 -> [guard:process-change] PASS, 1 warning: 'locked edit authorised by d0460, a marked Decision the human accepted, cited as the charter of the co-committed sprint record .tracking/delivery/sprint692_testResultSkillNamesTheBinding.sysml (D0465)'; the same sprint chartered by d0465 (proposed) -> [guard:process-change] FAIL, 1 violation naming both paths; file and charter restored."; }
    // RAN: cargo test -p keel-cli --lib keystone -> 3 passed 0 failed; cargo clippy -p keel-cli --release -- -D warnings -> Finished; cargo build --release -> exit 0, keel-serve.exe version build eda9647+dirty; LIVE with 0465 file out of tree: sprint692 chartered by d0460 -> [guard:process-change] PASS 1 warning naming d0460 and the sprint file; chartered by d0465 (proposed) -> FAIL 1 violation naming both paths
    part acceptedCharterAuthorisesTheLockedEditImplementGateR1 : TestResult { :>> id = "c3a9098e-65cb-43ea-a738-8a6119cafd33"; :>> outcome = VerdictKind::pass; :>> judgedAgainst = "eda9647"; :>> judgedAt = "2026-09-13"; :>> judgedBy = "claudeFable5"; }
    verification acceptedCharterAuthorisesTheLockedEditReviewGate : Test { :>> id = "1b1c5f01-52a6-4859-9fac-3c326f5ab30f"; :>> title = "Sprint 693 review gate — three passes per D0172"; :>> createdAt = "2026-09-13"; :>> createdBy = "claudeFable5"; :>> method = VerificationMethod::inspect; :>> procedureText = "Three passes (D0172). Correctness: the second source reads acceptance from the Decision file on disk (accepted_charters), so a charter accepted in an earlier commit authorises, and a charter whose acceptance is only staged in this commit also does - which is the record-and-accept-together case the human already had. charter_targets is line-anchored on '#CharteredBy dependency from X to dNNNN;' so an edge quoted inside a procedureText string does not authorise (unit-tested). Honesty: the guard's pass now prints WHO authorised it; before D0465 a pass was silent about which Decision it read. Scope: is_enforcement_surface and is_process_def unchanged; the first source unchanged; the exemption D0441 unchanged; no other guard touched. Residual stated: any accepted marked charter in the commit authorises EVERY locked edit in the commit, as the first source already did for any marked Decision - the lock binds the commit, not the file."; }
    part acceptedCharterAuthorisesTheLockedEditReviewGateR1 : TestResult { :>> id = "99c8893b-65d1-4f5b-9e35-e99a002773ed"; :>> outcome = VerdictKind::proposed; :>> judgedAgainst = "eda9647"; :>> judgedAt = "2026-09-13"; :>> judgedBy = "claudeFable5"; }
    verification acceptedCharterAuthorisesTheLockedEditCloseOutGate : Test { :>> id = "e824390a-369b-46d8-b46d-fea46da57b80"; :>> title = "Sprint 693 closeOut gate (autonomous, D0049)"; :>> createdAt = "2026-09-13"; :>> createdBy = "claudeFable5"; :>> method = VerificationMethod::inspect; :>> procedureText = "Closes on gate validate, gate check-engine, gate guard --no-receipt ALL PASS over the tree holding D0465, sprints 692-694 and the guards.rs change; cargo test keystone 3 passed; clippy clean; the commit lands with D0465 co-committed as a #SafetyChange and the CR: prefix; issue517 resolution computed from the item's result."; }
    part acceptedCharterAuthorisesTheLockedEditCloseOutGateR1 : TestResult { :>> id = "8272e8c7-2266-4606-8dfd-06fde9943f8f"; :>> outcome = VerdictKind::proposed; :>> judgedAgainst = "eda9647"; :>> judgedAt = "2026-09-13"; :>> judgedBy = "claudeFable5"; }
    verification acceptedCharterAuthorisesTheLockedEditRetroGate : Test { :>> id = "34d7de75-9c3d-43b8-87b4-cce18b852767"; :>> title = "Sprint 693 retro gate (autonomous, D0049)"; :>> createdAt = "2026-09-13"; :>> createdBy = "claudeFable5"; :>> method = VerificationMethod::analyze; :>> procedureText = "AVOIDABLE-ISSUE SCAN (D0131): the gap existed since D0337 (2026-09-04) made process-change Decisions HELD - every held-then-accepted process change since then either rode a later marked Decision or touched its own Decision file to count as changed. That is evidence of a defect class, so it is tracked as issue517 with this item as resolver, not restated as a Decision. One new item: the guard passes on a charter whose acceptance is itself uncommitted (read from disk, working tree) - the pair here read a committed acceptance, and a live probe of the staged-acceptance case is owed before the residual is called covered; recorded as issue518 with resolver dcStagedAcceptanceIsProbedAsACharter."; }
    part acceptedCharterAuthorisesTheLockedEditRetroGateR1 : TestResult { :>> id = "3f804add-aff6-4d57-8956-386566bb2762"; :>> outcome = VerdictKind::proposed; :>> judgedAgainst = "eda9647"; :>> judgedAt = "2026-09-13"; :>> judgedBy = "claudeFable5"; }
}
