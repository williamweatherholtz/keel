// ProjectDeliveryS712 — Sprint 712: Resolve issue547 and issue548 through dcCliFactSupersessionIsHonoured. D0108 says a non-owner ADDS or SUPERSEDES, never overwrites, and guard ownership enforces it; but for a CliCommand fact the SUPERSEDE remedy does not work, because parse_cli_facts (guards.rs:6947) reads every line containing : CliCommand { and ignores #Supersede, so a superseder of the same command name is a second fact and the retired one still speaks. Twice now (74c1923 cliGithub, sprint 711 cliRecord) the only passing path was to delete the part and re-author it under a new id, discarding Invariant 3's immutable identity to satisfy an ownership rule whose own remedy the reader cannot see - and every fact authored by a retired actor meets the same wall at its next change. Reading the same code for the fix found issue548: cli_surface_violations compares family, effect, stability and synopsis and never the invocation, so facts = help = dispatch (D0271) is not held for the field --help renders, and accept already drifts between its two homes. Chartered by D0477 (cli-surface-declared reads the facts in force and every field; process-change, proposed for the human), under D0271 (the CLI surface is typed facts and this guard is its control) and D0108 (owner edits own items; others add or supersede). 2 pts.. EXECUTE. 2 pts.
package ProjectDeliveryS712 {
    private import EngineElement::*;
    private import EngineWork::*;
    private import EngineVerification::*;
    private import EngineRelationships::*;

    // D0477 (#ProspectiveChange, held proposed for the human - D0337) is the clause this sprint executes: guard
    // cli-surface-declared reads the facts IN FORCE and compares every field. It is co-committed as the marked
    // Decision that authorises the guards.rs edit. D0271 made the surface typed facts and this guard their
    // control; D0108 is the rule whose supersede remedy the reader now honours.
    #CharteredBy dependency from cliFactSupersessionIsHonouredStory to d0477;
    #DependsOn dependency from cliFactSupersessionIsHonouredStory to d0271;
    #DependsOn dependency from cliFactSupersessionIsHonouredStory to d0108;

    part cliFactSupersessionIsHonouredStory : Story {
        :>> id = "e85baeed-caa7-4835-9b39-a7464080ee42";
        :>> title = "Sprint 712: Resolve issue547 and issue548 through dcCliFactSupersessionIsHonoured. D0108 says a non-owner ADDS or SUPERSEDES, never overwrites, and guard ownership enforces it; but for a CliCommand fact the SUPERSEDE remedy does not work, because parse_cli_facts (guards.rs:6947) reads every line containing : CliCommand { and ignores #Supersede, so a superseder of the same command name is a second fact and the retired one still speaks. Twice now (74c1923 cliGithub, sprint 711 cliRecord) the only passing path was to delete the part and re-author it under a new id, discarding Invariant 3's immutable identity to satisfy an ownership rule whose own remedy the reader cannot see - and every fact authored by a retired actor meets the same wall at its next change. Reading the same code for the fix found issue548: cli_surface_violations compares family, effect, stability and synopsis and never the invocation, so facts = help = dispatch (D0271) is not held for the field --help renders, and accept already drifts between its two homes. Chartered by D0477 (cli-surface-declared reads the facts in force and every field; process-change, proposed for the human), under D0271 (the CLI surface is typed facts and this guard is its control) and D0108 (owner edits own items; others add or supersede). 2 pts. (2 pts)";
        :>> createdAt = "2026-09-14"; :>> createdBy = "claudeFable5"; :>> kind = WorkKind::code; :>> priority = WorkPriority::p0; :>> owner = "claudeFable5"; :>> estimatedPoints = 2;
    }

    action def DeliveryRunS712 {
        action storyCliFactSupersessionIsHonoured;
        verification storyCliFactSupersessionIsHonouredDoD : Test { :>> id = "77487b07-3780-434c-bddd-917064f4c435"; :>> method = VerificationMethod::test; :>> procedureText = "Resolves issue547 and issue548: parse_cli_facts carries each fact's part name and honours #Supersede dependency from X to Y; lines in the same file (the edge lives beside the fact, one home), so a superseded CliCommand is not an authored fact in force; supersede_edges also scans .engine/cli so the retired set every kernel-free reader shares agrees. cli_surface_violations compares invocation alongside the four fields and reports two facts in force of one name as a violation. cli_facts.rs accept is regenerated to the .sysml invocation. Known-positive: a fixture with cliX superseded by cliX2 of the same name yields one authored fact, the superseder's, and a mirror equal to it is clean; known-negative: the same fixture without the edge is a duplicate-name violation, and a mirror whose invocation differs is an invocation violation (unit tests in guards.rs). The two delete-and-re-author precedents are not re-opened."; }
        // RAN: cargo test --release -p keel-cli --lib -- cli_surface -> 12 passed 0 failed. Known-positive a_superseded_fact_is_not_in_force_and_two_live_facts_of_one_name_are_a_violation: cliX superseded by cliX2 of one name parses to ONE fact (part cliX2, synopsis s) and a level mirror is clean; known-negative: the same two lines without the edge -> violation naming `cliX` and `cliX2` as two CliCommand facts in force. an_invocation_that_drifts_between_the_two_homes_is_caught: mirror invocation differs -> 1 violation containing 'invocation differs' and '--words'; level mirror -> clean. supersede_edges dirs now [.engine/decisions, .engine/cli, .tracking] (lib.rs). cli_facts.rs accept invocation regenerated. keel gate guard --no-receipt . -> cli-surface-declared PASS 86 scanned. Precedents not re-opened (git status: commands.sysml clean).
        part storyCliFactSupersessionIsHonouredDoDR1 : TestResult { :>> id = "d23a09ca-33f8-4d5f-a375-1e17c9fd7ce4"; :>> outcome = VerdictKind::pass; :>> judgedAgainst = "c592ef6"; :>> judgedAt = "2026-09-14"; :>> judgedBy = "claudeFable5"; }
    }

    verification cliFactSupersessionIsHonouredRefineGate : Test { :>> id = "8a34ec6a-916b-4603-8f0e-e8b6e62818b5"; :>> title = "Sprint 712 refine gate (DoR)"; :>> createdAt = "2026-09-14"; :>> createdBy = "claudeFable5"; :>> method = VerificationMethod::inspect; :>> procedureText = "Chartered by D0477 (#ProspectiveChange, recorded in this commit and held proposed - D0337), under D0271 (the Decision whose control this guard is) and D0108 (the rule honoured). The change is to a guard's reader and comparison (guards.rs) plus the mirror; it tightens cli-surface-declared by two new violation classes on facts that today pass, so the tree is probed for both before the tightening is claimed: the invocation diff over 86 facts finds exactly one (accept, the mirror side is wrong) and no two facts in force share a name. It IS a process change: an enforced guard's reader and comparison change (two new violation classes), so D0477 carries the marker and waits for the human's word; guards.rs is a locked file and the co-committed marked Decision is what authorises the edit - D0271 could not, its acceptance being standing consent (D0337). Two points: one reader, one comparison, one mirror line, a scan directory, four unit tests. DoR: dcCliFactSupersessionIsHonoured ranks first on keel show whats-next after the reorder recorded in this commit."; }
    // RAN: DoR at c592ef6. keel show whats-next . -> dcCliFactSupersessionIsHonoured ranks first after the backlog reorder (rank.py moved it before dcEveryProseFlagReadsAFile; #DependsOn edge from dcEveryProseFlagReadsAFile to it recorded). estimatedPoints 2 on the Story. Charter: #CharteredBy to d0477 (process-change, recorded this commit, held proposed - D0337), #DependsOn d0271 and d0108. DoD on dcCliFactSupersessionIsHonoured amended to name issue548 and the invocation comparison. Probe pair before the tightening: python inv_diff.py over both fact homes -> 86 facts, 1 DIFF (accept: fact --words|--note, mirror --note only); duplicate names in force -> 0.
    part cliFactSupersessionIsHonouredRefineGateR1 : TestResult { :>> id = "33994fcd-b45a-4a14-8e67-10e9c0f5a864"; :>> outcome = VerdictKind::proposed; :>> judgedAgainst = "c592ef6"; :>> judgedAt = "2026-09-14"; :>> judgedBy = "claudeFable5"; }
    verification cliFactSupersessionIsHonouredStandupGate : Test { :>> id = "07b7f7ff-b6b0-49f3-876a-1b0a98b3139b"; :>> title = "Sprint 712 standup gate"; :>> createdAt = "2026-09-14"; :>> createdBy = "claudeFable5"; :>> method = VerificationMethod::inspect; :>> procedureText = "Order: this record first; AuthoredCliFact gains part; parse_cli_facts collects #Supersede targets from the text and drops facts whose part is a target; supersede_edges adds .engine/cli to its scan; cli_surface_violations compares invocation and reports duplicate names in force; cli_facts.rs accept invocation regenerated; unit tests for the positive and negative pairs of both classes; cargo build --release, copy, cargo test --release --lib -- cli_surface, clippy -D warnings, gate guard --no-receipt with cli-surface-declared PASS on the real tree; then keel verify . and the land."; }
    // RAN: Order followed at c592ef6: sprint record first (fill712.md); AuthoredCliFact.part; parse_cli_facts collects #Supersede targets from its own text and drops facts whose part is a target; lib.rs supersede_edges adds .engine/cli; cli_surface_violations compares invocation and reports two facts in force of one name; cli_facts.rs accept invocation regenerated; two probe tests (a_superseded_fact_is_not_in_force_and_two_live_facts_of_one_name_are_a_violation, an_invocation_that_drifts_between_the_two_homes_is_caught). Blocker met and cleared: process-change red under d0108 then d0271 (both standing-consent acceptances, no Acceptance::Human, guards.rs:1304) -> D0477 recorded --process-change as the co-committed marked Decision.
    part cliFactSupersessionIsHonouredStandupGateR1 : TestResult { :>> id = "171a14ee-edf2-4c52-8c80-595e533e0946"; :>> outcome = VerdictKind::proposed; :>> judgedAgainst = "c592ef6"; :>> judgedAt = "2026-09-14"; :>> judgedBy = "claudeFable5"; }
    verification cliFactSupersessionIsHonouredImplementGate : Test { :>> id = "c6b78494-4abf-4c23-aaca-4a439a18eff6"; :>> title = "Sprint 712 implement gate"; :>> createdAt = "2026-09-14"; :>> createdBy = "claudeFable5"; :>> method = VerificationMethod::test; :>> procedureText = "The implement gate holds when: cargo test --release --lib -- guards::cli_surface passes the existing tests and the four new ones; cargo clippy --release --all-targets -- -D warnings exits 0; keel gate guard --no-receipt . reports cli-surface-declared PASS with the mirror regenerated; keel --help renders accept with the --words form; sync-claude --check clean. Its evidence quotes those commands' own lines through --evidence-from."; }
    // RAN: cargo test --release -p keel-cli --lib -- cli_surface -> 12 passed 0 failed (the two new probe tests among them). cargo clippy --release --all-targets -- -D warnings -> Finished release, no warnings. keel gate guard --no-receipt . -> [guard:cli-surface-declared] PASS 86 scanned 0 violation(s); [guard:process-change] PASS 1 scanned (working tree); [guard:retro-backlog] PASS; ALL PASS. Real-tree probe before revert: old binary with a probe superseder of cliOverride -> PASS 87 scanned (defect present); new binary -> FAIL 86 scanned naming the override invocation drift (control catches); probe reverted -> PASS 86. keel --help renders accept as <decision> (--words TEXT | --note TEXT) --by <person> --date YYYY-MM-DD. keel sync-claude --check . -> keel-owned subset matches this binary's generator (47 registry skill(s)). keel gate validate . -> 817 clean; gate check-engine . -> clean.
    part cliFactSupersessionIsHonouredImplementGateR1 : TestResult { :>> id = "51225dca-ae73-41ca-8e01-c100626a4624"; :>> outcome = VerdictKind::pass; :>> judgedAgainst = "c592ef6"; :>> judgedAt = "2026-09-14"; :>> judgedBy = "claudeFable5"; }
    verification cliFactSupersessionIsHonouredReviewGate : Test { :>> id = "e06729de-1322-4767-95b8-ed4b165dd37b"; :>> title = "Sprint 712 review gate — three passes per D0172"; :>> createdAt = "2026-09-14"; :>> createdBy = "claudeFable5"; :>> method = VerificationMethod::inspect; :>> procedureText = "Three passes (D0172). Correctness: the retired set is read from the same text the facts are read from, so a fact and its supersession cannot be split across files and read by one but not the other; the duplicate-name check runs on facts in force only, so a superseder sharing its target's name is the intended case, not a violation. Honesty: the two new violation classes were probed against the real tree before being enabled (one invocation drift, on the mirror side, fixed here; zero duplicate names); the precedents are left as they are. Scope: the ownership guard is untouched - D0108's rule was right, its remedy was unreadable."; }
    // RAN: Three passes (D0172) at c592ef6. Correctness: the retired set is collected from the same text the facts are parsed from (guards.rs parse_cli_facts), so a fact and its #Supersede cannot be split across files; the duplicate-name check runs after retired facts are dropped, so a superseder sharing its target's name is the intended case and the unit test asserts it. Honesty: both new violation classes were probed on the real tree before enabling - inv_diff.py 86 facts 1 drift (accept, mirror side, fixed in cli_facts.rs), 0 duplicate names; the refine text that said NOT A PROCESS CHANGE was wrong and is corrected - this is an enforced guard's reader changing, D0477 carries the marker. Scope: guard ownership untouched; the two delete-and-re-author precedents (74c1923, sprint 711) left as landed; D0271's D0188 warning (no inbound edge) noted, not this sprint's.
    part cliFactSupersessionIsHonouredReviewGateR1 : TestResult { :>> id = "c3f27de1-95a0-45cf-b574-a6e21c892915"; :>> outcome = VerdictKind::proposed; :>> judgedAgainst = "c592ef6"; :>> judgedAt = "2026-09-14"; :>> judgedBy = "claudeFable5"; }
    verification cliFactSupersessionIsHonouredCloseOutGate : Test { :>> id = "7244fe06-903b-4b52-9fe3-4cb9f2467299"; :>> title = "Sprint 712 closeOut gate (autonomous, D0049)"; :>> createdAt = "2026-09-14"; :>> createdBy = "claudeFable5"; :>> method = VerificationMethod::inspect; :>> procedureText = "Closes at the commit that lands the reader, the comparison, the mirror line and the tests with this record: keel-land runs the touched set; gate validate / check-engine / guard --no-receipt green; dcCliFactSupersessionIsHonouredDoD carries a pass through --evidence-from; git status -sb level with origin and the CI conclusion for that commit read from gh run list --json conclusion."; }
    // RAN: Sprint 712 closed at af5def6 (CR: cli-surface-declared reads the facts in force and compares the invocation). keel-land touched set: .keel/metrics/touched-receipt.toml head = af5def6, outcome = pass, passed = 679, failed = 0, runner = cargo-nextest 0.9.144, stems cli_facts/guards/init. Post-land reads on 2026-09-14: git status -sb -> main...origin/main (level); gh run list --limit 1 --json conclusion,status,headSha -> conclusion success, status completed, headSha af5def638d8e411e3c8e16906f4c2c6473271659. gate validate / check-engine / guard --no-receipt were green in the pre-commit verify ladder (verify-receipt.toml pass, 927 s). dcCliFactSupersessionIsHonouredDoDR1 pass at c592ef6 through --evidence-from.
    part cliFactSupersessionIsHonouredCloseOutGateR1 : TestResult { :>> id = "5591ff21-0f26-4dc4-bee9-e67b66a08b06"; :>> outcome = VerdictKind::proposed; :>> judgedAgainst = "af5def6"; :>> judgedAt = "2026-09-14"; :>> judgedBy = "claudeFable5"; }
    verification cliFactSupersessionIsHonouredRetroGate : Test { :>> id = "72cd83e5-3359-4cce-8252-5c9774f17f56"; :>> title = "Sprint 712 retro gate (autonomous, D0049)"; :>> createdAt = "2026-09-14"; :>> createdBy = "claudeFable5"; :>> method = VerificationMethod::analyze; :>> procedureText = "Avoidable issues scanned; findings are tracked items, not prose. The class here is a rule whose remedy the enforcing reader could not see: D0108 named SUPERSEDE as the path and the guard behind D0271 did not read the edge, so two sprints paid a cost the rule said they need not. One finding already tracked in this commit: issue548 (cli-surface-declared never compared the invocation, and accept had drifted), found by the reading this sprint did, resolver dcCliFactSupersessionIsHonoured - the same task, its DoD amended to name it. The retro asks whether any other guard names a remedy its reader does not honour, and each found becomes an Issue with a resolver."; }
    // RAN: Retro for sprint 712, read at af5def6. Finding class: a rule whose remedy its enforcing reader could not see (D0108 supersede vs the cli-surface-declared parser). Already tracked: issue548 (invocation never compared; accept drifted between homes), resolver dcCliFactSupersessionIsHonoured, delivered in the same commit. The retro's open question - does any other guard name a remedy its reader does not honour - was answered on the first real use of the new reader in sprint 713: four claudeOpus5-owned CliCommand facts (cliAccept, cliReject, cliJudgeSet, cliOverride) were retired by #Supersede edges beside them and cli-surface-declared reported PASS at 86 scanned with ownership PASS (keel gate guard --no-receipt ., 2026-09-14), so the path D0108 names now passes the guard that used to wall it. No further guard was found reading a remedy it ignores in this pass; no new item beyond issue548.
    part cliFactSupersessionIsHonouredRetroGateR1 : TestResult { :>> id = "0e89abb7-67a9-49ad-bc3b-1398ede6e025"; :>> outcome = VerdictKind::proposed; :>> judgedAgainst = "af5def6"; :>> judgedAt = "2026-09-14"; :>> judgedBy = "claudeFable5"; }
}
