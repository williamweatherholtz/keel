// ProjectDeliveryS756 — Sprint 756: Every row of .engine/docs/guards.md carries a Family cell naming the module that dispatches the guard, and doc-guard-count holds that cell equal to the FAMILIES tables - a guard moved between family files without its row is a red gate (D0539; issue584, issue667). EXECUTE. 2 pts.
package ProjectDeliveryS756 {
    private import EngineElement::*;
    private import EngineWork::*;
    private import EngineVerification::*;
    private import EngineRelationships::*;

    #CharteredBy dependency from guardsCatalogueNamesTheFamilyStory to d0539;
    #Delivers dependency from guardsCatalogueNamesTheFamilyStory to dcGuardsCatalogueNamesTheFamily;

    part guardsCatalogueNamesTheFamilyStory : Story {
        :>> id = "a82edfd1-99ec-47e8-a306-66674a3a0c98";
        :>> title = "Sprint 756: Every row of .engine/docs/guards.md carries a Family cell naming the module that dispatches the guard, and doc-guard-count holds that cell equal to the FAMILIES tables - a guard moved between family files without its row is a red gate (D0539; issue584, issue667) (2 pts)";
        :>> createdAt = "2026-09-20"; :>> createdBy = "claudeFable5"; :>> kind = WorkKind::code; :>> priority = WorkPriority::p0; :>> owner = "claudeFable5"; :>> estimatedPoints = 2;
    }

    action def DeliveryRunS756 {
        action storyGuardsCatalogueNamesTheFamily;
        verification storyGuardsCatalogueNamesTheFamilyDoD : Test { :>> id = "e47c7416-98dc-4b51-9223-18c20bd799d6"; :>> method = VerificationMethod::test; :>> procedureText = "DELIVERED BACKLOG ITEM: dcGuardsCatalogueNamesTheFamily. DONE MEANS: the task's DoD passes as written - both catalogue tables read | Guard | Family | ... | and each of the 77 rows names the family from members/keel-guards/src/<family>.rs FAMILY tables; doc_guard_count in enforcement.rs extends its violations with family_cell_violations, which for a file whose header declares the column reads every | `guard` | cell | row and fails one whose cell is empty, is not a family, or names another family, the message carrying file:line, the row, the cell, the dispatching family and its module path; a file without the header claims nothing (the keel-process cursor.rs fixture stays a count-only red); family_cell_tests hold the D0388 pair (a fixture row naming doc-guard-count under identity fails naming identity and enforcement, a row with an empty cell fails naming sprints; the shipped catalogue passes and every GUARD_NAMES member's row carries its dispatching family); every_catalogue_row_sits_inside_a_table in lib.rs holds that each row renders under a table header (issue667 - twenty rows did not); guards.md's preamble and doc-guard-count row describe the column and the clause. Verified by the verifier ladder with the two family_cell_tests as the D0388 pair and keel gate guard green at the landing tree."; }
        // RAN: validate=pass guard=pass clippy=pass probe=pass touched=pass; 922 passed in 822s
        part storyGuardsCatalogueNamesTheFamilyDoDR1 : TestResult { :>> id = "076275ee-ee0e-43fa-8efd-7adec8ec0394"; :>> outcome = VerdictKind::pass; :>> judgedAgainst = "957b2888"; :>> judgedAt = "2026-09-20"; :>> judgedBy = "claudeFable5"; }
    }

    verification guardsCatalogueNamesTheFamilyRefineGate : Test { :>> id = "94b8563f-45b5-4d4c-8c6b-b7897de0e551"; :>> title = "Sprint 756 refine gate (DoR)"; :>> createdAt = "2026-09-20"; :>> createdBy = "claudeFable5"; :>> method = VerificationMethod::inspect; :>> procedureText = "One backlog item, sized 2: one new clause on an existing hard guard with three pure helpers, three unit tests in its family module and one in lib.rs, a one-shot regeneration of the catalogue's two tables (77 rows, reconciled row count and family coverage), two Issues and one resolver task. DoR: estimatedPoints 2; #CharteredBy d0539 (proposed, #ProspectiveChange, held for the human - the guard change rides it as the co-committed Decision); #Delivers dcGuardsCatalogueNamesTheFamily; no blocking dependency; the DoD exists in the backlog with its known-positive and known-negative named before the tree was read, its guard name corrected from doc-sync to doc-guard-count by its owner before work began (the item is undone, so the edit makes nothing suspect)."; }
    // RAN: validate=pass guard=pass clippy=pass probe=pass touched=pass
    part guardsCatalogueNamesTheFamilyRefineGateR1 : TestResult { :>> id = "1f047840-0b16-484c-84a5-9c1f45ff84ec"; :>> outcome = VerdictKind::proposed; :>> judgedAgainst = "957b2888"; :>> judgedAt = "2026-09-20"; :>> judgedBy = "claudeFable5"; }
    verification guardsCatalogueNamesTheFamilyStandupGate : Test { :>> id = "205b296c-c564-4317-a4d8-3f71d9100f5b"; :>> title = "Sprint 756 standup gate"; :>> createdAt = "2026-09-20"; :>> createdBy = "claudeFable5"; :>> method = VerificationMethod::inspect; :>> procedureText = "The clause sits in doc-guard-count, not doc-sync: doc-sync is a diff guard whose violations are always empty, and the DoD asks for a red gate. The header scope is deliberate: the clause reads a catalogue file only where its table header declares the Family column, so a downstream copy of guards.md shipped before the column stays green (D0419, issue433). The tier census run to place the five orphaned rows found that the catalogue's tier, WARNING_ONLY_GUARDS and the code disagree for five guards - not this item's clause, so it is issue668 with its own resolver dcGuardTierHasOneHome. Impediment: none."; }
    // RAN: validate=pass guard=pass clippy=pass probe=pass touched=pass
    part guardsCatalogueNamesTheFamilyStandupGateR1 : TestResult { :>> id = "c71d7d08-6350-4225-bcec-144f66d0487c"; :>> outcome = VerdictKind::proposed; :>> judgedAgainst = "957b2888"; :>> judgedAt = "2026-09-20"; :>> judgedBy = "claudeFable5"; }
    verification guardsCatalogueNamesTheFamilyImplementGate : Test { :>> id = "f6e980da-15ab-4fa3-9c7e-582eaf9873e0"; :>> title = "Sprint 756 implement gate"; :>> createdAt = "2026-09-20"; :>> createdBy = "claudeFable5"; :>> method = VerificationMethod::test; :>> procedureText = "members/keel-guards/src/enforcement.rs: doc_guard_count extends violations with family_cell_violations(rel, text); guard_family_claims reads the rows of a file carrying the | Guard | Family | header; family_of reads FAMILIES; family_cell_tests (three tests). members/keel-guards/src/lib.rs: every_catalogue_row_sits_inside_a_table beside every_guard_has_a_catalogue_row. .engine/docs/guards.md regenerated by a scratchpad script that read the FAMILY tables, added the column to both headers and all 77 rows, removed the blank line at 83 and moved the five rows at 102-106 below the Warning-only header; asserted 77 rows before and after, every row with a family, every enforced guard with a row, every row under a header; preamble paragraph and the doc-guard-count row describe the column and clause. cargo test -p keel-guards family_cell_tests catalogue_row every_catalogue_row_sits: 5 passed; cargo test -p keel-process a_bound_earlier_step: 1 passed; cargo clippy -p keel-guards -p keel-process --all-targets -D warnings clean; keel gate guard doc-guard-count . PASS 4 scanned 0 violations in 164 ms; doc-sync PASS; gate validate 873 clean. Records: task dcGuardTierHasOneHome (EngineBuild), issue667 resolver dcGuardsCatalogueNamesTheFamily, issue668 resolver dcGuardTierHasOneHome, D0539 proposed with the process-change marker, #CharteredBy from the item to d0539, DoD repointed at doc-guard-count."; }
    // RAN: validate=pass guard=pass clippy=pass probe=pass touched=pass
    part guardsCatalogueNamesTheFamilyImplementGateR1 : TestResult { :>> id = "f837e054-7f4b-403e-a913-234fc562b5a4"; :>> outcome = VerdictKind::pass; :>> judgedAgainst = "957b2888"; :>> judgedAt = "2026-09-20"; :>> judgedBy = "claudeFable5"; }
    verification guardsCatalogueNamesTheFamilyReviewGate : Test { :>> id = "bfbcab52-520e-4933-a027-5210224f7708"; :>> title = "Sprint 756 review gate — three passes per D0172"; :>> createdAt = "2026-09-20"; :>> createdBy = "claudeFable5"; :>> method = VerificationMethod::inspect; :>> procedureText = "Three passes per D0172. Code read back: guard_family_claims returns empty when no line starts with the header constant, so CLAUDE.md and the other .engine/docs/*.md files doc-guard-count scans contribute nothing; the row parser splits on the first backtick-pipe so a description cell containing pipes is never read as the family; family_cell_violations skips a name no family holds (a stale row for a retired guard is the catalogue-row test's direction, not this clause's); the two message shapes differ only in whether the cell names a family, so a typo names the row and the right family. Ceremony: D0539 is proposed with the process-change marker and held; a new violation clause on a hard guard is an enforcement change, so the Decision is co-committed under the CR prefix. FINDING for the retro: the census heuristic that classified a guard's tier from its function body was wrong in both directions for several guards (decision-requirement-link read as hard because its error arm returns violations: vec![...] while its normal arm returns violations: Vec::new(); sprint-coverage read as warning because it binds let violations = ... without mut or push), so only the four guards read by file:line are named in issue668 - the heuristic's other rows were not asserted."; }
    // RAN: validate=pass guard=pass clippy=pass probe=pass touched=pass
    part guardsCatalogueNamesTheFamilyReviewGateR1 : TestResult { :>> id = "5850065a-c8c9-40a1-82ed-a92c507805af"; :>> outcome = VerdictKind::proposed; :>> judgedAgainst = "957b2888"; :>> judgedAt = "2026-09-20"; :>> judgedBy = "claudeFable5"; }
    verification guardsCatalogueNamesTheFamilyCloseOutGate : Test { :>> id = "33582007-f71b-4275-9497-e67b3bbfd948"; :>> title = "Sprint 756 closeOut gate (autonomous, D0049)"; :>> createdAt = "2026-09-20"; :>> createdBy = "claudeFable5"; :>> method = VerificationMethod::inspect; :>> procedureText = "The task's DoD result and the six gate results are recorded from the verifier's rendered receipt, itself passed by check_receipt.py before the recorder was dispatched; issue584 and issue667 resolve when the DoD passes; issue668 stays open on dcGuardTierHasOneHome. Doc-sync rode the change. The touched test set is keel-guards and its dependents; the catalogue regeneration script stays in the scratchpad - the two tests are the control that keeps the column true, not the script."; }
    // RAN: validate=pass guard=pass clippy=pass probe=pass touched=pass
    part guardsCatalogueNamesTheFamilyCloseOutGateR1 : TestResult { :>> id = "1c94027a-d538-4834-93d6-e8eed41bedbd"; :>> outcome = VerdictKind::proposed; :>> judgedAgainst = "957b2888"; :>> judgedAt = "2026-09-20"; :>> judgedBy = "claudeFable5"; }
    verification guardsCatalogueNamesTheFamilyRetroGate : Test { :>> id = "b9c6da62-1ae3-4148-ab8b-ef85e49d1ace"; :>> title = "Sprint 756 retro gate (autonomous, D0049)"; :>> createdAt = "2026-09-20"; :>> createdBy = "claudeFable5"; :>> method = VerificationMethod::analyze; :>> procedureText = "Two findings, avoidable issues scanned (issue584, issue667, issue668). Finding one: the item's DoD named doc-sync as the guard to hold the family, and doc-sync cannot make a red gate; the DoD was written (2026-09-17) without reading doc_sync's report shape, and the mismatch surfaced only at design time. NOT A PROCESS CHANGE: the D0388 rule already asks for the positive and negative to be chosen before the tree is read; a DoD that names a guard should read that guard's tier the same way - the item was corrected by its owner, and issue668's resolver gives the tier one computable home so the next DoD can read it rather than infer it. Finding two: a one-line census heuristic over function bodies produced a tier table that was wrong for the three guards read back at the code (decision-requirement-link, verification-trace, sprint-coverage) and unverified for the rest, and only the D0151 rule - name the check before the claim - kept it out of the record; the Issue names four guards read at file:line and no more. NOT A PROCESS CHANGE: dcGuardTierHasOneHome makes the tier an arm-level fact, after which no heuristic is needed."; }
    // RAN: validate=pass guard=pass clippy=pass probe=pass touched=pass
    part guardsCatalogueNamesTheFamilyRetroGateR1 : TestResult { :>> id = "e334b0ae-2c14-4323-aa06-a78cf1f505e3"; :>> outcome = VerdictKind::proposed; :>> judgedAgainst = "957b2888"; :>> judgedAt = "2026-09-20"; :>> judgedBy = "claudeFable5"; }
}
