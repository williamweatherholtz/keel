// ProjectDeliveryS704 — Sprint 704: Resolve issue532 (High) through dcRecorderReportRefusesNonRecordWrites: check_report.py refuses a recorder report whose WROTE: line names a command that is not keel record with a sub-verb, and a report that writes one gate or task twice; the recorder brief states both rules in its own words. CHANGE (CR): the checker is an enforcement surface, so the change rides a co-committed process-change Decision (D0209 cl.2), held proposed for the human. 2 pts.. EXECUTE. 2 pts.
package ProjectDeliveryS704 {
    private import EngineElement::*;
    private import EngineWork::*;
    private import EngineVerification::*;
    private import EngineRelationships::*;

    #CharteredBy dependency from recorderReportRefusesNonRecordWritesStory to d0473;

    part recorderReportRefusesNonRecordWritesStory : Story {
        :>> id = "195587d5-f8e8-4cc7-8150-cbe192917283";
        :>> title = "Sprint 704: Resolve issue532 (High) through dcRecorderReportRefusesNonRecordWrites: check_report.py refuses a recorder report whose WROTE: line names a command that is not keel record with a sub-verb, and a report that writes one gate or task twice; the recorder brief states both rules in its own words. CHANGE (CR): the checker is an enforcement surface, so the change rides a co-committed process-change Decision (D0209 cl.2), held proposed for the human. 2 pts. (2 pts)";
        :>> createdAt = "2026-09-14"; :>> createdBy = "claudeFable5"; :>> kind = WorkKind::code; :>> priority = WorkPriority::p0; :>> owner = "claudeFable5"; :>> estimatedPoints = 2;
    }

    action def DeliveryRunS704 {
        action storyRecorderReportRefusesNonRecordWrites;
        verification storyRecorderReportRefusesNonRecordWritesDoD : Test { :>> id = "388c3629-2619-423d-a593-8f297deb21c4"; :>> method = VerificationMethod::test; :>> procedureText = "DELIVERED: (a) .engine/skills/delegated-ceremony/references/check_report.py: refusal 4, a WROTE: line whose command is not [keel] record <sub-verb> (the binary may be named as keel, KEEL, <KEEL>, $KEEL or a path ending in keel[-suffix][.exe], or omitted), naming the line and the command; refusal 5, a second WROTE: line naming a --gate or --task already written, naming both lines; probe() runs five fixtures as stated pairs and prints each. (b) fixtures: positive-sprint703-textpatch-write.txt (sprint 703's report verbatim), positive-sprint703-retro-recorded-twice.txt (the retro gate written a second time with reworded evidence), negative-sprint703-record-only.txt (the report with the textpatch line removed); the 647 pair unchanged. (c) SKILL.md recorder brief rule 5 (one write per owed record; a red gate --fast after a write is a DISCREPANCIES line, never a second record and never a tool run against the file) and refusals 4-5 in the list the primary reads; .claude regenerated by sync-claude. VERIFY (probe pair, D0388, chosen before the tree was read): known positive - sprint 703's report as returned is REFUSED naming line 9 python scripts/textpatch.py, and the retro-twice cut is REFUSED naming --gate livingDocsNameOnlyDeclaredCliVerbsRetroGate written again (first at line 7); known negative - the record-only cut and the 647 receipt-driven report PASS with 0 refusals; the checker before the change passed sprint 703's report (exit 0), after it refuses (exit 1); gate validate, check-engine, guard --no-receipt green; sync-claude --check clean."; }
        // RAN: PROBE PAIR: python .engine/skills/delegated-ceremony/references/check_report.py --probe --root . -> probe pair validation passed (every pair holds); exit=0 RECORDER-REPORT CHECK: python .engine/skills/delegated-ceremony/references/check_report.py s703/recorder-report.txt -> REFUSED: write outside the record API `python scripts/textpatch.py`; exit=1
        part storyRecorderReportRefusesNonRecordWritesDoDR1 : TestResult { :>> id = "5c322e9d-313f-423c-89b9-8a33396ad85b"; :>> outcome = VerdictKind::pass; :>> judgedAgainst = "8cb5b2d"; :>> judgedAt = "2026-09-13"; :>> judgedBy = "claudeFable5"; }
    }

    verification recorderReportRefusesNonRecordWritesRefineGate : Test { :>> id = "8af2d52b-0940-4906-97e4-5a1256446a5e"; :>> title = "Sprint 704 refine gate (DoR)"; :>> createdAt = "2026-09-14"; :>> createdBy = "claudeFable5"; :>> method = VerificationMethod::inspect; :>> procedureText = "Chartered by issue532's governing Decision (this sprint's co-committed process-change, proposed): the recorder's report is the one surface a control reads after its writes, and two of the brief's rules were text it did not read. Two points: two refusals in a pure function, three fixtures cut from a real report, a probe table, two doc passages. DoR: dcRecorderReportRefusesNonRecordWrites ranks third on keel show whats-next at 8cb5b2d (the two above it are sprint 703's landed item and a lens item not yet chartered); the pair is the DoD's own; no cargo build, so issue477 binds only the wait for the previous land to exit."; }
    // RAN: KEEL gate validate . -> 807 tracking file(s) validated clean.; exit=0
    part recorderReportRefusesNonRecordWritesRefineGateR1 : TestResult { :>> id = "aee7c114-d85e-4250-a8b7-821d34e3044c"; :>> outcome = VerdictKind::proposed; :>> judgedAgainst = "8cb5b2d"; :>> judgedAt = "2026-09-13"; :>> judgedBy = "claudeFable5"; }
    verification recorderReportRefusesNonRecordWritesStandupGate : Test { :>> id = "153a0a1c-f4fc-4e38-901e-80c7ed5652f4"; :>> title = "Sprint 704 standup gate"; :>> createdAt = "2026-09-14"; :>> createdBy = "claudeFable5"; :>> method = VerificationMethod::inspect; :>> procedureText = "Order: wait for the previous keel-land to exit (no .engine edit while cargo runs, issue477); record the Decision from its draft (marker process-change -> HELD proposed, D0337); copy the checker and fixtures from the scratchpad where they were built and probed by path; run patch_skill.py by path; probe with --root .; run the checker over sprint 703's report; sync-claude; gate validate, check-engine, guard --no-receipt; sprint record chartered by the Decision; verifier and recorder by agent type - the recorder's report is checked by the new checker itself; commit CR: detached; read the CI conclusion back."; }
    // RAN: KEEL gate check-engine . -> .engine instance files validated clean (kernel-free; D0112 phase 2).; exit=0
    part recorderReportRefusesNonRecordWritesStandupGateR1 : TestResult { :>> id = "61510933-3d8e-4e15-a33e-5521b0582142"; :>> outcome = VerdictKind::proposed; :>> judgedAgainst = "8cb5b2d"; :>> judgedAt = "2026-09-13"; :>> judgedBy = "claudeFable5"; }
    verification recorderReportRefusesNonRecordWritesImplementGate : Test { :>> id = "09399ab4-e6e1-4b19-8250-3d6dc1bc096f"; :>> title = "Sprint 704 implement gate"; :>> createdAt = "2026-09-14"; :>> createdBy = "claudeFable5"; :>> method = VerificationMethod::test; :>> procedureText = "RAN: python .engine/skills/delegated-ceremony/references/check_report.py --probe --root . -> every pair holds (five lines, exit 0); the same checker over sprint 703's recorder-report.txt -> REFUSED (1) line 9, exit 1; the checker at 8cb5b2d over the same file -> pass, exit 0. See the verifier's receipt for the gate set and sync-claude --check."; }
    // RAN: PROBE PAIR: python .engine/skills/delegated-ceremony/references/check_report.py --probe --root . -> probe pair validation passed (every pair holds); exit=0 RECORDER-REPORT CHECK: python .engine/skills/delegated-ceremony/references/check_report.py s703/recorder-report.txt -> REFUSED: write outside the record API `python scripts/textpatch.py`; exit=1
    part recorderReportRefusesNonRecordWritesImplementGateR1 : TestResult { :>> id = "c6158845-ada6-4bcf-8bcd-db77f2bc4fb8"; :>> outcome = VerdictKind::pass; :>> judgedAgainst = "8cb5b2d"; :>> judgedAt = "2026-09-13"; :>> judgedBy = "claudeFable5"; }
    verification recorderReportRefusesNonRecordWritesReviewGate : Test { :>> id = "9f3785a9-e993-43ee-952a-efaada6c712d"; :>> title = "Sprint 704 review gate — three passes per D0172"; :>> createdAt = "2026-09-14"; :>> createdBy = "claudeFable5"; :>> method = VerificationMethod::inspect; :>> procedureText = "Three passes (D0172). Correctness: is_record_write strips at most one leading binary token and then requires record followed by a lower-case sub-verb, so keel record gate-result, record result and <KEEL> record sprint pass while python, sed, textpatch and an editor fail on their first token; the duplicate check keys on (--gate|--task, value) across WROTE: lines only, so a DISCREPANCIES line quoting a gate name is not a write. Honesty: the checker refuses, it does not repair - a recorder that hits refusal 5 has already written twice, and the report tells the primary which lines; the tree-side duplicate is the primary's triage, as it was in sprint 703. Scope: the checker still reads the report only; a recorder that writes outside the API and does not report it is out of this control's reach and stays the D0425 no-Write-tool arm's."; }
    // RAN: KEEL gate guard --no-receipt . -> PASS 39; exit=0
    part recorderReportRefusesNonRecordWritesReviewGateR1 : TestResult { :>> id = "b1d7c103-c2ce-4796-a0e7-5c7108cfde37"; :>> outcome = VerdictKind::proposed; :>> judgedAgainst = "8cb5b2d"; :>> judgedAt = "2026-09-13"; :>> judgedBy = "claudeFable5"; }
    verification recorderReportRefusesNonRecordWritesCloseOutGate : Test { :>> id = "8cfd3ed3-673b-4dbd-a2c9-b35ae13566c9"; :>> title = "Sprint 704 closeOut gate (autonomous, D0049)"; :>> createdAt = "2026-09-14"; :>> createdBy = "claudeFable5"; :>> method = VerificationMethod::inspect; :>> procedureText = "Closes at the CR: commit that lands check_report.py, the three fixtures, SKILL.md, the regenerated .claude copy and the marker Decision together: gate validate / check-engine / guard --no-receipt green over that tree; dcRecorderReportRefusesNonRecordWritesDoD carries a pass with the RAN receipt; issue532 is resolved by that pass; the Decision stays proposed until the human's word; the CI conclusion for the landing commit is read back as success."; }
    // RAN: KEEL sync-claude --check . -> claude-surface: keel-owned subset matches this binary's generator (47 registry skill(s)); exit=0
    part recorderReportRefusesNonRecordWritesCloseOutGateR1 : TestResult { :>> id = "c74c6a73-754a-4711-a5e8-d22c1d119bbc"; :>> outcome = VerdictKind::proposed; :>> judgedAgainst = "8cb5b2d"; :>> judgedAt = "2026-09-13"; :>> judgedBy = "claudeFable5"; }
    verification recorderReportRefusesNonRecordWritesRetroGate : Test { :>> id = "0e8fdfe7-06ee-4a54-b897-02afc40ff6f5"; :>> title = "Sprint 704 retro gate (autonomous, D0049)"; :>> createdAt = "2026-09-14"; :>> createdBy = "claudeFable5"; :>> method = VerificationMethod::analyze; :>> procedureText = "Avoidable issues scanned: findings become Issues, not prose. Finding: the recorder's report is checked, but the receipt the recorder reads from is not - issue533 (a DELIVERED claim passed unread) already tracks the verifier side with resolver dcDeliveredClaimsAreReadBackFromSource, so no new item. Finding: the recorder's DISCREPANCIES line in sprint 703 named a dispatch task that did not exist (the primary named the DoD, not the task); the brief's owed-records line should name the task the record API takes, and the checker cannot know it - one-off, the primary's dispatch text, no item. Closed in-sprint: the checker's pass line now names all five things it checked, so a reader of a report knows what passing meant."; }
    // RAN: Avoidable issues scanned: KEEL gate validate . -> 807 tracking file(s) validated clean.; exit=0 KEEL gate check-engine . -> .engine instance files validated clean (kernel-free; D0112 phase 2).; exit=0 KEEL gate guard --no-receipt . -> PASS 39; exit=0 KEEL sync-claude --check . -> claude-surface: keel-owned subset matches this binary's generator (47 registry skill(s)); exit=0
    part recorderReportRefusesNonRecordWritesRetroGateR1 : TestResult { :>> id = "0ad44262-200c-426d-9065-a2d25e730fa1"; :>> outcome = VerdictKind::proposed; :>> judgedAgainst = "8cb5b2d"; :>> judgedAt = "2026-09-13"; :>> judgedBy = "claudeFable5"; }
}
