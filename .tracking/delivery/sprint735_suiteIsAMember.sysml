// ProjectDeliveryS735 — Sprint 735: the build-and-test tooling is a member - dcSuiteIsAMember, the fifth D0479 extraction. suite.rs, touched.rs, verify.rs and hook_binary.rs leave keel-cli/src for members/keel-suite/src, contentkey.rs joins them from the guard member (the touched set's D0474 key is the tooling's, not a guard's), and the --no-receipt predicate descends to keel_fs::fsx::no_receipt_forced so keel-suite depends on keel-fs, keel-git, keel-actor, keel-model and keel-perf only (cargo tree -p keel-suite --depth 1): no view, no guard, no keel-write. Every old path resolves through keel-cli's lib.rs re-exports; keel_guards::receipt::forced re-exports the descended predicate. D0506 (held proposed) is the marked record the members/keel-guards/src/ lock asks for.. EXECUTE. 5 pts.
package ProjectDeliveryS735 {
    private import EngineElement::*;
    private import EngineWork::*;
    private import EngineVerification::*;
    private import EngineRelationships::*;

    #CharteredBy dependency from suiteIsAMemberStory to d0479;

    part suiteIsAMemberStory : Story {
        :>> id = "cb30f3b4-4362-47db-9925-6392c441dd4f";
        :>> title = "Sprint 735: the build-and-test tooling is a member - dcSuiteIsAMember, the fifth D0479 extraction. suite.rs, touched.rs, verify.rs and hook_binary.rs leave keel-cli/src for members/keel-suite/src, contentkey.rs joins them from the guard member (the touched set's D0474 key is the tooling's, not a guard's), and the --no-receipt predicate descends to keel_fs::fsx::no_receipt_forced so keel-suite depends on keel-fs, keel-git, keel-actor, keel-model and keel-perf only (cargo tree -p keel-suite --depth 1): no view, no guard, no keel-write. Every old path resolves through keel-cli's lib.rs re-exports; keel_guards::receipt::forced re-exports the descended predicate. D0506 (held proposed) is the marked record the members/keel-guards/src/ lock asks for. (5 pts)";
        :>> createdAt = "2026-09-17"; :>> createdBy = "claudeFable5"; :>> kind = WorkKind::code; :>> priority = WorkPriority::p0; :>> owner = "claudeFable5"; :>> estimatedPoints = 5;
    }

    action def DeliveryRunS735 {
        action storySuiteIsAMember;
        verification storySuiteIsAMemberDoD : Test { :>> id = "e306ab66-1304-4e46-988f-6682bcc50428"; :>> method = VerificationMethod::test; :>> procedureText = "DELIVERED BACKLOG ITEMS: dcSuiteIsAMember. DONE MEANS: members/keel-suite holds suite, touched, verify, hook_binary and contentkey with the member lint preamble; keel-cli/src holds none of the five and its lib.rs re-exports each (pub use keel_suite::suite; touched; verify; hook_binary; contentkey); keel-guards' lib.rs no longer declares contentkey and receipt.rs's forced is pub use keel_fs::fsx::no_receipt_forced as forced; the root manifest lists members/keel-suite before keel-cli and keel-cli's manifest depends on it; scripts/extract_suite.py is the idempotent transform (dry-run default, 56 crate:: references rewritten across five files with a length-delta reconciliation, re-run says already applied); cargo clippy --release --workspace --all-targets -D warnings clean; keel --help byte-identical to the pre-move render (cmp help-pre.txt help-post.txt) and keel version's guard line unchanged (75: 66 hard-blocking, 9 warning-only); python scripts/modgraph.py --check and python scripts/module_home.py --probe hold. Known-positive, chosen before the tree is read: touching members/keel-view/src/view/mod.rs leaves keel-suite Fresh under cargo build --release --verbose while keel-view, keel-guards and keel-cli recompile, and the member's receipt tests pass (pos735.py). Known-negative: a fourth receipt writer with an outcome and no running form planted under members/keel-fs/src makes the census every_receipt_writer_with_an_outcome_renders_a_running_form red naming the plant, removed on every path (neg735.py). The DoD's dependency prose (keel-write and keel-guards' receipt module) and its Fresh probe cannot both hold because keel-guards depends on keel-view; the probe is the contract, and D0506 records the two descents that make it hold."; }
        // RAN: LADDER: keel-serve.exe verify . --probe-from pair735.txt -> outcome=pass stopped_at=none seconds=1145
        part storySuiteIsAMemberDoDR1 : TestResult { :>> id = "4752e700-a706-4999-8281-bc7abe934896"; :>> outcome = VerdictKind::pass; :>> judgedAgainst = "7394a28"; :>> judgedAt = "2026-09-17"; :>> judgedBy = "claudeFable5"; }
    }

    verification suiteIsAMemberRefineGate : Test { :>> id = "3bb9fa2c-f2d8-40cd-9c7a-22cc79f1f6f1"; :>> title = "Sprint 735 refine gate (DoR)"; :>> createdAt = "2026-09-17"; :>> createdBy = "claudeFable5"; :>> method = VerificationMethod::inspect; :>> procedureText = "DoR: dcSuiteIsAMember is the first line of keel show whats-next at 7394a28 (brief 41 landed, CI conclusion success). Chartered by D0479 (accepted) through its #CharteredBy edge; #DependsOn dcModelAndWriteAreMembers, done; dcOneRepoRootHelper (sprint 734) landed first so no cwd-relative anchor rides into the member. Sized 5 - five files moved with a codemod, one new member manifest, two descents (contentkey into the member, forced into keel-fs) under the guard lock with their marked Decision, four test repoints, one census widened to the workspace, doc-sync in facts.py, collapse_repo_root.py, fsx.rs and the test-verify skill, and the D0388 pair as two scripts. Blocking dependencies: none."; }
    // RAN: LADDER: keel-serve.exe verify . --probe-from pair735.txt -> outcome=pass stopped_at=none seconds=1145
    part suiteIsAMemberRefineGateR1 : TestResult { :>> id = "7bc8d0a5-61aa-4038-a208-e0a6f2bf3d32"; :>> outcome = VerdictKind::proposed; :>> judgedAgainst = "7394a28"; :>> judgedAt = "2026-09-17"; :>> judgedBy = "claudeFable5"; }
    verification suiteIsAMemberStandupGate : Test { :>> id = "023a1d1f-52d5-4084-8d43-5baf2ce40a0e"; :>> title = "Sprint 735 standup gate"; :>> createdAt = "2026-09-17"; :>> createdBy = "claudeFable5"; :>> method = VerificationMethod::inspect; :>> procedureText = "Owner claudeFable5. Blocker: none - brief 41 landed in 7394a28, no ladder or land is running. Order: (1) scripts/extract_suite.py: git mv the five files, rewrite crate:: paths through MODULE_MAP, write the member's Cargo.toml and lib.rs, edit the root and keel-cli manifests and keel-cli's lib.rs re-exports, drop contentkey from keel-guards, descend forced to keel_fs::fsx::no_receipt_forced; dry-run reconciled, then --apply. (2) hand repoints in the moved tests: the custom-harness census and the scratch census read keel_fs::test_support::repo_root(); the anchor scan asserts keel-cli/src/main.rs and keel-suite/src/touched.rs are both in its population; the receipt-writer census walks keel-cli/src and every members/*/src. (3) cargo build --release, clippy --workspace --all-targets, keel --help against help-pre.txt, keel version, cargo test on keel-suite, keel-fs, keel-guards. (4) pos735/neg735; pair735.txt; modgraph --check; module_home --probe. (5) doc-sync, sync-claude. (6) D0506 with the process-change marker, issue588 with resolver dcSuiteMeasuresTheWorkspace (new backlog item after dcTouchedSetDescendsTheWorkspace), the sprint with the retro filled; verifier with the pair file; recorder --owed 7; land; CI conclusion."; }
    // RAN: LADDER: keel-serve.exe verify . --probe-from pair735.txt -> outcome=pass stopped_at=none seconds=1145
    part suiteIsAMemberStandupGateR1 : TestResult { :>> id = "75f49113-f91c-475e-9cd2-467769cae424"; :>> outcome = VerdictKind::proposed; :>> judgedAgainst = "7394a28"; :>> judgedAt = "2026-09-17"; :>> judgedBy = "claudeFable5"; }
    verification suiteIsAMemberImplementGate : Test { :>> id = "049a92bc-0046-4e22-b94f-85fb4e1c4ae9"; :>> title = "Sprint 735 implement gate"; :>> createdAt = "2026-09-17"; :>> createdBy = "claudeFable5"; :>> method = VerificationMethod::test; :>> procedureText = "The implement gate is the DoD's own probes plus the ladder: cargo build --release clean; cargo clippy --release --workspace --all-targets -- -D warnings Finished clean; cmp help-pre.txt help-post.txt byte-identical (15089 bytes); keel version guards line 75 (66 hard-blocking, 9 warning-only); cargo test --release -p keel-suite --lib 50 passed, -p keel-fs --lib 3 passed, -p keel-guards --lib 137 passed; python pos735.py exit 0 (Fresh keel-suite, keel-view recompiled, receipt tests pass); python neg735.py exit 0 (census rc 101 naming planted_fourth_receipt.rs, plant removed); python scripts/modgraph.py --check exit 0 (73 modules, 100 edges); python scripts/module_home.py --probe 0 failures; keel verify . --probe-from pair735.txt (validate, guard, clippy, the pair, suite --touched) green."; }
    // RAN: LADDER: keel-serve.exe verify . --probe-from pair735.txt -> outcome=pass stopped_at=none seconds=1145
    part suiteIsAMemberImplementGateR1 : TestResult { :>> id = "ed927bae-8b2f-41ef-8a15-ae95d22919d6"; :>> outcome = VerdictKind::pass; :>> judgedAgainst = "7394a28"; :>> judgedAt = "2026-09-17"; :>> judgedBy = "claudeFable5"; }
    verification suiteIsAMemberReviewGate : Test { :>> id = "d04cec99-ef90-489b-b5b5-08d02844ab45"; :>> title = "Sprint 735 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every moved test passes in its new crate (50 in keel-suite), every caller of the five modules and of forced resolves through a re-export, and the binary's help and guard count are byte-for-byte the pre-move ones. Honesty: the receipt-writer census's population is asserted over 40 files across every crate's src and the negative plants in a MEMBER, the tree the old census never read; the anchor scan asserts both keel-cli/src and the member's own src are in its population. Scope: under members/keel-guards/src the diff is one removed module line and one re-export; no guard predicate, family table, severity or gate set changes, and D0506 says so in its decision text."; }
    // RAN: LADDER: keel-serve.exe verify . --probe-from pair735.txt -> outcome=pass stopped_at=none seconds=1145
    part suiteIsAMemberReviewGateR1 : TestResult { :>> id = "3788a082-1e78-41ca-89ee-4e2890458c2a"; :>> outcome = VerdictKind::proposed; :>> judgedAgainst = "7394a28"; :>> judgedAt = "2026-09-17"; :>> judgedBy = "claudeFable5"; }
    verification suiteIsAMemberCloseOutGate : Test { :>> id = "644d48cf-0d33-4da1-afda-4b0b629d7514"; :>> title = "Sprint 735 closeOut gate (autonomous, D0049)"; :>> createdAt = "2026-09-17"; :>> createdBy = "claudeFable5"; :>> method = VerificationMethod::inspect; :>> procedureText = "Landed when the verifier's receipt reads DISCREPANCIES: NONE and its probe rung row names pair735.txt, the recorder's report passes check_report.py --owed 7, git status -sb is clean after keel land and gh run list names the landing commit with conclusion success. The DoD result is recorded against dcSuiteIsAMemberDoD at that sha; D0506 waits in the authority queue (brief 42 republishes the page, decision-surfacing); issue588's resolution is computed from its #Resolves edge to dcSuiteMeasuresTheWorkspace."; }
    // RAN: LADDER: keel-serve.exe verify . --probe-from pair735.txt -> outcome=pass stopped_at=none seconds=1145
    part suiteIsAMemberCloseOutGateR1 : TestResult { :>> id = "b7f90827-7834-401d-965e-f59337f0ff27"; :>> outcome = VerdictKind::proposed; :>> judgedAgainst = "7394a28"; :>> judgedAt = "2026-09-17"; :>> judgedBy = "claudeFable5"; }
    verification suiteIsAMemberRetroGate : Test { :>> id = "ebd70817-9bfc-4a25-8148-bff807195e14"; :>> title = "Sprint 735 retro gate (autonomous, D0049)"; :>> createdAt = "2026-09-17"; :>> createdBy = "claudeFable5"; :>> method = VerificationMethod::analyze; :>> procedureText = "Written at close-out, before the verifier is dispatched; avoidable issues scanned (issue011), each finding a tracked item or the reason it is not. (1) The full suite measures keel-cli alone: suite.rs DELIVERABLE_PATHS omits members/ and keel-parser/ so a member edit leaves the receipt's fingerprint equal and the staleness message never fires, and the run is cargo test --manifest-path keel-cli/Cargo.toml, so every member's lib tests are outside the full run while the touched set includes them; found reading the file it moved, predating the move -> issue588, new item dcSuiteMeasuresTheWorkspace declared after dcTouchedSetDescendsTheWorkspace (D0052: declaration order is priority), its DoD reads the population from the root manifest so the next member joins it without an edit. (2) The DoD's dependency prose (keel-write and keel-guards' receipt module) contradicted its own Fresh probe because keel-guards depends on keel-view; the probe won and two facts descended (contentkey to the member, forced to keel-fs). Not tracked: D0506 is the record and its rationale is the rule (the probe is the contract, as sprint 734's retro read for counts); write_atomic was never keel-write's fact, only its re-export. (3) The lock fired for the second sprint running on an edit that changes no guard logic (D0505: a test line; D0506: a module removal and a re-export), and each cost a held Decision and a brief. Not tracked as a new item: D0505's consequences already name the fork (exempt cfg(test) lines, or narrow the lock to guard predicates) as a separate process-change Decision; a third firing is the trigger, and the control-census removalCandidates view is where its friction count shows. (4) The codemod's content check first reversed MODULE_MAP over the whole file and flagged contentkey.rs, which already named keel_git::gitx legitimately; replaced by a length-delta conservation check. Not tracked: a one-shot script, its own dry-run caught it before --apply (migration skill gate 2 working). (5) pos735.py's first run read keel-suite Dirty because the preceding cargo test -p keel-suite had unified features differently; the probe now settles the workspace build before touching. Not tracked: a scratchpad probe, and the D0388 discipline caught the probe rather than the tree, as in sprint 734 (4). (6) The test-verify skill's stems row still described the keel-cli-only key from before sprint 714 (members were added to the key then); synced here to touched.rs's rule. Not tracked: the doc-sync guard does not read skill prose against code, and no third site names the key's population (git grep keel-cli/src/<stem>); one line, fixed in this commit. (7) clippy items_after_test_module and too_long_first_doc_paragraph each fired once on the descended predicate (keel-fs's preamble denies nursery); both fixed in the codemod's FORCED_DOC so a re-run lands the linted shape. Non-finding: the control exists and fired under --all-targets, as sprint 733 (7) recorded."; }
    // RAN: LADDER: keel-serve.exe verify . --probe-from pair735.txt -> outcome=pass stopped_at=none seconds=1145
    part suiteIsAMemberRetroGateR1 : TestResult { :>> id = "96aec1cb-353c-4cea-9528-b76c147971b4"; :>> outcome = VerdictKind::proposed; :>> judgedAgainst = "7394a28"; :>> judgedAt = "2026-09-17"; :>> judgedBy = "claudeFable5"; }
}
