// ProjectDeliveryS711 — Sprint 711: Resolve issue543 through dcEvidenceGoesThroughAFile: record result and record gate-result read --evidence straight from the shell argument (main.rs cmd_append_result, cmd_append_gate_result) and have no file form, while decision (--from), issue (--description-from) and task (--dod-from) do. D0224's fifth occurrence, 2026-09-14: two backtick spans in sprint 708's implement-gate evidence were taken as command substitution and both quotes landed empty. The pain: the two verbs that carry the most quoted command lines of any record are the two the D0224 control never reached, and the control was applied verb by verb, each after its own occurrence - fixing three of five call sites is what let it recur (the same sentence main.rs already says about the fourth). The fix is the class: one prose_flag reader for every --X / --X-from pair, used by all five, refusing both at once by name. Chartered by D0224 (prose goes through a file). 2 pts.. EXECUTE. 2 pts.
package ProjectDeliveryS711 {
    private import EngineElement::*;
    private import EngineWork::*;
    private import EngineVerification::*;
    private import EngineRelationships::*;

    #CharteredBy dependency from evidenceGoesThroughAFileStory to d0224;

    part evidenceGoesThroughAFileStory : Story {
        :>> id = "9fdb65c3-3ad8-4c7b-af3e-47b568875346";
        :>> title = "Sprint 711: Resolve issue543 through dcEvidenceGoesThroughAFile: record result and record gate-result read --evidence straight from the shell argument (main.rs cmd_append_result, cmd_append_gate_result) and have no file form, while decision (--from), issue (--description-from) and task (--dod-from) do. D0224's fifth occurrence, 2026-09-14: two backtick spans in sprint 708's implement-gate evidence were taken as command substitution and both quotes landed empty. The pain: the two verbs that carry the most quoted command lines of any record are the two the D0224 control never reached, and the control was applied verb by verb, each after its own occurrence - fixing three of five call sites is what let it recur (the same sentence main.rs already says about the fourth). The fix is the class: one prose_flag reader for every --X / --X-from pair, used by all five, refusing both at once by name. Chartered by D0224 (prose goes through a file). 2 pts. (2 pts)";
        :>> createdAt = "2026-09-14"; :>> createdBy = "claudeFable5"; :>> kind = WorkKind::code; :>> priority = WorkPriority::p0; :>> owner = "claudeFable5"; :>> estimatedPoints = 2;
    }

    action def DeliveryRunS711 {
        action storyEvidenceGoesThroughAFile;
        verification storyEvidenceGoesThroughAFileDoD : Test { :>> id = "61e1b940-0717-4640-8882-2c9c3c5b8081"; :>> method = VerificationMethod::test; :>> procedureText = "Resolves issue543 (D0224, fifth occurrence): record result and record gate-result accept --evidence-from FILE (and --notes-from FILE for gate-result), read verbatim, with --evidence still accepted for one-line receipts; passing both is refused naming the two flags. The usage line, CLI_FACTS invocation, commands.sysml and the CLAUDE.md sect.4 writes line name the file form and say PREFER THIS for anything quoting a command. Known-positive: a file whose text carries a backtick span and a parenthesised refusal round-trips into the RAN line byte for byte (unit test), where the same text as a double-quoted shell argument would have been substituted; known-negative: the existing one-line --evidence path is unchanged and every result recorded before this change parses as before (cargo test on the write module; gate validate over the tree)."; }
        // RAN: cargo test --release -p keel-cli --test evidence_goes_through_a_file -> 3 passed 0 failed: known-positive a_receipt_read_from_a_file_lands_verbatim_backticks_included (a file whose text carries two backtick spans and a parenthesised refusal lands in // RAN: byte for byte); known-negative the_one_line_shell_form_still_lands (--evidence TEXT unchanged) and both_flags_at_once_are_refused_by_name_and_nothing_is_written (refusal names --evidence-from and --evidence; file untouched; unreadable file refused with cannot read). cargo test --release -p keel-cli --lib -- write:: -> 36 passed unchanged; keel gate validate . -> 815 clean over every result recorded before this change; cargo clippy --release --all-targets -- -D warnings exit 0; cli-surface-declared PASS 86, cli-reference PASS 441.
        part storyEvidenceGoesThroughAFileDoDR1 : TestResult { :>> id = "39e09f3d-7741-41e9-978f-adbc25d2e699"; :>> outcome = VerdictKind::pass; :>> judgedAgainst = "838f75f"; :>> judgedAt = "2026-09-14"; :>> judgedBy = "claudeFable5"; }
    }

    verification evidenceGoesThroughAFileRefineGate : Test { :>> id = "32525c57-6f3a-439b-aa6c-0f5f23bf0993"; :>> title = "Sprint 711 refine gate (DoR)"; :>> createdAt = "2026-09-14"; :>> createdBy = "claudeFable5"; :>> method = VerificationMethod::inspect; :>> procedureText = "Chartered by D0224 (prose goes through a file, accepted); the CLI surface is an authored fact (D0271) so commands.sysml and cli_facts.rs change with the usage line and guard cli-surface-declared holds them equal; no enforcement surface changes, so no marker is needed - NOT A PROCESS CHANGE: a new flag on two record sub-verbs, the write path unchanged. Two points: one reader, five call sites, one integration test on the binary, four doc homes. DoR: dcEvidenceGoesThroughAFile ranks first on keel show whats-next once sprints 709 and 710 are stamped; the pair is the DoD's own."; }
    // RAN: DoR held before the first edit: estimatedPoints 2 on the Story; #CharteredBy to d0224 (accepted; prose goes through a file); scope is one reader and five call sites with one integration test and four doc homes; the DoD dcEvidenceGoesThroughAFileDoD (67074b85) names the known-positive and known-negative before the tree was read (D0388); no blocking dependency - the write path (write.rs append_result / append_gate_result) is untouched. NOT A PROCESS CHANGE: two record sub-verbs gain a flag; no guard, hook or workflow changes.
    part evidenceGoesThroughAFileRefineGateR1 : TestResult { :>> id = "44235569-c237-4f80-bb65-3f07a8b31fea"; :>> outcome = VerdictKind::proposed; :>> judgedAgainst = "838f75f"; :>> judgedAt = "2026-09-14"; :>> judgedBy = "claudeFable5"; }
    verification evidenceGoesThroughAFileStandupGate : Test { :>> id = "a18e8d9e-582b-4beb-8815-1c0b28cc708f"; :>> title = "Sprint 711 standup gate"; :>> createdAt = "2026-09-14"; :>> createdBy = "claudeFable5"; :>> method = VerificationMethod::inspect; :>> procedureText = "Order: this record first; prose_flag(args, name, verb) in main.rs reading --NAME-from FILE else --NAME, refusing both by name and a file it cannot read; cmd_append_result and cmd_append_gate_result (evidence, notes) plus record task (dod), record issue (description) read it; usage lines and the record error texts say PREFER --evidence-from; cli_facts.rs record invocation, .engine/cli/commands.sysml, CLAUDE.md sect.4 writes line; integration test evidence_goes_through_a_file.rs on the binary against a minimal backlog fixture: a file carrying a backtick span and a parenthesised refusal lands in the RAN line byte for byte, --evidence alone still lands, both together refuse and write nothing; cargo build --release, copy, cargo test --release --test evidence_goes_through_a_file, clippy -D warnings, gate guard --no-receipt with cli-surface-declared and cli-reference PASS."; }
    // RAN: Order followed as the clause set it: this record first (keel record sprint 711 evidenceGoesThroughAFile --charter d0224 --points 2 --fill), then prose_flag in main.rs after flag(), then the five call sites (result evidence; gate-result notes and evidence; task dod; issue description), usage lines, cli_facts.rs and commands.sysml invocation, CLAUDE.md sect.4, the integration test, build. One deviation surfaced by the gate set and tracked rather than absorbed: the commands.sysml edit hit guard ownership (cliRecord owned by claudeOpus5) - re-authored as cliRecordVerbs per 74c1923, issue547 recorded with resolver dcCliFactSupersessionIsHonoured.
    part evidenceGoesThroughAFileStandupGateR1 : TestResult { :>> id = "e4ea6e38-130b-42ca-be86-9963fae5d243"; :>> outcome = VerdictKind::proposed; :>> judgedAgainst = "838f75f"; :>> judgedAt = "2026-09-14"; :>> judgedBy = "claudeFable5"; }
    verification evidenceGoesThroughAFileImplementGate : Test { :>> id = "10c13e37-73df-4f4f-a10f-e1f87c2d5caa"; :>> title = "Sprint 711 implement gate"; :>> createdAt = "2026-09-14"; :>> createdBy = "claudeFable5"; :>> method = VerificationMethod::test; :>> procedureText = "The implement gate holds when: cargo test --release --test evidence_goes_through_a_file passes its three tests; cargo test --release --lib -- write:: passes unchanged; cargo clippy --release --all-targets -- -D warnings exits 0; keel record result --help names --evidence-from; keel gate guard --no-receipt . reports cli-surface-declared PASS and cli-reference PASS; sync-claude --check clean. Its evidence quotes those commands' own lines - through --evidence-from, the first record to use it."; }
    // RAN: cargo test --release -p keel-cli --test evidence_goes_through_a_file -> 3 passed 0 failed (a_receipt_read_from_a_file_lands_verbatim_backticks_included; the_one_line_shell_form_still_lands; both_flags_at_once_are_refused_by_name_and_nothing_is_written). cargo test --release -p keel-cli --lib -- write:: -> 36 passed 0 failed, unchanged. cargo clippy --release --all-targets -- -D warnings -> exit 0. keel record result (usage) names --evidence-from: grep -c 1. keel gate guard --no-receipt . -> [guard:cli-surface-declared] PASS 86 scanned; [guard:cli-reference] PASS 441 scanned; ALL PASS. keel sync-claude --check . -> claude-surface: keel-owned subset matches this binary's generator (47 registry skills). First live use: sprint 709's story R2 evidence carried the span `cargo nextest run --workspace --release --no-fail-fast -E 'not (...)'` byte for byte into its RAN line (grep -c 1 on the record), where the shell form would have run it.
    part evidenceGoesThroughAFileImplementGateR1 : TestResult { :>> id = "03d3ee23-82e1-425c-a39b-148a4da8a41b"; :>> outcome = VerdictKind::pass; :>> judgedAgainst = "838f75f"; :>> judgedAt = "2026-09-14"; :>> judgedBy = "claudeFable5"; }
    verification evidenceGoesThroughAFileReviewGate : Test { :>> id = "8c290a80-52b2-431d-90c3-7e1501dd9c19"; :>> title = "Sprint 711 review gate — three passes per D0172"; :>> createdAt = "2026-09-14"; :>> createdBy = "claudeFable5"; :>> method = VerificationMethod::inspect; :>> procedureText = "Three passes (D0172). Correctness: the reader is one function, so a sixth prose flag added later gets the file form by construction rather than after its own occurrence; sanitize_field still collapses a multi-line file to the one-line RAN literal, so a file with paragraphs cannot break the SysML literal. Honesty: the shell argument form stays for one-line receipts because ci-run id=... and a demo command are exactly that and refusing them would push receipts back into prose; the refusal on both flags names both so a caller learns which won. Scope: the write path (append_result, append_gate_result) is untouched; every result already in the tree parses as before."; }
    // RAN: Three passes (D0172) over the diff. Correctness: prose_flag is the single reader; the five sites call it and none reads --X-from itself any more (grep flag(args, 'dod-from') and 'description-from' -> 0 outside prose_flag); both-given is Err by name and unreadable-file is Err with the path; sanitize_field still collapses a multi-line file to one RAN literal so paragraphs cannot break the SysML string. Honesty: the shell form stays for one-line receipts because ci-run id=... and demo receipts are one token each; the usage line says which to prefer and why. Scope: the write path is untouched (write:: 36 passed unchanged); the seven remaining prose flags are issue546, not silent scope creep; cliRecord's re-authoring is the 74c1923 precedent and its cost is issue547.
    part evidenceGoesThroughAFileReviewGateR1 : TestResult { :>> id = "cc98aad5-9bf4-43a1-8348-e1a5a2cce368"; :>> outcome = VerdictKind::proposed; :>> judgedAgainst = "838f75f"; :>> judgedAt = "2026-09-14"; :>> judgedBy = "claudeFable5"; }
    verification evidenceGoesThroughAFileCloseOutGate : Test { :>> id = "55f2d280-05bb-41c1-8854-a7cbcca51723"; :>> title = "Sprint 711 closeOut gate (autonomous, D0049)"; :>> createdAt = "2026-09-14"; :>> createdBy = "claudeFable5"; :>> method = VerificationMethod::inspect; :>> procedureText = "Closes at the commit that lands the reader, the five call sites, the test and the four doc homes with this record: keel-land runs the touched set; gate validate / check-engine / guard --no-receipt green; dcEvidenceGoesThroughAFileDoD carries a pass whose own RAN line was written through --evidence-from; git status -sb level with origin and the CI conclusion for that commit read from gh run list --json conclusion."; }
    // RAN: git commit (detached) -> a4a9986 'CR: every prose input of keel record reads a file' ; keel-land: .keel/metrics/touched-receipt.toml head = a4a9986, outcome = pass, runner = cargo-nextest 0.9.144 ; land merged origin (3d462bf, currency intake) as c592ef6 and pushed ; git status -sb -> ## main...origin/main (level) ; gh run list --limit 1 --json conclusion,status,headSha -> conclusion success, headSha c592ef61b7ab35815e8beb27558aa2333ea745d5, status completed ; at c592ef6: keel gate validate . -> 816 tracking file(s) validated clean ; keel gate check-engine . -> .engine instance files validated clean ; keel gate guard --no-receipt . -> [guard] ALL PASS ; dcEvidenceGoesThroughAFileDoD carries pass 792b0232 whose RAN line was itself written through --evidence-from (the first record to use the reader). CloseOut clause met in full.
    part evidenceGoesThroughAFileCloseOutGateR1 : TestResult { :>> id = "65831784-93b5-45e6-8bfc-d433a1edd711"; :>> outcome = VerdictKind::proposed; :>> judgedAgainst = "c592ef6"; :>> judgedAt = "2026-09-14"; :>> judgedBy = "claudeFable5"; }
    verification evidenceGoesThroughAFileRetroGate : Test { :>> id = "9407172d-8f92-4793-a0e2-c648d97434d1"; :>> title = "Sprint 711 retro gate (autonomous, D0049)"; :>> createdAt = "2026-09-14"; :>> createdBy = "claudeFable5"; :>> method = VerificationMethod::analyze; :>> procedureText = "Avoidable issues scanned; findings are tracked items, not prose. The class is a control applied to the instance that fired and not to its siblings - main.rs said so at the fourth occurrence and the fifth still came, because the sentence was a comment, not a reader all five sites share. The retro asks which other flag-shaped prose inputs remain on the argument path (accept --words is a human's short quote and stays; statement and story are read through their own files already) and each found becomes an Issue with a resolver, not a line here. Two findings, both tracked in this commit: seven prose flags remain on the argument path (override --reason, story --i-want / --implication / --triage-note, issue / accept / reject / judge-set --note) - issue546, resolver dcEveryProseFlagReadsAFile; and the CLI fact cliRecord, owned by claudeOpus5, could not be superseded because parse_cli_facts ignores #Supersede, so it was deleted and re-authored as cliRecordVerbs under a new id, the 74c1923 precedent - issue547, resolver dcCliFactSupersessionIsHonoured."; }
    // RAN: Retro scan of sprint 711 (D0131: findings are tracked items). Question the clause asked - which flag-shaped prose inputs remain on the argument path: grep of main.rs for flag(args, over prose names -> override --reason (main.rs:2496), record story --i-want / --so-that / --triage-note (3431-3456; --implication is an ImplicationKind enum member, not prose), accept / reject / judge-set --note (5042 / 5148 / 5270, plus the fold_words_into_note and fold_warnings_into_note readers of --note). Tracked: issue546, resolver dcEveryProseFlagReadsAFile (DoD amended in this commit: --so-that in, --implication out, the enum reason stated). Second finding: the CLI fact cliRecord (claudeOpus5) could not be superseded because parse_cli_facts (guards.rs:6947) ignores #Supersede - tracked as issue547, resolver dcCliFactSupersessionIsHonoured. Third finding made while reading for issue547: cli_surface_violations (guards.rs:6980-6984) compares family, effect, stability and synopsis and never the invocation, so the D0271 claim facts = help = dispatch does not hold for the invocation - and accept already drifts (commands.sysml says (--words TEXT | --note TEXT), cli_facts.rs says --note TEXT; check: scratchpad s712/inv_diff.py over both homes, 86 facts, 1 DIFF). Tracked as issue548, same resolver, whose DoD names it. Consequence for order: issue546 must change four facts owned by claudeOpus5 (accept, reject, judge-set, override), so dcCliFactSupersessionIsHonoured is moved ahead of dcEveryProseFlagReadsAFile in the backlog (declaration order is priority, D0052) with a #DependsOn edge stating why. What went well: the ladder (D0476) was climbed once, green, and the land ran the touched set to pass under nextest on the first attempt. Nothing else avoidable found.
    part evidenceGoesThroughAFileRetroGateR1 : TestResult { :>> id = "3577b931-f588-4199-aed4-f73e5b1800fe"; :>> outcome = VerdictKind::proposed; :>> judgedAgainst = "c592ef6"; :>> judgedAt = "2026-09-14"; :>> judgedBy = "claudeFable5"; }
}
