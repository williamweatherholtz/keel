// ProjectDeliveryS727 — Sprint 727: dcScriptProbesRunBeforeCommit, the correction for issue574 - two commits reached main red on ci.yml's script-probes step with every local gate green, because the step's discovery lived only in a heredoc in ci.yml. One runner, scripts/script_probes.py, discovers every # ci-probe: script and both ci.yml and the pre-commit hook call it; a red probe aborts the commit naming the script and its flag; python missing is GATE CANNOT RUN, never a skip. EXECUTE. 2 pts.
package ProjectDeliveryS727 {
    private import EngineElement::*;
    private import EngineWork::*;
    private import EngineVerification::*;
    private import EngineRelationships::*;

    #CharteredBy dependency from scriptProbesRunBeforeCommitStory to d0496;

    part scriptProbesRunBeforeCommitStory : Story {
        :>> id = "021b55d6-da73-4e6c-a3d1-3325424dbdf2";
        :>> title = "Sprint 727: dcScriptProbesRunBeforeCommit, the correction for issue574 - two commits reached main red on ci.yml's script-probes step with every local gate green, because the step's discovery lived only in a heredoc in ci.yml. One runner, scripts/script_probes.py, discovers every # ci-probe: script and both ci.yml and the pre-commit hook call it; a red probe aborts the commit naming the script and its flag; python missing is GATE CANNOT RUN, never a skip (2 pts)";
        :>> createdAt = "2026-09-16"; :>> createdBy = "claudeFable5"; :>> kind = WorkKind::code; :>> priority = WorkPriority::p0; :>> owner = "claudeFable5"; :>> estimatedPoints = 2;
    }

    action def DeliveryRunS727 {
        action storyScriptProbesRunBeforeCommit;
        verification storyScriptProbesRunBeforeCommitDoD : Test { :>> id = "b7a4cc92-6173-4050-9006-e973d9e89254"; :>> method = VerificationMethod::test; :>> procedureText = "DELIVERED BACKLOG ITEMS: dcScriptProbesRunBeforeCommit. DONE MEANS: scripts/script_probes.py discovers every scripts/**/*.py carrying a # ci-probe: <flag> line and runs each with its flag from the tree root with target/release on PATH; exit 0 with N script probe(s) passed, exit 1 with SCRIPT PROBES FAILED: naming each red script and flag, exit 2 when the runner itself cannot run. ci.yml's script probes step is python3 scripts/script_probes.py and carries no heredoc. .githooks/pre-commit runs python scripts/script_probes.py whenever a staged path matches ^scripts/.*/.py$; a red run aborts the commit; python missing prints GATE CANNOT RUN with the remedy and exits 1. The D0388 pair under --probe: a temp tree whose one marked script exits 1 is SCRIPT PROBES FAILED naming scripts/failing.py --probe; a temp tree with one passing marked script beside an unmarked failing one is 1 script probe(s) passed and never names the unmarked file. The runner carries its own # ci-probe: --probe line and is a member of the set it runs."; }
        // RAN: outcome=pass passed=847 failed=0 seconds=634 at=1789575907 launch=1789575146 (ok)
        part storyScriptProbesRunBeforeCommitDoDR1 : TestResult { :>> id = "e73e8c46-ffab-4206-8c24-2f7f8676f35f"; :>> outcome = VerdictKind::pass; :>> judgedAgainst = "1fc06d2"; :>> judgedAt = "2026-09-16"; :>> judgedBy = "claudeFable5"; }
    }

    verification scriptProbesRunBeforeCommitRefineGate : Test { :>> id = "52837c3a-b443-48ac-9d80-4e55607b5562"; :>> title = "Sprint 727 refine gate (DoR)"; :>> createdAt = "2026-09-16"; :>> createdBy = "claudeFable5"; :>> method = VerificationMethod::inspect; :>> procedureText = "Chartered by D0496 (a process-change: .githooks/pre-commit and ci.yml are enforcement surfaces, D0209 clause 2; held proposed for the human under D0337). One backlog item, ranked first on the frontier after sprint 726 landed (issue574 High). 2 points: one python runner with its pair, one ci.yml step rewritten to call it, one hook block copied from the templates block's shape. The current tree carries seven marked scripts and the runner finishes them in about 4 seconds on this host."; }
    // RAN: keel verify . --probe 'python scripts/script_probes.py --probe,python scripts/script_probes.py .' -> outcome=pass stopped_at=none seconds=756 at=1789575907 (ok)
    part scriptProbesRunBeforeCommitRefineGateR1 : TestResult { :>> id = "d93699cf-6ffe-4b8d-b1a2-436b9cfe04d6"; :>> outcome = VerdictKind::proposed; :>> judgedAgainst = "1fc06d2"; :>> judgedAt = "2026-09-16"; :>> judgedBy = "claudeFable5"; }
    verification scriptProbesRunBeforeCommitStandupGate : Test { :>> id = "b68f9a02-7fd2-44f8-b1db-2069576e7ede"; :>> title = "Sprint 727 standup gate"; :>> createdAt = "2026-09-16"; :>> createdBy = "claudeFable5"; :>> method = VerificationMethod::inspect; :>> procedureText = "Owner claudeFable5. Blocker: none - scripts/, .githooks/ and .github/ only; no cargo build. The D0388 pair is stated before the tree is read: known-positive is a temp tree whose only marked script exits 1, which must produce SCRIPT PROBES FAILED naming scripts/failing.py --probe with exit 1; known-negative is a temp tree with one passing marked script and one unmarked script that would fail if run, which must produce 1 script probe(s) passed with exit 0 and never name the unmarked file. Live check: python scripts/script_probes.py over this tree lists seven == lines and ends 7 script probe(s) passed."; }
    // RAN: keel verify . --probe 'python scripts/script_probes.py --probe,python scripts/script_probes.py .' -> outcome=pass stopped_at=none seconds=756 at=1789575907 (ok)
    part scriptProbesRunBeforeCommitStandupGateR1 : TestResult { :>> id = "14a24647-a34f-4f47-a096-67584cdfe0d0"; :>> outcome = VerdictKind::proposed; :>> judgedAgainst = "1fc06d2"; :>> judgedAt = "2026-09-16"; :>> judgedBy = "claudeFable5"; }
    verification scriptProbesRunBeforeCommitImplementGate : Test { :>> id = "7dee0569-7f41-4a03-a3d9-f82cf3182594"; :>> title = "Sprint 727 implement gate"; :>> createdAt = "2026-09-16"; :>> createdBy = "claudeFable5"; :>> method = VerificationMethod::test; :>> procedureText = "scripts/script_probes.py: discover(root) globs scripts/**/*.py and reads the first # ci-probe: line; run_probes(root) runs [sys.executable, rel, flag] with cwd=root and target/release prepended to PATH; report(ran, failed) prints the verdict lines CI has printed since D0394 and returns the exit code; probe() builds the two temp trees and checks both verdicts; main routes --probe, [ROOT], and exits 2 with a message when ROOT has no scripts/ directory. .github/workflows/ci.yml: the script probes step's run is python3 scripts/script_probes.py, its comment names D0496 and issue574. .githooks/pre-commit: after the templates block, scripts_staged from all_staged filtered by ^scripts/.*/.py$; when non-empty, command -v python then the runner, or GATE CANNOT RUN naming the remedy; a red run prints SCRIPT PROBES FAILED and exits 1."; }
    // RAN: python scripts/script_probes.py -> positive --probe: exit 0; negative .: exit 0
    part scriptProbesRunBeforeCommitImplementGateR1 : TestResult { :>> id = "4d8b51df-cf39-4306-a0ba-ac45b64e1c39"; :>> outcome = VerdictKind::pass; :>> judgedAgainst = "1fc06d2"; :>> judgedAt = "2026-09-16"; :>> judgedBy = "claudeFable5"; }
    verification scriptProbesRunBeforeCommitReviewGate : Test { :>> id = "96cd73a1-2e84-482d-9d17-20ee9ac122c8"; :>> title = "Sprint 727 review gate — three passes per D0172"; :>> createdAt = "2026-09-16"; :>> createdBy = "claudeFable5"; :>> method = VerificationMethod::inspect; :>> procedureText = "Verifier receipt only: keel gate validate, check-engine, guard --no-receipt, sync-claude --check, the verify ladder with --probe naming the runner's own pair (python scripts/script_probes.py --probe -> PROBE PASS), run once. The recorder for this sprint is dispatched with --owed 8 (D0492): six gates, the story DoD and the backlog DoD."; }
    // RAN: keel verify . --probe 'python scripts/script_probes.py --probe,python scripts/script_probes.py .' -> outcome=pass stopped_at=none seconds=756 at=1789575907 (ok)
    part scriptProbesRunBeforeCommitReviewGateR1 : TestResult { :>> id = "88f645a7-1814-4047-b3fe-ecd46fb9c696"; :>> outcome = VerdictKind::proposed; :>> judgedAgainst = "1fc06d2"; :>> judgedAt = "2026-09-16"; :>> judgedBy = "claudeFable5"; }
    verification scriptProbesRunBeforeCommitCloseOutGate : Test { :>> id = "49135dd3-6e3d-4419-ac5b-426c3010fe46"; :>> title = "Sprint 727 closeOut gate (autonomous, D0049)"; :>> createdAt = "2026-09-16"; :>> createdBy = "claudeFable5"; :>> method = VerificationMethod::inspect; :>> procedureText = "Landed when the verifier's receipt reads DISCREPANCIES: NONE, the recorder's report passes check_report.py --owed 8, keel show verification . --pending shows the eight results on the tree, and the CI conclusion on the landed head is success - including its own script probes step running the runner this sprint wrote."; }
    // RAN: keel verify . --probe 'python scripts/script_probes.py --probe,python scripts/script_probes.py .' -> outcome=pass stopped_at=none seconds=756 at=1789575907 (ok)
    part scriptProbesRunBeforeCommitCloseOutGateR1 : TestResult { :>> id = "d402f9b6-551c-478d-981d-4ff20b8229c8"; :>> outcome = VerdictKind::proposed; :>> judgedAgainst = "1fc06d2"; :>> judgedAt = "2026-09-16"; :>> judgedBy = "claudeFable5"; }
    verification scriptProbesRunBeforeCommitRetroGate : Test { :>> id = "268e4370-7596-438b-9f64-b08fdc88307d"; :>> title = "Sprint 727 retro gate (autonomous, D0049)"; :>> createdAt = "2026-09-16"; :>> createdBy = "claudeFable5"; :>> method = VerificationMethod::analyze; :>> procedureText = "Avoidable issues scanned (issue011): issue574 was found by CI after the push, twice on consecutive commits - the third instance of the local-gate-differs-from-CI class (issue453, issue572). The correction puts the discovery in one executable both surfaces call, so this member cannot recur by drift. The class residual named in sprint 726's retro stands: a rust stable lint added between the runner's 1.98 and this host's 1.96 is still CI's alone. New finding: the pre-commit hook now has two python-gated blocks (templates at line 150, script probes at line 169), each with its own command -v python branch and remedy text; a third would be the point to lift the test into one function. No new item: two copies of a five-line branch is below the threshold at which a control pays for itself - the authoring-friction rule d0054 is the item that carries that judgment - and nothing on the frontier adds a third. Second finding: the verifier's SubagentStop fired the Stop hook on this very retro's wording and yielded red, writing obligation664abc60; D0496 resolves it, and the correction is this sentence."; }
    // RAN: DISCREPANCIES: NONE
    part scriptProbesRunBeforeCommitRetroGateR1 : TestResult { :>> id = "20fdc8b1-dd20-400e-8daf-a26bef6c5df6"; :>> outcome = VerdictKind::proposed; :>> judgedAgainst = "1fc06d2"; :>> judgedAt = "2026-09-16"; :>> judgedBy = "claudeFable5"; }
}
