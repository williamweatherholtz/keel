// ProjectDeliveryS746 — Sprint 746: v0.5.0 lands downstream green - the release the adopters asked for (GH#68, GH#86-90) is cut, published, verified from its own asset, and the three retro-745 findings that would meet the next adopter are closed: the guard set runs over an adopter-shaped tree in the suite (issue615), the SchemaLacksMember refusal is a census row and a ledger fact (issue616), and keel onboard's unresolved-charter advice fits a first-time adopter (issue617); the release cut itself surfaced a fourth, two guard fixtures pinned at the literal 0.4.1 (issue619). The human's direction: 'Proceed to release and fix downstream' (2026-09-18).. EXECUTE. 5 pts.
package ProjectDeliveryS746 {
    private import EngineElement::*;
    private import EngineWork::*;
    private import EngineVerification::*;
    private import EngineRelationships::*;

    #CharteredBy dependency from releaseDownstreamGreenStory to d0519;
    #Delivers dependency from releaseDownstreamGreenStory to dcReleaseGuardFixturesPinTheBinaryVersion;
    #Delivers dependency from releaseDownstreamGreenStory to dcAFreshAdopterTreeIsGreenUnderEveryGuard;
    #Delivers dependency from releaseDownstreamGreenStory to dcSchemaLacksMemberRefusalIsLedgered;
    #Delivers dependency from releaseDownstreamGreenStory to dcUnresolvedCharterAdviceFitsAFirstTimeAdopter;
    #Delivers dependency from releaseDownstreamGreenStory to dcVerbFoldsTravelWithMigrate;
    #Delivers dependency from releaseDownstreamGreenStory to dcAllocatedNameIsOneNamespaceAcrossPackages;

    part releaseDownstreamGreenStory : Story {
        :>> id = "6a180e3d-65bf-403b-aaa9-98903d381dc2";
        :>> title = "Sprint 746: v0.5.0 lands downstream green - the release the adopters asked for (GH#68, GH#86-90) is cut, published, verified from its own asset, and the three retro-745 findings that would meet the next adopter are closed: the guard set runs over an adopter-shaped tree in the suite (issue615), the SchemaLacksMember refusal is a census row and a ledger fact (issue616), and keel onboard's unresolved-charter advice fits a first-time adopter (issue617); the release cut itself surfaced a fourth, two guard fixtures pinned at the literal 0.4.1 (issue619). The human's direction: 'Proceed to release and fix downstream' (2026-09-18). (5 pts)";
        :>> createdAt = "2026-09-19"; :>> createdBy = "claudeFable5"; :>> kind = WorkKind::code; :>> priority = WorkPriority::p0; :>> owner = "claudeFable5"; :>> estimatedPoints = 5;
    }

    action def DeliveryRunS746 {
        action storyReleaseDownstreamGreen;
        verification storyReleaseDownstreamGreenDoD : Test { :>> id = "e145c270-44a1-4e71-b6bb-45aed2d78f8e"; :>> method = VerificationMethod::test; :>> procedureText = "DELIVERED BACKLOG ITEMS: dcReleaseGuardFixturesPinTheBinaryVersion, dcAFreshAdopterTreeIsGreenUnderEveryGuard, dcSchemaLacksMemberRefusalIsLedgered, dcUnresolvedCharterAdviceFitsAFirstTimeAdopter, dcVerbFoldsTravelWithMigrate (added mid-sprint: the downloaded 0.5.0 rolled back on the adopter tree - issue622 - so the release that lands downstream is 0.5.1, cut in this sprint), dcAllocatedNameIsOneNamespaceAcrossPackages (added mid-sprint: issue624, the issue-number collision the merge landed green). DONE MEANS: each task's DoD holds with its own tests (the D0388 pairs named in the DoDs); tag v0.5.0 is pushed at a commit CI verified, the release run attached three assets, their .sha256 files and SHA256SUMS, the downloaded windows asset verifies against SHA256SUMS and reports 0.5.0 at the tagged commit, keel-wrapper.toml carries the ['0.5.0'] entries copied from the published SHA256SUMS and release050's commit field names the tagged sha; keel migrate run by the DOWNLOADED 0.5.1 binary over a tree keel init 0.4.1 scaffolded (a Cargo.toml and one Rust member, not the self-build) ends green under its own post-apply gate with its CLAUDE.md naming keel show orient; 0.5.1 is tagged, published and wrapper-pinned the same way as 0.5.0; GH#86-90 carry a comment naming the release that lands; the ladder is green and CI green at each landing commit."; }
        // RAN: // RAN: the six delivered items each carry a passing DoD result read from .tracking/backlog.sysml (dcReleaseGuardFixturesPinTheBinaryVersionDoDR1 @72eebf0a; dcAFreshAdopterTreeIsGreenUnderEveryGuardDoDR1, dcSchemaLacksMemberRefusalIsLedgeredDoDR1, dcUnresolvedCharterAdviceFitsAFirstTimeAdopterDoDR1, dcVerbFoldsTravelWithMigrateDoDR1 @4a0abc85; dcAllocatedNameIsOneNamespaceAcrossPackagesDoDR1 @5170199e); v0.5.1 cut at 5f89df77, release run 35425995013 success, published Windows asset sha256sum -c OK and `keel version` 0.5.1/5f89df7; the downloaded binary retained over a fresh 0.4.1-scaffolded tree (/c/kt/adopt051: migrate exit 0, pin 0.5.1, gate guard ALL PASS); GH#86-90 answered and closed. Deviation stated: issue623 (repeated single flag) was tracked mid-sprint and NOT delivered; it stays on the frontier.
        part storyReleaseDownstreamGreenDoDR1 : TestResult { :>> id = "a5ce4b55-a4bd-4649-9d77-c584681bad59"; :>> outcome = VerdictKind::pass; :>> judgedAgainst = "5f89df77"; :>> judgedAt = "2026-09-19"; :>> judgedBy = "claudeFable5"; }
    }

    verification releaseDownstreamGreenRefineGate : Test { :>> id = "8f4789f9-97fc-4a60-83f0-254e7c746de5"; :>> title = "Sprint 746 refine gate (DoR)"; :>> createdAt = "2026-09-19"; :>> createdBy = "claudeFable5"; :>> method = VerificationMethod::inspect; :>> procedureText = "DoR: four tasks sized together at 5 points - the adopter-shaped suite test is a module (a fixture, the guard run, the pair), the census/ledger rows and the onboard advice are one-function changes with tests, the fixture pin is a two-line change already verified; the release steps are the release skill's procedure, not new code. Scope is the four DoDs plus the release skill's steps 2-5. No blocking dependency: the release cut is committed locally (72eebf0a) and lands with the fixture fix."; }
    part releaseDownstreamGreenRefineGateR1 : TestResult { :>> id = "c100edbe-c923-4c46-a038-7f8261dba4cc"; :>> outcome = VerdictKind::proposed; :>> judgedAgainst = "4a0abc85"; :>> judgedAt = "2026-09-18"; :>> judgedBy = "claudeFable5"; :>> notes = "DoR read against the story: four tasks named with DoDs carrying D0388 pairs; 5 points; #CharteredBy d0519 (accepted, marked); no blocking dependency - the release cut 72eebf0a and the fixture fix 4a0abc85 landed, CI success at 4a0abc85, tag v0.5.0 pushed at it."; }
    verification releaseDownstreamGreenStandupGate : Test { :>> id = "9db30b8c-8ef1-4c5a-84b8-084da8b4973e"; :>> title = "Sprint 746 standup gate"; :>> createdAt = "2026-09-19"; :>> createdBy = "claudeFable5"; :>> method = VerificationMethod::inspect; :>> procedureText = "Owner claudeFable5. Blocker: none. Risk: the tag must point at a commit CI has verified, so the fixture fix lands and CI concludes before the tag is pushed; the wrapper entries can only be copied after the release run publishes SHA256SUMS, so they and the release050 commit field land one commit after the tag (issue311). A second risk: the adopter-shaped test deploys the embedded engine, so it is keyed on the engine's content and re-runs on every .engine change - the cost is the suite's, stated in the DoD."; }
    part releaseDownstreamGreenStandupGateR1 : TestResult { :>> id = "dba6c1ea-2f2c-4080-93d8-b0b4e8c0eff3"; :>> outcome = VerdictKind::proposed; :>> judgedAgainst = "4a0abc85"; :>> judgedAt = "2026-09-18"; :>> judgedBy = "claudeFable5"; :>> notes = "Standup: owner claudeFable5; release run 35417343896 concluded success at 4a0abc85; the three resolvers are coded and their tests pass locally (init_smoke 3 passed, schema_member_refusal_is_ledgered 3 passed, keel-model onboard:: 4 passed); the ladder is being climbed; the wrapper entries wait on the published SHA256SUMS (issue311)."; }
    verification releaseDownstreamGreenImplementGate : Test { :>> id = "5497e63b-99a6-4b0a-a231-2648ed4d95b2"; :>> title = "Sprint 746 implement gate"; :>> createdAt = "2026-09-19"; :>> createdBy = "claudeFable5"; :>> method = VerificationMethod::test; :>> procedureText = "The implement gate is the change itself under the ladder: keel verify . --probe-from pair746.txt (validate, check-engine, guard, clippy, the pair, suite --touched), stopping at the first red; plus the release skill's verification of the published asset (sha256sum -c against SHA256SUMS, the downloaded binary's version and build commit)."; }
    // RAN: // RAN: keel verify . --probe-from pair746c.txt (detached, receipt .keel/metrics/verify-receipt.toml) at the tree committed as d19cb819: validate pass 0 s (863 clean), guard pass 4 s (ALL PASS), clippy pass 109 s (both triples, -D warnings), probe pass 173 s (POS cargo test --release -p keel-guards --lib an_allocated_name_is_one_namespace_across_packages -> 1 passed; NEG cargo test --release -p keel-cli --test migration_respells_the_projects_own_docs an_uncommitted_claude_md_is_refused_at_the_door -> 1 passed), touched pass 671 s; 'keel verify: pass - every rung green in 959 s'. Earlier rungs on the way (pair746b): source-reference red on migrate.rs:965 citations, clippy must_use_candidate on living_doc_files, resync_is_not_a_self_modification asserting the old wording - each fixed, the ladder relaunched. Release cut 5f89df77 gated by the rebuilt 0.5.1 binary: gate validate 863 clean; gate check-engine clean; gate guard --no-receipt ALL PASS (release-recorded PASS 10 scanned); cargo clippy --release --workspace --all-targets -- -D warnings Finished. Published asset (release run 35425995013, conclusion success): gh release download v0.5.1 --pattern keel-windows-x86_64.exe --pattern SHA256SUMS; sha256sum -c --ignore-missing SHA256SUMS -> keel-windows-x86_64.exe: OK; ./keel-windows-x86_64.exe version -> 'keel 0.5.1 / build commit: 5f89df7 / api contract: 2.0.0 / guards: 76'. Downloaded 0.5.1 over a fresh 0.4.1-scaffolded adopter (/c/kt/adopt051, `keel-windows-x86_64.exe init .` from the v0.4.1 asset, committed 633f5e4): KEEL_ACTOR=adopter keel migrate . -> exit 0, verb-respell CLAUDE.md 14 edits + attestation-policy.toml 1 + github-actors.toml 1, 'pin: engine-version.toml now reads 0.5.1', 'NEXT: commit' - RETAINED, no rollback; then gate validate 1 clean, gate guard --no-receipt ALL PASS, CLAUDE.md holds 0 retired verbs (grep -c keel orient|whats-next|add-task|report -> 0, was 6).
    part releaseDownstreamGreenImplementGateR1 : TestResult { :>> id = "d4b1c6d8-1d62-4899-bba8-ffbef586b22e"; :>> outcome = VerdictKind::pass; :>> judgedAgainst = "5f89df77"; :>> judgedAt = "2026-09-19"; :>> judgedBy = "claudeFable5"; }
    verification releaseDownstreamGreenReviewGate : Test { :>> id = "a66cf76e-7fba-4d86-8b0e-16e3ee48cc8e"; :>> title = "Sprint 746 review gate — three passes per D0172"; :>> createdAt = "2026-09-19"; :>> createdBy = "claudeFable5"; :>> method = VerificationMethod::inspect; :>> procedureText = "Verifier receipt read against the four DoDs: every named test present and passing; the release assets and SHA256SUMS verified from the download, not from the workflow log; guard wrapper-pin-checksummed green once the entries land; three passes per D0172 (substance, ceremony, doc-sync: the CHANGELOG entry names what shipped, the release skill's steps were followed in order)."; }
    // RAN: // RAN: Review at 5f89df77+wrapper (2026-09-19), three passes (D0172). SUBSTANCE: the five delivered DoDs each carry a passing result read from the tree - dcReleaseGuardFixturesPinTheBinaryVersionDoDR1 (judgedAgainst 72eebf0a), dcAFreshAdopterTreeIsGreenUnderEveryGuardDoDR1 / dcSchemaLacksMemberRefusalIsLedgeredDoDR1 / dcUnresolvedCharterAdviceFitsAFirstTimeAdopterDoDR1 / dcVerbFoldsTravelWithMigrateDoDR1 (4a0abc85), dcAllocatedNameIsOneNamespaceAcrossPackagesDoDR1 (5170199e); `keel show open-issues .` at this tree lists issue615, issue616, issue617, issue619, issue622, issue624 as NOT open and issue623 as OPEN - issue623's resolver dcARepeatedSingleFlagIsRefused has no result and is NOT in the sprint's delivered list, correctly. The published asset was verified from the download, not the workflow log: sha256sum -c SHA256SUMS -> OK, `keel version` -> 0.5.1 at 5f89df7; the downloaded binary RETAINED over the fresh 0.4.1 adopter /c/kt/adopt051 (migrate exit 0, verb-respell 16 edits, pin 0.5.1, guards ALL PASS). CEREMONY: sprint746 Story #CharteredBy d0519 (accepted); refine and standup results proposed (AI-examined, D0312 B); guard wrapper-pin-checksummed PASS 1 scanned 0 warnings once the ['0.5.1'] entries landed from run 35425995013's SHA256SUMS; release051 tag = v0.5.1, commit = 5f89df77 (the tagged commit, issue311); gate validate 863 clean. DOC-SYNC: CHANGELOG v0.5.1 names D0523/issue615-617/issue622 and the D0524/issue624 guard class, and does NOT name issue623; the release skill's steps ran in order (version reconciled -> gate at the cut tree with the 0.5.1 binary -> tag, run 35425995013 success, asset downloaded and asked -> wrapper entries copied from the published SHA256SUMS -> Release recorded). FINDING: release051's purpose as first authored (5f89df77) named issue623 as fixed - it was not; corrected here, tracked as issue627 with resolver dcAReleasePurposeNamesOnlyResolvedIssues (a guard reading a Release purpose's issue references against computed resolution at its commit).
    part releaseDownstreamGreenReviewGateR1 : TestResult { :>> id = "879b4ef3-9fe0-440d-8c22-c5e9cccebeaa"; :>> outcome = VerdictKind::proposed; :>> judgedAgainst = "5f89df77"; :>> judgedAt = "2026-09-19"; :>> judgedBy = "claudeFable5"; }
    verification releaseDownstreamGreenCloseOutGate : Test { :>> id = "3298d61d-5b01-4975-a4c5-fd9926c362b8"; :>> title = "Sprint 746 closeOut gate (autonomous, D0049)"; :>> createdAt = "2026-09-19"; :>> createdBy = "claudeFable5"; :>> method = VerificationMethod::inspect; :>> procedureText = "Landed by keel land with the touched set green and CI green at each landing commit; issue615-617 and issue619 resolve by their #Resolves edges; the tag is published and its assets verified; GH#86-90 are answered on GitHub with the release named."; }
    // RAN: // RAN: closeOut at 5f89df77 + this commit (2026-09-19). Landings: 4a0abc85 (sprint opens, issue619), 1809e70f (issue622 verb-respell, ladder 558 s green), 5170199e (merge with claudeOpus5's 1228a756, gated by hand: validate 863 clean, guard ALL PASS), d19cb819 (D0524/issue624, ladder 959 s green, `keel land: landed.`, CI 35425146062 success), 5f89df77 (release cut, touched 907 passed in 697 s, `keel land: landed.`, CI 35425969654 + release 35425995013 success). `git status -sb` read `## main...origin/main` after each land. Resolution read from `keel show open-issues .`: issue615, issue616, issue617, issue619, issue622, issue624 not open; issue623 open (not delivered, not claimed). Tag v0.5.1 published with three binaries, three .sha256 and SHA256SUMS; the Windows asset downloaded, checksum OK, `keel version` 0.5.1 at 5f89df7; retained over /c/kt/adopt051. GH#86, #87, #88, #89, #90 answered with the release named and closed (completed) via gh issue comment --body-file / gh issue close; one correction comment on #88 (issue628).
    part releaseDownstreamGreenCloseOutGateR1 : TestResult { :>> id = "e7482a3e-274b-44ad-be72-e0e771019aa7"; :>> outcome = VerdictKind::proposed; :>> judgedAgainst = "5f89df77"; :>> judgedAt = "2026-09-19"; :>> judgedBy = "claudeFable5"; }
    verification releaseDownstreamGreenRetroGate : Test { :>> id = "1f06fa9d-8e75-407f-be00-5b59f4b6058d"; :>> title = "Sprint 746 retro gate (autonomous, D0049)"; :>> createdAt = "2026-09-19"; :>> createdBy = "claudeFable5"; :>> method = VerificationMethod::analyze; :>> procedureText = "Written at closeOut, after the verifier's receipt and before the recorder; avoidable issues scanned (issue011), each finding a tracked item or the reason it is not. (1) Found at the sprint's opening, landing the release cut: keel land refused the push because two wrapper-pin guard fixtures pinned the literal 0.4.1 and were refused under engine-version skew by the 0.5.0 binary before the guard ran - a fixture that encodes the current release is green by coincidence and red on the next cut. Tracked: issue619 (Low), resolved by dcReleaseGuardFixturesPinTheBinaryVersion (the fixture reads env!(CARGO_PKG_VERSION); delivered in the same commit that adds it). Further findings are appended at closeOut."; }
    // RAN: // RAN: retro at closeOut (2026-09-19), avoidable issues scanned (issue011); every finding is a tracked item this commit adds or its reason. (2) Two sessions on two machines minted issue620/issue621 from the same base and the merge landed green because duplicate-identity keyed names per package while every lens reads the bare name - tracked as issue624, resolved in-sprint by dcAllocatedNameIsOneNamespaceAcrossPackages under D0524 (guard class 5; held proposed for the human). (3) `keel land`'s merged-tree gate, inside the post-commit hook, refused the merge on two edge-endpoints violations the merged tree does not have (both actions declared at backlog.sysml:2884/2886); the merge was committed by hand - tracked as issue625 (Medium), resolver dcLandMergedGateReadsTheTreeTheMergeWrote: reproduce under the hook's environment before reasoning about the cause. (4) An incremental build ships the previous .engine tree - include_dir has no rerun-if-changed edge and the `touch embedded.rs` line is a reminder, not a control (D0047); it was forgotten twice this sprint - tracked as issue626 (Low), resolver dcEngineEmbedRerunsOnEngineChange (a build.rs). (5) release051's purpose as first authored named issue623 as fixed in v0.5.1; it is open, its resolver has no result; the AI wrote what shipped from memory of the sprint and no guard reads a Release purpose's issue references against computed resolution - corrected in this commit, tracked as issue627 (Medium), resolver dcAReleasePurposeNamesOnlyResolvedIssues. (6) GH#88's answer typed issue612's resolver by a name the tree does not hold; github-intake step 4 has no render and every comment is prose from memory - corrected on GitHub, tracked as issue628 (Low), resolver dcGitHubAnswerRendersFromTheModel. Pattern across (5) and (6): both are state authored in prose for a reader outside the model (D0018), caught only by reading back after the write; the controls proposed put the read-back BEFORE the write. Not tracked: the issue622 renumbering's byte replacement also rewrote the other session's two DoD texts (caught by guard issues red, restored before commit) - the guard was the control and it fired.
    part releaseDownstreamGreenRetroGateR1 : TestResult { :>> id = "046946aa-25b4-4dff-8da5-0c2d8c5a052c"; :>> outcome = VerdictKind::proposed; :>> judgedAgainst = "5f89df77"; :>> judgedAt = "2026-09-19"; :>> judgedBy = "claudeFable5"; }
}
