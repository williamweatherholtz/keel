// ProjectDeliveryS754 — Sprint 754: The recorder's report is read against the tree it describes: under --root, check_report.py counts the TestResult parts the working tree gained since HEAD under .tracking and refuses a report whose WROTE lines claim fewer, naming each gained result no WROTE key claims (D0537; issue602). EXECUTE. 2 pts.
package ProjectDeliveryS754 {
    private import EngineElement::*;
    private import EngineWork::*;
    private import EngineVerification::*;
    private import EngineRelationships::*;

    #CharteredBy dependency from recorderReportAccountsForEveryTreeWriteStory to d0537;
    #Delivers dependency from recorderReportAccountsForEveryTreeWriteStory to dcRecorderReportAccountsForEveryTreeWrite;

    part recorderReportAccountsForEveryTreeWriteStory : Story {
        :>> id = "4e0584dc-bf8c-48cf-a824-b9b7cf7d5db7";
        :>> title = "Sprint 754: The recorder's report is read against the tree it describes: under --root, check_report.py counts the TestResult parts the working tree gained since HEAD under .tracking and refuses a report whose WROTE lines claim fewer, naming each gained result no WROTE key claims (D0537; issue602) (2 pts)";
        :>> createdAt = "2026-09-20"; :>> createdBy = "claudeFable5"; :>> kind = WorkKind::code; :>> priority = WorkPriority::p0; :>> owner = "claudeFable5"; :>> estimatedPoints = 2;
    }

    action def DeliveryRunS754 {
        action storyRecorderReportAccountsForEveryTreeWrite;
        verification storyRecorderReportAccountsForEveryTreeWriteDoD : Test { :>> id = "477aefa3-04ba-49c9-a371-7bafc4c23b14"; :>> method = VerificationMethod::test; :>> procedureText = "DELIVERED BACKLOG ITEM: dcRecorderReportAccountsForEveryTreeWrite. DONE MEANS: the task's DoD passes as written - .engine/skills/delegated-ceremony/references/check_report.py gains results_gained(root) (git diff HEAD -U0 -- .tracking added lines plus untracked .tracking/*.sysml, matched by the RESULT_PART regex and attributed to their file) and refusal 9: a report whose WROTE lines number fewer than the gained results is refused naming each gained result no WROTE key claims, where a --gate G key claims G R<n> and a --task T key claims T R<n> or T DoDR<n>; the recorder brief's rule 7 says a write that lands after a refused attempt is a WROTE line naming the command that landed, never a REFUSED line for the attempt that did not; fixtures positive-sprint741-landed-write-filed-refused.txt (seven WROTE, one REFUSED, refused under --owed 8 over the eight results sprint 741 gained, naming dcTouchedSetDescendsTheWorkspaceDoDR1 in .tracking/backlog.sysml) and negative-sprint741-eight-written.txt (eight WROTE over the same eight; passes) sit in references/fixtures and in the --probe table as rows carrying their gained list; --probe --root . reports every pair holds over twelve rows; the process step dcyRecorderReport, SKILL.md's refusal list and probe paragraph, and CLAUDE.md name the clause; sync-claude --check matches. Verified by the verifier ladder with the two fixture probes as the D0388 pair and keel gate guard green at the landing tree."; }
        // RAN: keel suite --touched: pass - 925 passed in 776s over [83 binaries]; 0 failed, failing []
        part storyRecorderReportAccountsForEveryTreeWriteDoDR1 : TestResult { :>> id = "c32262b8-4d1f-470b-b3ae-415e30bf11b2"; :>> outcome = VerdictKind::pass; :>> judgedAgainst = "6983116e"; :>> judgedAt = "2026-09-20"; :>> judgedBy = "claudeFable5"; }
    }

    verification recorderReportAccountsForEveryTreeWriteRefineGate : Test { :>> id = "783fc320-19bf-453c-81c0-503e385468cf"; :>> title = "Sprint 754 refine gate (DoR)"; :>> createdAt = "2026-09-20"; :>> createdBy = "claudeFable5"; :>> method = VerificationMethod::inspect; :>> procedureText = "One backlog item, sized 2: a Python check gains a git-reading function and one refusal, two fixtures, two probe rows, a brief rule, one process actionText clause and three doc surfaces. DoR: estimatedPoints 2; #CharteredBy d0537 (proposed, #ProspectiveChange, held for the human - the code change rides it as the co-committed Decision); #Delivers dcRecorderReportAccountsForEveryTreeWrite; no blocking dependency; the DoD exists in the backlog with its own known-positive and known-negative named before the tree was read."; }
    // RAN: validate=pass guard=pass clippy=pass probe=pass touched=pass
    part recorderReportAccountsForEveryTreeWriteRefineGateR1 : TestResult { :>> id = "667edaf4-251c-42ae-aa37-a9216ac41e68"; :>> outcome = VerdictKind::proposed; :>> judgedAgainst = "6983116e"; :>> judgedAt = "2026-09-20"; :>> judgedBy = "claudeFable5"; }
    verification recorderReportAccountsForEveryTreeWriteStandupGate : Test { :>> id = "00ad40b8-a8e7-44fd-8334-ddda8bdbfdba"; :>> title = "Sprint 754 standup gate"; :>> createdAt = "2026-09-20"; :>> createdBy = "claudeFable5"; :>> method = VerificationMethod::inspect; :>> procedureText = "The check reads git, not the recorder's word: what the tree gained since HEAD is the fact, the report is the claim, and refusal 9 holds the claim to the fact. A WROTE key claims a result by the API's own naming (G R<n>, T R<n>, T DoDR<n>), so a result recorded under the action name is claimed by the --task line that named the action - the sprint 741 shape (the DoD Test name in the dispatch, the action name on the retry) is exactly what the claim rule resolves. Residual named in D0537: a result the primary records onto the dirty tree before dispatch is gained and unclaimed, so the primary commits its own results first or lists them as owed. Impediment: none."; }
    // RAN: validate=pass guard=pass clippy=pass probe=pass touched=pass
    part recorderReportAccountsForEveryTreeWriteStandupGateR1 : TestResult { :>> id = "a694ae6e-5153-40f1-9779-2d5467ea0363"; :>> outcome = VerdictKind::proposed; :>> judgedAgainst = "6983116e"; :>> judgedAt = "2026-09-20"; :>> judgedBy = "claudeFable5"; }
    verification recorderReportAccountsForEveryTreeWriteImplementGate : Test { :>> id = "ef125ff2-0e22-4e7c-bd8a-4487ac4427bc"; :>> title = "Sprint 754 implement gate"; :>> createdAt = "2026-09-20"; :>> createdBy = "claudeFable5"; :>> method = VerificationMethod::test; :>> procedureText = "python .engine/skills/delegated-ceremony/references/check_report.py --probe --root .: probe: every pair holds (12 rows, the two sprint741 rows judged over a tree that gained 8 result(s)). The parser fed the diff HEAD~1..HEAD named all eight of sprint 753's landed TestResult parts by part and file. The live sprint 753 report re-checked under --root passes with 0 gained at the committed tree. gate validate 871 clean; check-engine clean; gate guard --no-receipt ALL PASS; sync-claude synced 47/47 skills and --check matches."; }
    // RAN: validate=pass guard=pass clippy=pass probe=pass touched=pass
    part recorderReportAccountsForEveryTreeWriteImplementGateR1 : TestResult { :>> id = "70e76c67-19b2-4a69-af98-0b75dde402be"; :>> outcome = VerdictKind::pass; :>> judgedAgainst = "6983116e"; :>> judgedAt = "2026-09-20"; :>> judgedBy = "claudeFable5"; }
    verification recorderReportAccountsForEveryTreeWriteReviewGate : Test { :>> id = "0ccebea7-84ee-456f-97e2-899c15108940"; :>> title = "Sprint 754 review gate — three passes per D0172"; :>> createdAt = "2026-09-20"; :>> createdBy = "claudeFable5"; :>> method = VerificationMethod::inspect; :>> procedureText = "Three passes per D0172. Code read back: results_gained runs git -C root diff HEAD -U0 -- .tracking and git ls-files --others --exclude-standard -- .tracking, tracks the current file from +++ b/ headers, matches added lines with RESULT_PART, and degrades to a stderr note and an empty list when git is absent so the other eight refusals still run; claims() is a fullmatch of key + optional DoD + R + digits; the refusal fires only when gained exceeds the WROTE count and names the unclaimed subset, or every gained result when all are claimed by name yet the count is short. Ceremony: D0537 is proposed with the process-change marker and held for the human; the change to a skill check and a process actionText is an enforcement change, so the Decision is co-committed under the CR prefix. Doc-sync in the same commit: dcyRecorderReport actionText, SKILL.md refusal 9, probe paragraph and recorder rule 7, CLAUDE.md subagents paragraph, the .claude copies via sync-claude. FINDING for the retro: the dispatch that caused sprint 741's refusal named the DoD Test rather than the action, and the same slip was made at sprint 753's dispatch - the recorder corrected it silently both times."; }
    // RAN: validate=pass guard=pass clippy=pass probe=pass touched=pass
    part recorderReportAccountsForEveryTreeWriteReviewGateR1 : TestResult { :>> id = "059a86c9-cb41-4e4f-9884-155124fce949"; :>> outcome = VerdictKind::proposed; :>> judgedAgainst = "6983116e"; :>> judgedAt = "2026-09-20"; :>> judgedBy = "claudeFable5"; }
    verification recorderReportAccountsForEveryTreeWriteCloseOutGate : Test { :>> id = "3781a392-84e4-43e2-b621-d9a3cb133a64"; :>> title = "Sprint 754 closeOut gate (autonomous, D0049)"; :>> createdAt = "2026-09-20"; :>> createdBy = "claudeFable5"; :>> method = VerificationMethod::inspect; :>> procedureText = "The task's DoD result and the six gate results are recorded from the verifier's rendered receipt; issue602 resolves when the DoD passes. Doc-sync rode the change. The check's own probe table is the regression suite for the two new fixtures; no code under keel-cli changed, so the touched test set is the members the ladder names."; }
    // RAN: validate=pass guard=pass clippy=pass probe=pass touched=pass
    part recorderReportAccountsForEveryTreeWriteCloseOutGateR1 : TestResult { :>> id = "1fb94aa4-e4b9-430d-a643-2abf502dfa05"; :>> outcome = VerdictKind::proposed; :>> judgedAgainst = "6983116e"; :>> judgedAt = "2026-09-20"; :>> judgedBy = "claudeFable5"; }
    verification recorderReportAccountsForEveryTreeWriteRetroGate : Test { :>> id = "65b69e91-7cac-4764-857b-a15c611c72ca"; :>> title = "Sprint 754 retro gate (autonomous, D0049)"; :>> createdAt = "2026-09-20"; :>> createdBy = "claudeFable5"; :>> method = VerificationMethod::analyze; :>> procedureText = "One finding, avoidable issues scanned (issue602). Finding: two dispatches in a row (sprints 741 and 753) listed the owed DoD record by the Test's name (<action>DoD) while record result --task takes the action's name; the recorder retried and landed the write both times, and sprint 741's retry is the very write refusal 9 now catches. The dispatch's owed list is typed by the primary from the sprint file, and nothing checks that each --task it names is an action the API resolves. NOT A PROCESS CHANGE: this retro names the slip; whether the owed list is checked before dispatch is tracked as issue663 with resolver dcDispatchOwedListResolvesInTheTree (a pre-dispatch check of every --gate and --task key against the tree)."; }
    // RAN: validate=pass guard=pass clippy=pass probe=pass touched=pass
    part recorderReportAccountsForEveryTreeWriteRetroGateR1 : TestResult { :>> id = "5c55839a-0e35-4450-8b06-a0282bf15e0e"; :>> outcome = VerdictKind::proposed; :>> judgedAgainst = "6983116e"; :>> judgedAt = "2026-09-20"; :>> judgedBy = "claudeFable5"; }
}
