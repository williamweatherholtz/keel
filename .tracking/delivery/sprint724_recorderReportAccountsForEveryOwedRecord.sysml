// ProjectDeliveryS724 — Sprint 724: dcRecorderReportAccountsForEveryOwedRecord, the correction for issue568 - sprint 723's first recorder ran no record command, returned a three-line report reading DISCREPANCIES: NONE, and check_report.py passed it because its five refusals read only the WROTE lines present. The check now refuses a report that accounts for nothing, and under --owed N one that accounts for fewer records than the dispatch named (D0492, held for the human).. EXECUTE. 2 pts.
package ProjectDeliveryS724 {
    private import EngineElement::*;
    private import EngineWork::*;
    private import EngineVerification::*;
    private import EngineRelationships::*;

    #CharteredBy dependency from recorderReportAccountsForEveryOwedRecordStory to d0492;

    part recorderReportAccountsForEveryOwedRecordStory : Story {
        :>> id = "4a2108fb-110b-40ed-ad6f-28d4a2da2e99";
        :>> title = "Sprint 724: dcRecorderReportAccountsForEveryOwedRecord, the correction for issue568 - sprint 723's first recorder ran no record command, returned a three-line report reading DISCREPANCIES: NONE, and check_report.py passed it because its five refusals read only the WROTE lines present. The check now refuses a report that accounts for nothing, and under --owed N one that accounts for fewer records than the dispatch named (D0492, held for the human). (2 pts)";
        :>> createdAt = "2026-09-15"; :>> createdBy = "claudeFable5"; :>> kind = WorkKind::code; :>> priority = WorkPriority::p0; :>> owner = "claudeFable5"; :>> estimatedPoints = 2;
    }

    action def DeliveryRunS724 {
        action storyRecorderReportAccountsForEveryOwedRecord;
        verification storyRecorderReportAccountsForEveryOwedRecordDoD : Test { :>> id = "4ec9e24c-f7cc-49a6-93ee-8529b9c76bd7"; :>> method = VerificationMethod::test; :>> procedureText = "DELIVERED BACKLOG ITEMS: dcRecorderReportAccountsForEveryOwedRecord. DONE MEANS: .engine/skills/delegated-ceremony/references/check_report.py takes --owed N and refuses a report whose WROTE: plus REFUSED: lines number fewer than N, naming the shortfall (owed 7, accounted 6); with or without --owed it refuses a report with zero WROTE: lines and no REFUSED: line. PAIRS carries the owed count per fixture; three sprint 723 fixtures join (the first report as returned, refused; the second recorder's seven writes under --owed 7, passes; six of seven under --owed 7, refused). The recorder brief in SKILL.md passes --owed <COUNT> and states rule 6; process steps dcyDispatchRecorder and dcyRecorderReport name the count and the two refusals. D0492 (process-change, proposed) is co-committed. .claude regenerated by sync-claude. Resolves issue568. VERIFIED BY: python check_report.py --probe --root . prints probe: every pair holds (eight pairs); the checker before the change passed sprint 723's first report (exit 0), after it refuses it (exit 1); keel gate check-engine clean; sync-claude --check clean; the verify ladder green."; }
        // RAN: VERIFIER RECEIPT 2026-09-15 12:43:55 head=ebac62f tree=19 dirty paths
        part storyRecorderReportAccountsForEveryOwedRecordDoDR1 : TestResult { :>> id = "9bf5c6bb-50a6-44c1-b8ce-7907117e9c88"; :>> outcome = VerdictKind::pass; :>> judgedAgainst = "ebac62f"; :>> judgedAt = "2026-09-15"; :>> judgedBy = "claudeFable5"; }
    }

    verification recorderReportAccountsForEveryOwedRecordRefineGate : Test { :>> id = "cd4c377c-32d8-40ac-a96e-62eba08667c0"; :>> title = "Sprint 724 refine gate (DoR)"; :>> createdAt = "2026-09-15"; :>> createdBy = "claudeFable5"; :>> method = VerificationMethod::inspect; :>> procedureText = "Chartered by D0492 (proposed; the process-change is held for the human, the co-committed Decision is the keystone's authorisation). One backlog item, ranked first on the frontier by the sprint 723 retro. 2 points: a Python checker change with fixtures, a brief, a process step, a Decision."; }
    // RAN: VERIFIER RECEIPT 2026-09-15 12:43:55: validate=pass
    part recorderReportAccountsForEveryOwedRecordRefineGateR1 : TestResult { :>> id = "36af8d09-5d32-426b-8649-c37eb8b4f3a6"; :>> outcome = VerdictKind::proposed; :>> judgedAgainst = "ebac62f"; :>> judgedAt = "2026-09-15"; :>> judgedBy = "claudeFable5"; }
    verification recorderReportAccountsForEveryOwedRecordStandupGate : Test { :>> id = "b7e5750f-853f-4641-8a12-4df20d904e24"; :>> title = "Sprint 724 standup gate"; :>> createdAt = "2026-09-15"; :>> createdBy = "claudeFable5"; :>> method = VerificationMethod::inspect; :>> procedureText = "Owner claudeFable5. Blocker: none - the checker is pure Python read by path, no rebuild is needed for the recorder to run it. The D0388 pair is stated before the tree is read: known-positive fixtures/positive-sprint723-nothing-written.txt is refused naming zero WROTE: lines; known-negative fixtures/negative-sprint723-seven-owed.txt under --owed 7 passes."; }
    // RAN: VERIFIER RECEIPT: guard=pass
    part recorderReportAccountsForEveryOwedRecordStandupGateR1 : TestResult { :>> id = "ab7bf7b0-67d1-4b2c-abc2-2acbabffdcf3"; :>> outcome = VerdictKind::proposed; :>> judgedAgainst = "ebac62f"; :>> judgedAt = "2026-09-15"; :>> judgedBy = "claudeFable5"; }
    verification recorderReportAccountsForEveryOwedRecordImplementGate : Test { :>> id = "0f9d1a0b-ab20-4c61-8401-8c552ed58aa0"; :>> title = "Sprint 724 implement gate"; :>> createdAt = "2026-09-15"; :>> createdBy = "claudeFable5"; :>> method = VerificationMethod::test; :>> procedureText = "check_report.py: refusals 6 (nothing accounted) and 7 (shortfall under --owed N); REFUSED_LINE pattern; PAIRS rows carry an owed count; main parses --owed; the pass line names the owed count when given. Three fixtures under references/fixtures. SKILL.md recorder brief: rule 6 and --owed <COUNT> on the check command, with the note that the count is the control. delegated-ceremony.sysml: dcyDispatchRecorder names the count, dcyRecorderReport names both refusals. D0492 recorded via record decision --from, held under D0337."; }
    // RAN: VERIFIER RECEIPT: clippy=pass
    part recorderReportAccountsForEveryOwedRecordImplementGateR1 : TestResult { :>> id = "fc63d934-7566-4c30-99ba-70d41d1351ce"; :>> outcome = VerdictKind::pass; :>> judgedAgainst = "ebac62f"; :>> judgedAt = "2026-09-15"; :>> judgedBy = "claudeFable5"; }
    verification recorderReportAccountsForEveryOwedRecordReviewGate : Test { :>> id = "415294a0-87ff-4819-ae09-9d9fd84ab55d"; :>> title = "Sprint 724 review gate — three passes per D0172"; :>> createdAt = "2026-09-15"; :>> createdBy = "claudeFable5"; :>> method = VerificationMethod::inspect; :>> procedureText = "Verifier receipt only: keel gate validate, check-engine, guard --no-receipt, sync-claude --check, the verify ladder, the probe pair. The recorder for this sprint is dispatched with --owed 7 - the sprint's own control on its own ceremony."; }
    // RAN: VERIFIER RECEIPT: probe=pass
    part recorderReportAccountsForEveryOwedRecordReviewGateR1 : TestResult { :>> id = "4bac6ce9-c140-402a-ab18-a2e4ba149d2c"; :>> outcome = VerdictKind::proposed; :>> judgedAgainst = "ebac62f"; :>> judgedAt = "2026-09-15"; :>> judgedBy = "claudeFable5"; }
    verification recorderReportAccountsForEveryOwedRecordCloseOutGate : Test { :>> id = "98809880-88c6-46ac-948f-f8c4e8efc7b2"; :>> title = "Sprint 724 closeOut gate (autonomous, D0049)"; :>> createdAt = "2026-09-15"; :>> createdBy = "claudeFable5"; :>> method = VerificationMethod::inspect; :>> procedureText = "Landed when the verifier's receipt reads DISCREPANCIES: NONE, the recorder's report passes check_report.py --owed 7, and keel show verification . --pending shows the seven results on the tree."; }
    // RAN: VERIFIER RECEIPT: touched=pass
    part recorderReportAccountsForEveryOwedRecordCloseOutGateR1 : TestResult { :>> id = "80ecdfa7-cb12-4773-a053-a1d6fd292deb"; :>> outcome = VerdictKind::proposed; :>> judgedAgainst = "ebac62f"; :>> judgedAt = "2026-09-15"; :>> judgedBy = "claudeFable5"; }
    verification recorderReportAccountsForEveryOwedRecordRetroGate : Test { :>> id = "d9098d49-1486-441b-a071-59de7ed89589"; :>> title = "Sprint 724 retro gate (autonomous, D0049)"; :>> createdAt = "2026-09-15"; :>> createdBy = "claudeFable5"; :>> method = VerificationMethod::analyze; :>> procedureText = "Avoidable issues scanned (issue011): the finding this sprint corrects (issue568) was found by reading the sprint file, not by any control - the D0473 checker had no notion of what was owed. The correction puts the count in the checker's hands. One residual, already tracked: a dispatch that states a wrong count is still a reminder-class fault; the count comes from the primary's list, and no control reads that list against the sprint file's gate set (dcSprintCeremonyIsOneWrite is the item that would make the owed set computed from the record rather than typed by the primary). Two findings from this sprint's own ceremony, both tracked (D0131): the second verifier launched the ladder twice two seconds apart and nothing refused the second launch - the two touched runs collided on the receipt rename and on the lib tests' fixed temp dirs and the receipt reported five reds no single run produces (58/58 pass alone); recorded as issue569 (High, resolver dcTouchedRunIsExclusive: the running stub carries a pid and a second launch is refused naming it) and issue570 (Medium, resolver dcUnitTestScratchIsPerProcess: one per-process scratch helper and a census test over every src tree), both ranked directly after this item on the frontier. The third verifier's ladder was green at touched, and its receipt is the one the seven records cite."; }
    // RAN: VERIFIER RECEIPT: first red line: none
    part recorderReportAccountsForEveryOwedRecordRetroGateR1 : TestResult { :>> id = "bb26fd86-e792-49e4-84f1-f07e176f5422"; :>> outcome = VerdictKind::proposed; :>> judgedAgainst = "ebac62f"; :>> judgedAt = "2026-09-15"; :>> judgedBy = "claudeFable5"; }
}
