// ProjectDeliveryS732 — Sprint 732: the third D0479 extraction - dcViewIsAMember. The view layer (view/ and its ten submodules: census, checks, control_structure, critique, delta, flow, knowledge, reports, staleness, stpa_diagram), govern, pm, arch and the control-proof census become member keel-view, depending on keel-model, keel-write and the leaves and on nothing above. Three facts the views read from above descend first so the boundary can be drawn without a cycle: the enforced guard-name list (GUARD_NAMES) becomes keel-schema::guard_names on the enforcement-surface lock, the workspace-member reader joins keel-model::corpus, and the plugin directory joins keel-schema::embedded; the burndown takes its guard-receipt and proposed-result readings from keel-cli's reports instead of reaching up for them. keel-cli re-exports every module at its old path and the CLI surface is byte-identical. EXECUTE. 5 pts.. EXECUTE. 5 pts.
package ProjectDeliveryS732 {
    private import EngineElement::*;
    private import EngineWork::*;
    private import EngineVerification::*;
    private import EngineRelationships::*;

    #CharteredBy dependency from viewIsAMemberStory to d0479;

    part viewIsAMemberStory : Story {
        :>> id = "f74354bc-701a-469f-a670-563d2c2436f7";
        :>> title = "Sprint 732: the third D0479 extraction - dcViewIsAMember. The view layer (view/ and its ten submodules: census, checks, control_structure, critique, delta, flow, knowledge, reports, staleness, stpa_diagram), govern, pm, arch and the control-proof census become member keel-view, depending on keel-model, keel-write and the leaves and on nothing above. Three facts the views read from above descend first so the boundary can be drawn without a cycle: the enforced guard-name list (GUARD_NAMES) becomes keel-schema::guard_names on the enforcement-surface lock, the workspace-member reader joins keel-model::corpus, and the plugin directory joins keel-schema::embedded; the burndown takes its guard-receipt and proposed-result readings from keel-cli's reports instead of reaching up for them. keel-cli re-exports every module at its old path and the CLI surface is byte-identical. EXECUTE. 5 pts. (5 pts)";
        :>> createdAt = "2026-09-17"; :>> createdBy = "claudeFable5"; :>> kind = WorkKind::code; :>> priority = WorkPriority::p0; :>> owner = "claudeFable5"; :>> estimatedPoints = 5;
    }

    action def DeliveryRunS732 {
        action storyViewIsAMember;
        verification storyViewIsAMemberDoD : Test { :>> id = "06d7388a-e585-4d76-9654-6c556f62f19c"; :>> method = VerificationMethod::test; :>> procedureText = "DELIVERED BACKLOG ITEMS: dcViewIsAMember. DONE MEANS: members/keel-view exists holding view/ (mod plus census, checks, control_structure, critique, delta, flow, knowledge, reports, staleness, stpa_diagram), govern, pm, arch and control_proof; its Cargo.toml names keel-model, keel-write and the leaves and no crate above them, and python scripts/modgraph.py --check holds; keel-cli/src/lib.rs re-exports view, govern, pm, arch and control_proof at their old paths so no caller outside the members changed except imports; GUARD_NAMES is declared in members/keel-schema/src/guard_names.rs, re-exported by guards.rs, and that file is in GUARD_SOURCE_FILES so removing a name is a locked edit like adding an arm; every script that read the list (guard_dispatch_order.py, issue400_reproduction.py, guard_proof_census.py, facts.py) resolves module_home('guard_names'); module_home's anchor scan catches a nested keel-cli/src path (issue579: the two facts.py knowledge.rs anchors it missed, and the control_structure.rs anchor the widened scan then found) and those anchors resolve through module_home - this story resolves issue579. Known-positive, chosen before the tree is read: cargo build --verbose after an edit to keel-cli/src/serve.rs or guards.rs reports keel-view Fresh; after an edit to members/keel-view/src/view/reports.rs it rebuilds keel-view and keel-cli only. Known-negative: the full touched set passes; keel --help is byte-identical to the pre-move render; no crate:: reference in keel-view names a module outside it or keel-model/keel-write/the leaves (the release build under deny(warnings) plus modgraph); keel version's guards line is unchanged at 75."; }
        // RAN: RAN: verify . --probe-from pair732.txt: outcome=pass stopped_at=none; validate=pass guard=pass clippy=pass probe=pass touched=pass; first red line: none. TOUCHED RECEIPT: outcome=pass passed=904 failed=0; stems=[arch, census, checks, claude_surface, control_proof, control_structure, corpus, critique, delta, embedded, flow, govern, guard_names, guards, init, knowledge, pm, reports, staleness, stpa_diagram, touched, view]. PROBE PAIR: python scripts/module_home.py view/knowledge guard_names view/control_structure (pass); python neg732.py (pass). gate check-engine: .engine instance files validated clean; sync-claude --check: claude-surface matches this binary's generator (47 registry skill(s)). Primary's own reads before dispatch: keel --help byte-identical to the 397e49c render (cmp); keel version guards: 75; cargo clippy --release --workspace --all-targets -D warnings clean; python scripts/module_home.py --probe: 0 failure(s).
        part storyViewIsAMemberDoDR1 : TestResult { :>> id = "a70f7c6c-263f-4844-a433-cad223222c17"; :>> outcome = VerdictKind::pass; :>> judgedAgainst = "397e49c"; :>> judgedAt = "2026-09-16"; :>> judgedBy = "claudeFable5"; }
    }

    verification viewIsAMemberRefineGate : Test { :>> id = "2c308bbd-4a3d-4c02-a018-4bb3f93208d1"; :>> title = "Sprint 732 refine gate (DoR)"; :>> createdAt = "2026-09-17"; :>> createdBy = "claudeFable5"; :>> method = VerificationMethod::inspect; :>> procedureText = "DoR: dcViewIsAMember is the first line of keel show whats-next at 397e49c; chartered by D0479 (accepted) through its #CharteredBy edge (backlog.sysml); sized 5 - one new member of fourteen files (16,003 lines), three small descents (guard names to keel-schema, workspace_members to keel-model, PLUGIN_DIR to keel-schema), one signature inversion (burndown extras), the re-export layer, the Python anchors and the registry path. Blocking dependencies: none - sprint 717 broke view/orient and sprint 718 cut Model and the queries out of view/mod.rs, so what remains above the view is guards (through control_proof's census) and the receipt/attestation reads the burndown makes, both handled by the descents named in the purpose. The DoD's own text says nine submodules; the tree has ten (delta joined after the DoD was written) - the retro records the miscount, the DoD is not edited (D0307)."; }
    // RAN: VERIFIER RECEIPT 2026-09-16 head=397e49c LADDER: KEEL verify . --probe-from pair732.txt -> outcome=pass validate=pass guard=pass clippy=pass probe=pass touched=pass first red line: none All verification stages passed.
    part viewIsAMemberRefineGateR1 : TestResult { :>> id = "824930f8-3bb4-4c89-a655-d37d5d819a08"; :>> outcome = VerdictKind::proposed; :>> judgedAgainst = "397e49c"; :>> judgedAt = "2026-09-16"; :>> judgedBy = "claudeFable5"; }
    verification viewIsAMemberStandupGate : Test { :>> id = "89894272-110d-4a50-bfe9-cf14e1ce3d9b"; :>> title = "Sprint 732 standup gate"; :>> createdAt = "2026-09-17"; :>> createdBy = "claudeFable5"; :>> method = VerificationMethod::inspect; :>> procedureText = "Owner claudeFable5. Blocker: none - brief 38 landed in 397e49c (CI success), no ladder or land is running. Order: (1) members/keel-schema/src/guard_names.rs holds GUARD_NAMES; guards.rs re-exports it; GUARD_SOURCE_FILES gains the path; the marked Decision for the locked edit is recorded and held. (2) workspace_members into keel-model::corpus, touched.rs re-exports it; PLUGIN_DIR into keel-schema::embedded, claude_surface.rs re-exports it. (3) burndown_summary_json takes a BurndownExtras (guard_warnings Json, proposed_results count) computed in keel-cli/src/reports.rs, where actionable_guard_warnings moves. (4) members/keel-view Cargo.toml and lib.rs; git mv view/, govern.rs, pm.rs, arch.rs, control_proof.rs; rewrite crate:: paths per the module map; keel-cli lib.rs re-exports. (5) cargo build --release, clippy all targets, modgraph, keel --help cmp, the two Fresh probes. (6) Python: module_home('guard_names') in four scripts, the anchor scan widened with a probe case, facts.py knowledge.rs anchors resolved, module_home.py docstring. (7) code-registry: ceViewCore's path edited (mine), ceArchViews superseded by a member element; stpa-diagram process and skill name the renderer's member home under the same held Decision; sync-claude. (8) the retro filled BEFORE the verifier is dispatched (sprint 731's order); then verify with the D0500 pair file, recorder --owed 8, land, CI conclusion."; }
    // RAN: VERIFIER RECEIPT 2026-09-16 head=397e49c LADDER: KEEL verify . --probe-from pair732.txt -> outcome=pass validate=pass guard=pass clippy=pass probe=pass touched=pass first red line: none All verification stages passed.
    part viewIsAMemberStandupGateR1 : TestResult { :>> id = "aa8c5be1-d26e-4cc4-a5ca-ca317e227cde"; :>> outcome = VerdictKind::proposed; :>> judgedAgainst = "397e49c"; :>> judgedAt = "2026-09-16"; :>> judgedBy = "claudeFable5"; }
    verification viewIsAMemberImplementGate : Test { :>> id = "8dc3f807-fc38-4d1a-93dd-cd1893b54f82"; :>> title = "Sprint 732 implement gate"; :>> createdAt = "2026-09-17"; :>> createdBy = "claudeFable5"; :>> method = VerificationMethod::test; :>> procedureText = "The implement gate is the DoD's own probes plus the ladder: cargo build --release from the workspace root; cargo build --verbose Fresh reads after touching keel-cli/src/serve.rs and keel-cli/src/guards.rs (keel-view Fresh) and after touching members/keel-view/src/view/reports.rs (keel-view and keel-cli compile, every other member Fresh); keel --help cmp against the pre-move render at 397e49c; keel version guards line unchanged; python scripts/modgraph.py --check exit 0; python scripts/module_home.py --probe exit 0 with the nested-anchor case; cargo clippy --release --all-targets -- -D warnings clean; keel verify . --probe-from pair732.txt (validate, guard, clippy, the pair, suite --touched) green."; }
    // RAN: VERIFIER RECEIPT 2026-09-16 head=397e49c LADDER: KEEL verify . --probe-from pair732.txt -> outcome=pass validate=pass guard=pass clippy=pass probe=pass touched=pass first red line: none All verification stages passed.
    part viewIsAMemberImplementGateR1 : TestResult { :>> id = "48812a83-dd99-4d3d-8921-240068d5c2e8"; :>> outcome = VerdictKind::pass; :>> judgedAgainst = "397e49c"; :>> judgedAt = "2026-09-16"; :>> judgedBy = "claudeFable5"; }
    verification viewIsAMemberReviewGate : Test { :>> id = "023b0f97-00cc-429b-9b60-0899e936a53f"; :>> title = "Sprint 732 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every pub item keel-cli used is reachable at its old path (the release build and all-targets clippy are the proof); the burndown's JSON keys are unchanged with the extras passed in (reports::orient is the one composer). Honesty: GUARD_NAMES leaving guards.rs does not leave the lock - guard_names.rs is in GUARD_SOURCE_FILES and enforcement_surface_covers_every_guard_source still holds; the marked Decision is held for the human, not auto-accepted. Scope: only what the view layer owns moved, plus the three descents it needed; guards, receipt, attestation, workspace stay in keel-cli for dcGuardsAreMembersPerFamily and dcSuiteIsAMember."; }
    // RAN: VERIFIER RECEIPT 2026-09-16 head=397e49c LADDER: KEEL verify . --probe-from pair732.txt -> outcome=pass validate=pass guard=pass clippy=pass probe=pass touched=pass first red line: none All verification stages passed.
    part viewIsAMemberReviewGateR1 : TestResult { :>> id = "041c5957-7f4f-4234-8062-2784f7335cdd"; :>> outcome = VerdictKind::proposed; :>> judgedAgainst = "397e49c"; :>> judgedAt = "2026-09-16"; :>> judgedBy = "claudeFable5"; }
    verification viewIsAMemberCloseOutGate : Test { :>> id = "2e4f1e6f-ff07-4d2a-bc30-9020bee88a7a"; :>> title = "Sprint 732 closeOut gate (autonomous, D0049)"; :>> createdAt = "2026-09-17"; :>> createdBy = "claudeFable5"; :>> method = VerificationMethod::inspect; :>> procedureText = "Landed when the verifier's receipt reads DISCREPANCIES: NONE and its probe rung row names pair732.txt, the recorder's report passes check_report.py --owed 8, git status -sb is clean after keel land and gh run list names the landing commit with conclusion success. The DoD result is recorded against dcViewIsAMemberDoD at that sha; the marked Decision stays proposed until the human's word."; }
    // RAN: VERIFIER RECEIPT 2026-09-16 head=397e49c LADDER: KEEL verify . --probe-from pair732.txt -> outcome=pass validate=pass guard=pass clippy=pass probe=pass touched=pass first red line: none All verification stages passed.
    part viewIsAMemberCloseOutGateR1 : TestResult { :>> id = "873171bc-af37-4b77-b679-e2f6ff549114"; :>> outcome = VerdictKind::proposed; :>> judgedAgainst = "397e49c"; :>> judgedAt = "2026-09-16"; :>> judgedBy = "claudeFable5"; }
    verification viewIsAMemberRetroGate : Test { :>> id = "589d2a3b-5a8e-4b40-a76e-8dd31d8c7a1e"; :>> title = "Sprint 732 retro gate (autonomous, D0049)"; :>> createdAt = "2026-09-17"; :>> createdBy = "claudeFable5"; :>> method = VerificationMethod::analyze; :>> procedureText = "Avoidable issues scanned (issue011). Findings, each a tracked item or the reason it is not. (1) module_home's anchor scan (sprint 719's control for issue559) matched only join(..., 'keel-cli', 'src', 'x.rs') - a nested path (facts.py:1578 and :1725, join(REPO, 'keel-cli', 'src', 'view', 'knowledge.rs')) passed it as none while this sprint moved that very file: an Issue with the widened regex and its probe case as the control, resolved in this sprint. (2) The view/guards cycle survived sprint 717 through control_proof::census reading GUARD_NAMES - the descent to keel-schema is the fix and D0479's layering (a member's dependency list is its declared read set) is what made it visible; no new item for the cycle itself - the release build under deny(warnings) plus keel-view's Cargo.toml is the proof, since Cargo's acyclic crate graph cannot express view reading guards. (3) dcViewIsAMemberDoD says nine submodules and the tree has ten (delta.rs, D0282, landed after the DoD was written); the DoD is a done-adjacent text under D0307 and is left as written, the result quotes the ten; no new item - the count is computed by the member's lib.rs, not by the DoD. (4) A locked-surface edit (guards.rs) inside an extraction sprint needs a marked Decision even though D0479 governs the move - as sprint 718 needed D0486; recorded again here, and dcGuardsAreMembersPerFamily will meet it a third time: not an issue, the lock is doing its work, but its Decision names the pattern so the next sprint copies it rather than rediscovering it. (5) scripts/modgraph.py --check, the D0479 layering rung, reads only keel-cli/src: a module re-exported from a member is a fileless node with no outgoing edges, so after sprints 718 and 732 every forbidden source (view, orient, write, scaffold) is one and the line 'layering holds' cannot fail on what it names - a control that went silent when its subject moved, D0388's class. Tracked as an Issue whose resolver is dcWorkspaceLayeringIsGuarded (D0483, held): the crate-level guard over every member's Cargo.toml is the check that can fail on a member. (6) The widened anchor scan of finding (1) caught a third anchor the DoD had not named (facts.py control_structure.rs): resolved in this sprint, and it is the argument for finding (1)'s control being a probe-carried scan rather than a list of known sites. (7) The sprint 719 control for issue557 fired for the first time on a real move: the verifier's touched run failed no_member_test_anchors_on_a_cwd_relative_path naming three anchors in the moved view code (arch.rs repo_root, view/mod.rs render test and superseded-scope test), and render_dispatches_modes_and_rejects_unknown failed on the same anchor; each repointed to the .git-ancestor lookup sprint 718 used. The control worked as designed - the fix is the same three lines every extraction pays until dcOneRepoRootHelper collapses the helpers; no new item. (8) The second verifier dispatch was red at the probe rung on the pair file's negative side: a python -c one-liner whose quotes the ladder's whitespace split handed to the interpreter as fragments (SyntaxError), a red no check produced - D0500's class through a different door, costing one ladder climb. Tracked as issue581 with resolver dcQuotedProbeLineIsRefused (a quote in a probe line is refused before any rung runs; a check that needs arguments is a script by path)."; }
    // RAN: VERIFIER RECEIPT 2026-09-16 head=397e49c LADDER: KEEL verify . --probe-from pair732.txt -> outcome=pass validate=pass guard=pass clippy=pass probe=pass touched=pass first red line: none All verification stages passed.
    part viewIsAMemberRetroGateR1 : TestResult { :>> id = "b83e64d4-af0a-4b7b-8f24-d11f91af475a"; :>> outcome = VerdictKind::proposed; :>> judgedAgainst = "397e49c"; :>> judgedAt = "2026-09-16"; :>> judgedBy = "claudeFable5"; }
}
