// ProjectDeliveryS706 — Sprint 706: Implement D0474 through dcTouchedReceiptIsContentKeyedPerBinary: the touched receipt records, per test binary, the content it was observed green under - a code key over keel-cli, .engine, .githooks, .claude, Cargo.toml, Cargo.lock and keelw, and a tree key over every tracked and untracked non-ignored path outside .keel plus HEAD - and keel suite --touched and keel land skip a binary whose keys still hold, rerunning only what no green observation covers. The pain: every land ran the full touched set, 7 to 21 minutes, most of it re-proving binaries whose inputs had not changed (the panel in perf-options-panel-2026-09-13). Resolves issue537. Chartered by D0474 (process-change, accepted by the human 2026-09-14). 5 pts.. EXECUTE. 5 pts.
package ProjectDeliveryS706 {
    private import EngineElement::*;
    private import EngineWork::*;
    private import EngineVerification::*;
    private import EngineRelationships::*;

    #CharteredBy dependency from touchedReceiptIsContentKeyedPerBinaryStory to d0474;

    part touchedReceiptIsContentKeyedPerBinaryStory : Story {
        :>> id = "8374d09e-3957-4fd9-8aa9-633aa9d716ac";
        :>> title = "Sprint 706: Implement D0474 through dcTouchedReceiptIsContentKeyedPerBinary: the touched receipt records, per test binary, the content it was observed green under - a code key over keel-cli, .engine, .githooks, .claude, Cargo.toml, Cargo.lock and keelw, and a tree key over every tracked and untracked non-ignored path outside .keel plus HEAD - and keel suite --touched and keel land skip a binary whose keys still hold, rerunning only what no green observation covers. The pain: every land ran the full touched set, 7 to 21 minutes, most of it re-proving binaries whose inputs had not changed (the panel in perf-options-panel-2026-09-13). Resolves issue537. Chartered by D0474 (process-change, accepted by the human 2026-09-14). 5 pts. (5 pts)";
        :>> createdAt = "2026-09-14"; :>> createdBy = "claudeFable5"; :>> kind = WorkKind::code; :>> priority = WorkPriority::p0; :>> owner = "claudeFable5"; :>> estimatedPoints = 5;
    }

    action def DeliveryRunS706 {
        action storyTouchedReceiptIsContentKeyedPerBinary;
        verification storyTouchedReceiptIsContentKeyedPerBinaryDoD : Test { :>> id = "36bfe922-9f16-456e-8ea7-cf9e12afff2f"; :>> method = VerificationMethod::test; :>> procedureText = "DELIVERED: keel-cli/src/contentkey.rs (new: ContentKeys code/tree, is_code, paths from git ls-files -z with untracked non-ignored, hash_file over bytes, a live HEAD read because gitfacts::head_sha memoises per process); keel-cli/src/receipt.rs hashes bytes (the (len, mtime) racy window is gone); keel-cli/src/touched.rs rewritten - self_reading_tests (a test whose text names CARGO_MANIFEST_DIR, and lib always), Observed rows, split (run vs skipped), merge_observed (greens only when the keys held across the run, a red drops its row, observations carried across empty receipts), render_receipt emits self_reading, code_key, tree_key, ran, skipped and [[observed]] tables; suite.rs --touched routes through touched::cmd with --no-receipt / KEEL_NO_RECEIPT=1 forcing every binary; claude_surface.rs PROTECTED_PATHS gains .keel/metrics/; the integration test touched_tests_run_before_land.rs gains a_binary_observed_green_at_this_content_is_skipped_and_a_moved_key_reruns_it. VERIFY: the D0388 pair chosen before the real tree was read - known-positive a repeat run on an unchanged tree executes nothing, known-negative a .tracking edit reruns exactly the self-reading binaries and a keel-cli/src edit reruns all - is that integration test, 27 s, passed; 22 lib tests over contentkey, receipt, touched and the protected surface passed; on the real tree the first run executed 63 binaries in 1246 s and kept 60 observations, the second executed the 3 that had been red (56 s, 12 passed) and skipped 60, the third executed nothing in 1.5 s wall; gate validate 809 clean, check-engine clean, sync-claude --check clean, guard --no-receipt ALL PASS, clippy -D warnings clean."; }
        // RAN: cargo test --release --lib -- contentkey:: receipt:: touched:: claude_surface::tests::protected -> 22 passed; cargo test --release --test touched_tests_run_before_land -> ok 27 s; TOUCHED RECEIPT run 1: KEEL_PERF=1 keel suite --touched . -> outcome=fail passed=792 failed=5 seconds=1246 at=1789366319 head=8b731e6 code_key=3075e7dc4e6bdcbe tree_key=334ce8b08922fb81 observed=60 rows, failing=[control_structure_is_computed, library_read_side, stop_says_nothing_about_decisions] all on perf lines in stdout (issue539); run 2 without the variable: outcome=pass passed=12 seconds=56 over those 3, 60 skipped observed green; run 3: nothing to execute, 63 skipped, 1513 ms wall; clippy clean; gate validate 809 clean; check-engine clean; guard ALL PASS
        part storyTouchedReceiptIsContentKeyedPerBinaryDoDR1 : TestResult { :>> id = "5216fcb3-9ca5-40ce-8e79-19c42ef4240b"; :>> outcome = VerdictKind::pass; :>> judgedAgainst = "8b731e6"; :>> judgedAt = "2026-09-14"; :>> judgedBy = "claudeFable5"; }
    }

    verification touchedReceiptIsContentKeyedPerBinaryRefineGate : Test { :>> id = "8745eeb4-50f4-47b5-84d5-352257b2fae8"; :>> title = "Sprint 706 refine gate (DoR)"; :>> createdAt = "2026-09-14"; :>> createdBy = "claudeFable5"; :>> method = VerificationMethod::inspect; :>> procedureText = "Chartered by D0474, accepted by the human 2026-09-14 with the process-change marker (the receipt's meaning and land's behaviour change). Five points: a new module, a rewritten module, a protected surface, an integration test and a first run over the real tree; the sprint-planning table puts a subsystem with tests at 5. DoR: dcTouchedReceiptIsContentKeyedPerBinary ranks first on keel show whats-next at 8b731e6 (declaration order is priority, D0052); the pair is the DoD's own; issue477 binds - no keel-cli/src or .engine edit while cargo or keel-land runs; the receipt files are a fact surface the runs own, so they join PROTECTED_PATHS in the same change."; }
    // RAN: KEEL show whats-next . -> dcTouchedReceiptIsContentKeyedPerBinary first, then dcNextestIsTheTouchedRunner, dcVerifyLadderStopsAtTheFirstRed; KEEL show authority-queue . -> d0474, d0475, d0476 absent (accepted); grep 0474-*.sysml -> #ProspectiveChange x2, process-change x1
    part touchedReceiptIsContentKeyedPerBinaryRefineGateR1 : TestResult { :>> id = "d69f6a95-70fa-4501-894b-41019d13dd0f"; :>> outcome = VerdictKind::proposed; :>> judgedAgainst = "8b731e6"; :>> judgedAt = "2026-09-14"; :>> judgedBy = "claudeFable5"; }
    verification touchedReceiptIsContentKeyedPerBinaryStandupGate : Test { :>> id = "90d7ed2e-55f7-49f6-be2a-432dea41e352"; :>> title = "Sprint 706 standup gate"; :>> createdAt = "2026-09-14"; :>> createdBy = "claudeFable5"; :>> method = VerificationMethod::inspect; :>> procedureText = "Order: receipt.rs to byte hashing (prior segment); contentkey.rs with its scratch-git-repo unit test; touched.rs rewrite behind the existing Run/Touched shape; suite.rs routing and --help; claude_surface.rs protected surface then keel sync-claude; the integration test extended and run alone; clippy; doc-sync (guards.md, test-verify skill, CLAUDE.md sect.4); gates; the first real-tree run detached; sprint record; one CR: commit carrying D0474, D0475, D0476, the panel knowledge file, issue536-539 and their resolvers; keel-land on the commit; git status -sb and the CI conclusion read back."; }
    // RAN: KEEL gate validate . -> 809 tracking file(s) validated clean.; KEEL gate check-engine . -> .engine instance files validated clean (kernel-free; D0112 phase 2).; KEEL sync-claude --check . -> claude-surface: keel-owned subset matches this binary's generator (47 registry skill(s)); exit=0 each
    part touchedReceiptIsContentKeyedPerBinaryStandupGateR1 : TestResult { :>> id = "19e1fc21-f080-423b-82db-413c96af7dc5"; :>> outcome = VerdictKind::proposed; :>> judgedAgainst = "8b731e6"; :>> judgedAt = "2026-09-14"; :>> judgedBy = "claudeFable5"; }
    verification touchedReceiptIsContentKeyedPerBinaryImplementGate : Test { :>> id = "eb623b44-c372-4dc6-8b48-f7d85bb5ab10"; :>> title = "Sprint 706 implement gate"; :>> createdAt = "2026-09-14"; :>> createdBy = "claudeFable5"; :>> method = VerificationMethod::test; :>> procedureText = "RAN: cargo test --release --lib -- contentkey:: receipt:: touched:: claude_surface::tests::protected -> 22 passed, 0 failed; cargo test --release --test touched_tests_run_before_land -> passed in 27 s including a_binary_observed_green_at_this_content_is_skipped_and_a_moved_key_reruns_it; cargo clippy --release --all-targets -- -D warnings -> clean after four fixes (doc paragraph length x3, write! over format!-push, a redundant clone, an unread collection that became the live HEAD read); keel sync-claude . -> hooks regenerated with the .keel/metrics/ patterns. Two corrections in-sprint: the fixture crate's untracked target/ and Cargo.lock moved both keys under every run so no observation was ever kept - the fixture now ignores what cargo writes, as the real repository does; and the cliSuite/cliLand synopsis amendments were reverted because guard ownership refuses another actor's in-place edit of claudeOpus5's facts and cli-surface-declared leaves no supersede route (issue538)."; }
    // RAN: cargo test --release --lib -- contentkey:: receipt:: touched:: claude_surface::tests::protected -> 22 passed, 0 failed; cargo test --release --test touched_tests_run_before_land -> ok, 27 s, a_binary_observed_green_at_this_content_is_skipped_and_a_moved_key_reruns_it is the D0388 pair (positive: repeat run executes nothing; negative: records.md edit reruns [lib] only, widget.rs edit reruns all); cargo clippy --release --all-targets -- -D warnings -> clean; TOUCHED RECEIPT run 1: KEEL_PERF=1 keel suite --touched . -> outcome=fail passed=792 failed=5 seconds=1246 at=1789366319 head=8b731e6 code_key=3075e7dc4e6bdcbe tree_key=334ce8b08922fb81 observed=60 rows, failing=[control_structure_is_computed, library_read_side, stop_says_nothing_about_decisions] all on perf lines in stdout (issue539); run 2 without the variable: outcome=pass passed=12 seconds=56 over those 3, 60 skipped observed green; run 3: nothing to execute, 63 skipped, 1513 ms wall
    part touchedReceiptIsContentKeyedPerBinaryImplementGateR1 : TestResult { :>> id = "bde7ade6-0d5e-4bfc-b737-72d831cdd168"; :>> outcome = VerdictKind::pass; :>> judgedAgainst = "8b731e6"; :>> judgedAt = "2026-09-14"; :>> judgedBy = "claudeFable5"; }
    verification touchedReceiptIsContentKeyedPerBinaryReviewGate : Test { :>> id = "f05af0b4-2916-43b5-b03a-3ac58e65a791"; :>> title = "Sprint 706 review gate — three passes per D0172"; :>> createdAt = "2026-09-14"; :>> createdBy = "claudeFable5"; :>> method = VerificationMethod::inspect; :>> procedureText = "Three passes (D0172). Correctness: a green is recorded only when contentkey::compute before and after the run are equal (touched.rs run(): held is Some only on equality), so a tree that moved mid-run records nothing and the next run re-executes; a red drops its binary's row (merge_observed removes every ran entry and re-adds only the greens); the skip needs the code key equal and, for a self-reading binary, the tree key too - a .tracking edit alone reruns exactly the self-reading set, shown in the integration test. Honesty: the receipt names ran and skipped apart and the summary says 'skipped, observed green at this content', never 'passed'; --no-receipt and KEEL_NO_RECEIPT=1 run everything; the observation table is inside .keel/metrics/, now a protected surface, so no hand edit produces a skip. Scope: the perf report short-circuits when Model::build was never called, so contentkey:compute's phase is not printed - the overhead is measured as the whole third run instead, 1.5 s wall including the eol census; the synopses of cliSuite and cliLand still do not name the skip (issue538, tracked, not patched)."; }
    // RAN: KEEL gate guard --no-receipt . -> [guard] ALL PASS - 331 actionable warning(s) across 10 guard(s); exit=0. Three passes per D0172 read against touched.rs run() (held only on key equality), merge_observed (ran rows removed, greens re-added only when keys held), split (code key, plus tree key when self_reading)
    part touchedReceiptIsContentKeyedPerBinaryReviewGateR1 : TestResult { :>> id = "5adda1ca-9d54-416f-b36f-c6376fa9667a"; :>> outcome = VerdictKind::proposed; :>> judgedAgainst = "8b731e6"; :>> judgedAt = "2026-09-14"; :>> judgedBy = "claudeFable5"; }
    verification touchedReceiptIsContentKeyedPerBinaryCloseOutGate : Test { :>> id = "3a56e563-ba64-40c3-b047-ee0723f3cb85"; :>> title = "Sprint 706 closeOut gate (autonomous, D0049)"; :>> createdAt = "2026-09-14"; :>> createdBy = "claudeFable5"; :>> method = VerificationMethod::inspect; :>> procedureText = "Closes at the CR: commit that lands contentkey.rs, receipt.rs, touched.rs, suite.rs, claude_surface.rs, the integration test, the regenerated hooks, the doc-sync, D0474-D0476, the panel knowledge file, issue536-539 with resolvers and this record together: keel-land runs the touched set from that commit skipping what the three real-tree runs observed (the code key moves with the commit only if the commit changes a code path - it does not, the tree was already at this content - so the lib and the self-reading binaries rerun for the new HEAD in the tree key and the rest skip); gate validate / check-engine / guard --no-receipt green over that tree; dcTouchedReceiptIsContentKeyedPerBinaryDoD carries a pass with the RAN receipts; issue537 resolves by that pass; the CI conclusion for the landing commit is read back as success; git status -sb shows main level with origin."; }
    // RAN: TOUCHED RECEIPT run 1: KEEL_PERF=1 keel suite --touched . -> outcome=fail passed=792 failed=5 seconds=1246 at=1789366319 head=8b731e6 code_key=3075e7dc4e6bdcbe tree_key=334ce8b08922fb81 observed=60 rows, failing=[control_structure_is_computed, library_read_side, stop_says_nothing_about_decisions] all on perf lines in stdout (issue539); run 2 without the variable: outcome=pass passed=12 seconds=56 over those 3, 60 skipped observed green; run 3: nothing to execute, 63 skipped, 1513 ms wall; the CR: commit and keel-land follow this record; CI conclusion read after the push
    part touchedReceiptIsContentKeyedPerBinaryCloseOutGateR1 : TestResult { :>> id = "f433dd40-f279-47fa-b510-89ab79d8af95"; :>> outcome = VerdictKind::proposed; :>> judgedAgainst = "8b731e6"; :>> judgedAt = "2026-09-14"; :>> judgedBy = "claudeFable5"; }
    verification touchedReceiptIsContentKeyedPerBinaryRetroGate : Test { :>> id = "787fe3f1-d3fc-43f2-80a8-e2e74f31ffd1"; :>> title = "Sprint 706 retro gate (autonomous, D0049)"; :>> createdAt = "2026-09-14"; :>> createdBy = "claudeFable5"; :>> method = VerificationMethod::analyze; :>> procedureText = "Avoidable issues scanned; findings are tracked items, not prose. Finding one: the first real-tree run was red for a reason outside the code - KEEL_PERF=1 in the suite's environment reached every keel the tests spawn, and three binaries that parse JSON or diff output failed on the perf lines; issue539, resolver dcTouchedRunScrubsPerfFromTheChildEnv (scrub the variable from the cargo child, report to stderr). Finding two: the D0108 supersede route does not exist for CliCommand facts because cli-surface-declared compares every authored fact to the mirror; issue538, resolver dcCliFactsOwnedByARetiredActorAreSupersedable (a guard change, so its Decision will be held for the human). Finding three: the fixture failure mode of D0474 is silent - a tree that always moves under cargo never skips and never says why; the integration test asserts a skip so the class is covered, and the real-tree third run (nothing to execute) is the census that the repository's ignores are sufficient today. Closed in-sprint: gitfacts::head_sha memoises per process, which would have keyed a mid-run commit under the old HEAD - contentkey reads HEAD live and its doc says why."; }
    // RAN: Avoidable issues scanned: issue539 (KEEL_PERF leaks into the tests' child keel processes) resolver dcTouchedRunScrubsPerfFromTheChildEnv; issue538 (no supersede route for CliCommand facts) resolver dcCliFactsOwnedByARetiredActorAreSupersedable; the silent never-skip failure mode is covered by the integration test's skip assertion and the real-tree third run; gitfacts::head_sha memoisation closed in-sprint by the live HEAD read in contentkey.rs
    part touchedReceiptIsContentKeyedPerBinaryRetroGateR1 : TestResult { :>> id = "25c4914f-5d45-48be-a196-56de9237a965"; :>> outcome = VerdictKind::proposed; :>> judgedAgainst = "8b731e6"; :>> judgedAt = "2026-09-14"; :>> judgedBy = "claudeFable5"; }
}
