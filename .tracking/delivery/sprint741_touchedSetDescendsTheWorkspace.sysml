// ProjectDeliveryS741 — Sprint 741: the touched set descends the workspace - dcTouchedSetDescendsTheWorkspace, chartered by D0481, resolving issue550 (a keel-parser edit contributed no stem). Before this sprint touched.rs read the changed paths against keel-cli alone: a member edit was attributed to a keel-cli stem by name or to nothing, keel-parser was not a member of anything the set knew, and every self-reading test binary (D0474) was keyed on the whole tree because nothing recorded what it actually read. This sprint the candidate set is computed over the workspace graph read from the Cargo manifests (members/keel-suite/src/wsgraph.rs: the changed path's owning member closed over its dependents, an unowned code path reaching every member, an unowned non-code path reaching nothing), member unit tests are rows named lib:<member> keyed on their own member's scoped code, and a test that reaches the tree only through keel_fs::test_support::{repo_root, repo_path} is a recorder whose key is the hash of the paths it recorded when it last ran (KEEL_READSET_DIR), falling back to the D0474 tree key when no read set exists. Eighteen integration tests under keel-cli/tests are converted from CARGO_MANIFEST_DIR to the helpers, and a keel-suite test (D0047) holds that population there.. EXECUTE. 8 pts.
package ProjectDeliveryS741 {
    private import EngineElement::*;
    private import EngineWork::*;
    private import EngineVerification::*;
    private import EngineRelationships::*;

    #CharteredBy dependency from touchedSetDescendsTheWorkspaceStory to d0481;
    #Delivers dependency from touchedSetDescendsTheWorkspaceStory to dcTouchedSetDescendsTheWorkspace;

    part touchedSetDescendsTheWorkspaceStory : Story {
        :>> id = "78a24bab-afdd-4c9c-a058-847ca7eb48fc";
        :>> title = "Sprint 741: the touched set descends the workspace - dcTouchedSetDescendsTheWorkspace, chartered by D0481, resolving issue550 (a keel-parser edit contributed no stem). Before this sprint touched.rs read the changed paths against keel-cli alone: a member edit was attributed to a keel-cli stem by name or to nothing, keel-parser was not a member of anything the set knew, and every self-reading test binary (D0474) was keyed on the whole tree because nothing recorded what it actually read. This sprint the candidate set is computed over the workspace graph read from the Cargo manifests (members/keel-suite/src/wsgraph.rs: the changed path's owning member closed over its dependents, an unowned code path reaching every member, an unowned non-code path reaching nothing), member unit tests are rows named lib:<member> keyed on their own member's scoped code, and a test that reaches the tree only through keel_fs::test_support::{repo_root, repo_path} is a recorder whose key is the hash of the paths it recorded when it last ran (KEEL_READSET_DIR), falling back to the D0474 tree key when no read set exists. Eighteen integration tests under keel-cli/tests are converted from CARGO_MANIFEST_DIR to the helpers, and a keel-suite test (D0047) holds that population there. (8 pts)";
        :>> createdAt = "2026-09-18"; :>> createdBy = "claudeFable5"; :>> kind = WorkKind::code; :>> priority = WorkPriority::p0; :>> owner = "claudeFable5"; :>> estimatedPoints = 8;
    }

    action def DeliveryRunS741 {
        action storyTouchedSetDescendsTheWorkspace;
        verification storyTouchedSetDescendsTheWorkspaceDoD : Test { :>> id = "0a87909b-6fba-4ac6-994e-83383636f330"; :>> method = VerificationMethod::test; :>> procedureText = "DELIVERED BACKLOG ITEMS: dcTouchedSetDescendsTheWorkspace. DONE MEANS: members/keel-suite/src/wsgraph.rs (259 lines, new) reads the root Cargo.toml's members and each member manifest's path dependencies into a Graph, and candidates(graph, changed) returns the owning members closed over dependents; touched.rs (2056 lines) computes the set from it (run() reads the graph, SetKeys::read carries member_code per member, split keys a member row on its member's scope, a recorder on reads_key from its recorded read set, everything else on D0474's code or tree key), runs member rows as lib:<member> through run_member_libs under the D0475 runner, creates the readset dir under .keel/metrics before the run and removes it after collect_reads, and writes members, self_reading, recorders, reads and reads_key into the receipt's [[observed]] rows; contentkey.rs (302 lines) gains reads_key(repo, listing, reads); members/keel-fs/src/test_support.rs (149 lines) records every repo_root()/repo_path(rel) under KEEL_READSET_DIR as <binary>.reads; suite.rs --help names the member rows, the scope key and the read-set key; CLAUDE.md's D0474 sentence carries the D0481 clause. Eighteen keel-cli/tests binaries read the tree only through the helpers (grep CARGO_MANIFEST_DIR keel-cli/tests = 0 files; 18 files name test_support::), and touched::tests::no_integration_test_reaches_the_tree_past_the_recording_helpers holds that over the whole directory with a synthetic negative for each UNRECORDED_REACH idiom and the child's-cwd non-match. cargo clippy --workspace --release --all-targets clean; cargo test -p keel-suite --release --lib 61 passed; the converted binaries pass (activation_round_trip 4, capability_refusal 9, control_census 1, no_op_writes 7, resync 3, tests_bind 6, touched_tests_run_before_land 5, unknown_flag 4, wrapper 7). Known-positive (pos741.py): wsgraph::tests::a_leaf_edit_reaches_the_leaf_and_its_dependent_and_not_the_third and contentkey::tests::a_read_set_keeps_its_key_across_an_edit_outside_it_and_loses_it_on_one_inside both pass, exactly two run. Known-negative (neg741.py): the two D0474 fallback tests pass narrowed to the fallback case, and a planted keel-cli/tests file reaching env!(CARGO_MANIFEST_DIR) fails the D0047 control naming the file and line, the plant removed on every path. The real land at the landing commit writes the touched receipt with members, recorders and per-row reads/reads_key fields and skips nothing without a matching key - read from .keel/metrics/touched-receipt.toml after the land, not from this text. Read at the pre-land run from a . root after the readset_env fix: 18 of 18 recorders carry reads and reads_key, member rows carry their own scoped code key, skipped = [], 781 passed 0 failed."; }
        // RAN: TOUCHED RECEIPT: outcome=pass passed=669 failed=0 seconds=235
        part storyTouchedSetDescendsTheWorkspaceDoDR1 : TestResult { :>> id = "c494c11f-8b59-4637-89d3-804d0052e96e"; :>> outcome = VerdictKind::pass; :>> judgedAgainst = "d7ffcc82"; :>> judgedAt = "2026-09-18"; :>> judgedBy = "claudeFable5"; }
    }

    verification touchedSetDescendsTheWorkspaceRefineGate : Test { :>> id = "01f0f8d9-a8e4-4d31-b099-2d5349eaaf98"; :>> title = "Sprint 741 refine gate (DoR)"; :>> createdAt = "2026-09-18"; :>> createdBy = "claudeFable5"; :>> method = VerificationMethod::inspect; :>> procedureText = "DoR: dcTouchedSetDescendsTheWorkspace was the third line of keel show whats-next at d7ffcc82 (sprint 740 and the D0513 surfacing landed, CI conclusion success) and the first unheld one: dcSittingReviewIsFinishedByAnalysis is chartered by D0510 and dcTheFourStayingModulesAreMembers by D0513, both held proposed for the human on the published brief (content gate, D0052), so the frontier is followed past them. Chartered by D0481 through its #CharteredBy edge; #Resolves issue550. Sized 8 - one new member module with its graph reader and tests, a rewrite of run()/split/merge in the largest module of keel-suite (2056 lines) with new receipt fields, a recording layer in keel-fs, eighteen integration-test conversions and a population test over them, help and CLAUDE.md doc-sync; no locked path changes and no schema or process change. Not split: the graph, the member key and the recorder key are one claim (the set and its keys descend the workspace) and D0481 states them as one. Blocking dependencies: none."; }
    // RAN: LADDER: keel verify . --probe-from pair741.txt: validate=pass guard=pass clippy=pass probe=pass touched=pass
    part touchedSetDescendsTheWorkspaceRefineGateR1 : TestResult { :>> id = "90174e5e-516a-4d91-bfbe-1cc64fed2e8c"; :>> outcome = VerdictKind::proposed; :>> judgedAgainst = "d7ffcc82"; :>> judgedAt = "2026-09-18"; :>> judgedBy = "claudeFable5"; }
    verification touchedSetDescendsTheWorkspaceStandupGate : Test { :>> id = "8d6f224c-6edc-4143-8a07-45f7a48c3d5f"; :>> title = "Sprint 741 standup gate"; :>> createdAt = "2026-09-18"; :>> createdBy = "claudeFable5"; :>> method = VerificationMethod::inspect; :>> procedureText = "Owner claudeFable5. Blocker: none - d7ffcc82 landed with CI conclusion success, no ladder or land running; the human's serve (pid 14600) runs from the pin cache, so the release image rebuilds freely. Order: (1) wsgraph.rs with its fixture tests and the real-workspace test; (2) contentkey reads_key and test_support recording under KEEL_READSET_DIR; (3) touched.rs: SetKeys per member, split with the recorder closure, run_member_libs, choose_runner, collect_reads, the receipt fields and the round-trip test; (4) convert the eighteen keel-cli/tests binaries to repo_root()/repo_path(rel), grep CARGO_MANIFEST_DIR to zero; (5) the D0047 control test over keel-cli/tests; (6) clippy, cargo build --release, keel-serve.exe refresh, the converted binaries; (7) pos741.py/neg741.py, pair741.txt; (8) the sprint record with the retro filled, verifier with the pair file, recorder --owed 8, the detached commit, git status -sb, CI conclusion, then the landed receipt's members/recorders/reads_key fields read back. decision-surfacing: no Decision is recorded this sprint, the pending set (sixteen ids) equals the page, silent."; }
    // RAN: LADDER: keel verify . --probe-from pair741.txt: validate=pass guard=pass clippy=pass probe=pass touched=pass
    part touchedSetDescendsTheWorkspaceStandupGateR1 : TestResult { :>> id = "52e7aab3-2566-425b-ba9c-9f6209a3adff"; :>> outcome = VerdictKind::proposed; :>> judgedAgainst = "d7ffcc82"; :>> judgedAt = "2026-09-18"; :>> judgedBy = "claudeFable5"; }
    verification touchedSetDescendsTheWorkspaceImplementGate : Test { :>> id = "d8706e38-d8a2-492b-8afd-722765a4587b"; :>> title = "Sprint 741 implement gate"; :>> createdAt = "2026-09-18"; :>> createdBy = "claudeFable5"; :>> method = VerificationMethod::test; :>> procedureText = "The implement gate is the DoD's own probes plus the ladder: cargo clippy --workspace --release --all-targets clean after missing_const_for_fn (nothing_to_run -> pub const fn), too_many_lines on run() twice (member-row attribution moved into run_member_libs as MemberLibs.failing, choose_runner extracted), redundant_clone and cloned_ref_to_slice_refs (std::slice::from_ref); cargo build --release Finished and target/release/keel-serve.exe refreshed from it; cargo test -p keel-suite --release --lib 61 passed 0 failed; the converted integration binaries pass (activation_round_trip_loses_nothing 4, capability_refusal_bites 9, control_census_names_friction 1, no_op_writes_lose_nothing 7, resync_is_not_a_self_modification 3, tests_bind_to_properties 6, touched_tests_run_before_land 5, unknown_flag_is_refused 4, wrapper_resolves_only_the_pin 7); grep -rl CARGO_MANIFEST_DIR keel-cli/tests = 0 files, 18 files name test_support::; python pos741.py pass (exit 0, test result: ok. 2 passed); python neg741.py pass (fallback narrowed 2 passed; planted reach exit 101 naming zz_probe741_unrecorded_reach.rs:3 CARGO_MANIFEST_DIR, plant removed); keel gate guard --no-receipt ALL PASS; keel gate check-engine clean; keel sync-claude --check matches (47 registry skills); gh run list for d7ffcc82 conclusion success. Three tests were corrected against their own fixtures before they passed: the round-trip test counted reads_key twice because the receipt header names the field (now matched as a line), the recorder-key test's set was unsorted while split sorts, and a nextest member-row assertion borrowed a temporary."; }
    // RAN: LADDER: keel verify . --probe-from pair741.txt: validate=pass guard=pass clippy=pass probe=pass touched=pass
    part touchedSetDescendsTheWorkspaceImplementGateR1 : TestResult { :>> id = "33fef7bc-1fee-4f02-b14f-af708d7844af"; :>> outcome = VerdictKind::pass; :>> judgedAgainst = "d7ffcc82"; :>> judgedAt = "2026-09-18"; :>> judgedBy = "claudeFable5"; }
    verification touchedSetDescendsTheWorkspaceReviewGate : Test { :>> id = "5ba10515-82a8-4903-a6a1-484c68dbbdd9"; :>> title = "Sprint 741 review gate — three passes per D0172"; :>> createdAt = "2026-09-18"; :>> createdBy = "claudeFable5"; :>> method = VerificationMethod::inspect; :>> procedureText = "Verifier receipt only: keel gate validate, check-engine, guard --no-receipt, sync-claude --check, the verify ladder with --probe-from naming pair741.txt (D0500), cargo clippy; the recorder writes this gate from the receipt. Three passes per D0172. Correctness: the candidate set is the owning member closed over dependents (a_leaf_edit_reaches_the_leaf_and_its_dependent_and_not_the_third), an unowned code path reaches every member and an unowned non-code path none, the real workspace graph has one Member per listed dir with keel-cli depending on keel-suite and keel-parser, and a member row is judged at its own member's scoped code (a_member_row_is_judged_at_its_own_members_code); a recorder is judged at the paths it read (a_recorder_is_judged_at_the_paths_it_read) and one that reaches the tree any other way is not a recorder (a_recorder_reaches_the_tree_only_through_the_support_layer, with the child's-cwd case that is NOT a reach). Honesty: the negative plants a real file under keel-cli/tests and asserts the control fails naming its path and line, not that some test fails; the positive runs exactly two named tests and asserts the count; the fixture workspace in touched_tests_run_before_land.rs has no root Cargo.toml, so its five tests exercise the fallback path only - the graph path's end-to-end evidence is the landed receipt's members and recorders fields, read at closeOut. Scope: no locked path is in the diff (no path under GUARD_SOURCE_FILES/GUARD_SOURCE_DIRS, no .githooks, CI yml, schema or process file), so no Decision is recorded and none is owed - NOT A PROCESS CHANGE: the land runs the same rungs; what changes is which binaries the touched rung selects and the key it skips them at, both authored by D0481 which is accepted."; }
    // RAN: LADDER: keel verify . --probe-from pair741.txt: validate=pass guard=pass clippy=pass probe=pass touched=pass
    part touchedSetDescendsTheWorkspaceReviewGateR1 : TestResult { :>> id = "b172dc78-31eb-4be4-a947-362acdc0fa6e"; :>> outcome = VerdictKind::proposed; :>> judgedAgainst = "d7ffcc82"; :>> judgedAt = "2026-09-18"; :>> judgedBy = "claudeFable5"; }
    verification touchedSetDescendsTheWorkspaceCloseOutGate : Test { :>> id = "b0bc2a60-1dc4-4010-b286-851d854dd37c"; :>> title = "Sprint 741 closeOut gate (autonomous, D0049)"; :>> createdAt = "2026-09-18"; :>> createdBy = "claudeFable5"; :>> method = VerificationMethod::inspect; :>> procedureText = "Landed when the verifier's receipt reads DISCREPANCIES: NONE and its probe rung row names pair741.txt, the recorder's report passes check_report.py --owed 8, git status -sb is clean after keel land and gh run list names the landing commit with conclusion success. The DoD result is recorded against dcTouchedSetDescendsTheWorkspaceDoD at that sha; issue550's resolution is computed from its #Resolves edge once that result lands. The landed receipt (.keel/metrics/touched-receipt.toml) is read back for the DoD's last clause: its header names members and recorders, its [[observed]] rows for the eighteen converted binaries carry reads and reads_key, and no row of the set is skipped without a matching key. No Decision recorded, the authority queue's pending set is unchanged and decision-surfacing is silent. dcSuiteMeasuresTheWorkspace (issue588: the full suite's fingerprint population and cargo scope stop at keel-cli) is the next line of the frontier below the two held items and builds on wsgraph.rs."; }
    // RAN: LADDER: keel verify . --probe-from pair741.txt: validate=pass guard=pass clippy=pass probe=pass touched=pass
    part touchedSetDescendsTheWorkspaceCloseOutGateR1 : TestResult { :>> id = "b1855805-95d2-4a9a-a1e8-3cd175910716"; :>> outcome = VerdictKind::proposed; :>> judgedAgainst = "d7ffcc82"; :>> judgedAt = "2026-09-18"; :>> judgedBy = "claudeFable5"; }
    verification touchedSetDescendsTheWorkspaceRetroGate : Test { :>> id = "36ad9a26-6ddf-4679-8396-391f2b060fc7"; :>> title = "Sprint 741 retro gate (autonomous, D0049)"; :>> createdAt = "2026-09-18"; :>> createdBy = "claudeFable5"; :>> method = VerificationMethod::analyze; :>> procedureText = "Written at close-out, before the verifier is dispatched; avoidable issues scanned (issue011), each finding a tracked item or the reason it is not. (1) UNRECORDED_REACH was first written with the idiom current_dir( - which every integration test carries as Command::current_dir(dir), the CHILD's cwd, not a read of ours - and would have disqualified nearly every converted binary from the recorder key, silently keying them on the whole tree: green, and the whole re-run D0481 exists to remove. Caught by reading the converted sources against the marker before the receipt was written, not by a test. Corrected to current_dir() and the near-miss is now a case in two tests (childs_cwd in a_recorder_reaches_the_tree_only_through_the_support_layer; the Command line in the control's synthetic). No new item: the class - a marker string that matches a neighbouring idiom - has its control in the pair the marker's test now carries, and the DoD's closing clause (no row skipped without a matching key, read from the landed receipt) is where a recurrence shows as a count of recorders that is not eighteen. (2) The CLAUDE.md line never CARGO_MANIFEST_DIR/.. in an integration test was written before any test held it - a reminder (D0047), the shape this repo's own rules forbid. Caught in-sprint; the control no_integration_test_reaches_the_tree_past_the_recording_helpers was added in the same working tree before the commit, over the population test_bearing_sources marks always_test. No new item: the sentence and its control land in one commit; a predicate over which CLAUDE.md sentences are prohibitions and what counts as their control has no defensible boundary (D0088), so the class stays with the review pass's Scope question. (3) The integration fixture in touched_tests_run_before_land.rs has no root Cargo.toml, so the graph path is exercised by wsgraph's fixture and real-workspace tests and by the land itself, not by the fixture that names the land. No new item: adding a manifest tree to that fixture is the next slice's (dcSuiteMeasuresTheWorkspace) own DoD material, since the suite's scope and the touched set's would then read one fixture; noted so it is asked for there. (4) The population floor in the control was typed as nineteen and the tree holds eighteen - the test failed on my own count, not on an offender, and the count was corrected from the failure. Non-finding: the floor is a lower bound so the population cannot silently shrink to zero; the exact count is read from the tree by the DoD's grep. (5) The pre-bash hook denied a python heredoc carrying a backslash inside a print (D0309/issue372 class) and the analysis was written as a scratchpad script instead. Non-finding: the control fired as designed. (6) No Decision was recorded this sprint and none was owed: D0481 states the whole change and is accepted. Non-finding, noted because the review gate's Scope pass says why. (7) The first verifier's touched run (780 passed, DISCREPANCIES: NONE) landed all eighteen recorders WITHOUT a reads_key: the readset directory was joined from the . root the ladder was launched with and handed relative to test processes nextest starts in keel-cli/, so every recorder resolved it under the package, the helper (silent by design) wrote nothing, and each row fell back to the tree key - green, and exactly the whole-tree re-run D0481 exists to remove. Found by reading the receipt back against the DoD's last clause (grep reads_key = 0 of 91 rows) before the recorder was dispatched, not by any test; the cause was confirmed by a probe (one recorder under nextest with an absolute dir wrote its .reads file, with a relative dir wrote nothing) before the fix. Corrected at the site the path leaves the process: capture hands readset_env(readset), an absolutized path, and the_readset_directory_reaches_the_test_processes_absolute is the control (D0047); the second run from a . root landed 18 of 18 with reads_key. No new item: the control is in this commit and the DoD's read-back clause now states the count it found; the class - a fact silently degrading to its fallback with no red - is what issue550's own resolver was, and the receipt's per-row reads_key is the surface a reader checks. The issue570 scratch-name control fired on this test's first negative (a fixed temp_dir name) and the case was rewritten over a synthetic absolute path - non-finding, the control fired as designed."; }
    // RAN: LADDER: keel verify . --probe-from pair741.txt: validate=pass guard=pass clippy=pass probe=pass touched=pass
    part touchedSetDescendsTheWorkspaceRetroGateR1 : TestResult { :>> id = "651e930b-a6aa-4968-83fd-90c6a558194c"; :>> outcome = VerdictKind::proposed; :>> judgedAgainst = "d7ffcc82"; :>> judgedAt = "2026-09-18"; :>> judgedBy = "claudeFable5"; }
}
