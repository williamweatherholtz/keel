// ProjectDeliveryS718 — Sprint 718: the second D0479 extraction - dcModelAndWriteAreMembers. The read model (corpus, ident, textscan, gitfacts, indexer, done, binding, evidence, fingerprint, model, queries, claims, suspect, algo, activation, orient) becomes member keel-model and the write API (write, scaffold, reverify, claim, intake_write) becomes member keel-write, with keel-fs holding the one atomic-write primitive both sides share. Model, the item queries and the claim read side leave view/mod.rs and claim.rs for keel-model so the two members depend only downward; keel-cli re-exports every module at its old path and the CLI surface is byte-identical. EXECUTE. 5 pts.
package ProjectDeliveryS718 {
    private import EngineElement::*;
    private import EngineWork::*;
    private import EngineVerification::*;
    private import EngineRelationships::*;

    #CharteredBy dependency from modelAndWriteAreMembersStory to d0479;

    part modelAndWriteAreMembersStory : Story {
        :>> id = "c70f9278-498b-4827-bc1e-233097e1e771";
        :>> title = "Sprint 718: the second D0479 extraction - dcModelAndWriteAreMembers. The read model (corpus, ident, textscan, gitfacts, indexer, done, binding, evidence, fingerprint, model, queries, claims, suspect, algo, activation, orient) becomes member keel-model and the write API (write, scaffold, reverify, claim, intake_write) becomes member keel-write, with keel-fs holding the one atomic-write primitive both sides share. Model, the item queries and the claim read side leave view/mod.rs and claim.rs for keel-model so the two members depend only downward; keel-cli re-exports every module at its old path and the CLI surface is byte-identical (5 pts)";
        :>> createdAt = "2026-09-15"; :>> createdBy = "claudeFable5"; :>> kind = WorkKind::code; :>> priority = WorkPriority::p0; :>> owner = "claudeFable5"; :>> estimatedPoints = 5;
    }

    action def DeliveryRunS718 {
        action storyModelAndWriteAreMembers;
        verification storyModelAndWriteAreMembersDoD : Test { :>> id = "978b4b0e-e7ca-4aef-ab93-de2390fce0b4"; :>> method = VerificationMethod::test; :>> procedureText = "DELIVERED BACKLOG ITEMS: dcModelAndWriteAreMembers, dcArchDriftDropsSupersededElements, dcRecordIssueRefusesANonResolverKind. Done means: members/keel-fs, members/keel-model and members/keel-write exist with the modules the DoD names (plus the model, queries and claims types that had to leave view/mod.rs for the read model to be self-contained), keel-write depends on keel-model and the leaves and keel-model on the leaves only; an edit to keel-cli/src/view/mod.rs rebuilds neither member and an edit to members/keel-write/src/write.rs leaves keel-model Fresh (cargo build --verbose, the known-positives); keel --help is byte-identical to the pre-move render, the guard count is unchanged, no crate:: reference in a member names a module outside it, and keel verify is green through the touched set (the known-negatives)"; }
        // RAN: // RAN: the DoD's own probes, run at 0e9f499 and landed unchanged in d110d0a: members/keel-fs, members/keel-model, members/keel-write present with the named modules plus model, queries and claims (Cargo.toml [workspace] members lists all three; cargo metadata dependency direction keel-write -> keel-model -> leaves, keel-model -> leaves only); cargo build --verbose known-positives: an edit to keel-cli/src/view/mod.rs left keel-fs, keel-model and keel-write Fresh (probe-view.log) and an edit to members/keel-write/src/write.rs left keel-model and keel-fs Fresh (probe-write.log); keel --help cmp against the pre-move render IDENTICAL (14593 bytes both); keel version -> guards: 75 (66 hard-blocking, 9 warning-only), unchanged; python scripts/modgraph.py --check -> layering holds (74 modules, 212 edges), exit 0, no crate:: reference in a member names a module outside it; keel verify . --probe 'python scripts/modgraph.py --check,cargo test --release -p keel-cli --lib no_member_test_anchors_on_a_cwd_relative_path' -> pass, every rung green in 626 s, touched 880 passed 0 failed in 596 s under cargo-nextest 0.9.144, receipt .keel/metrics/verify-receipt.toml head 0e9f499. The DoD names no CI condition; the closeOut gate does, and waits on the run at sprint 719's landing (the d110d0a run 34917362100 was red on a script probe outside this DoD, issue559).
        part storyModelAndWriteAreMembersDoDR1 : TestResult { :>> id = "21cece89-929f-40f7-a6aa-eb3bb320bc39"; :>> outcome = VerdictKind::pass; :>> judgedAgainst = "d110d0a"; :>> judgedAt = "2026-09-14"; :>> judgedBy = "claudeFable5"; }
    }

    verification modelAndWriteAreMembersRefineGate : Test { :>> id = "2b26df19-8351-4864-ac55-f1c7c70b89a5"; :>> title = "Sprint 718 refine gate (DoR)"; :>> createdAt = "2026-09-15"; :>> createdBy = "claudeFable5"; :>> method = VerificationMethod::inspect; :>> procedureText = "DoR: the item is the head of the ready frontier (keel show whats-next), chartered by D0479 (accepted) through its #CharteredBy edge, sized 5 (three members, the Model and query surgery out of view/mod.rs, the re-export layer, the registry and manifest paths that move). Blocking dependencies: none - sprint 717 already broke the view/orient cycle, so orient's burndown composition moves up into reports and nothing in the read model reaches back into view or guards"; }
    // RAN: // RAN: keel show whats-next . at 0e9f499 -> dcModelAndWriteAreMembers is the first line; #CharteredBy dependency from dcModelAndWriteAreMembers to d0479 (.tracking/backlog.sysml:3295), D0479 accepted; estimatedPoints 5 on modelAndWriteAreMembersStory; blocking dependency dcGuardsViewOrientCycleIsBroken delivered by sprint 717 (backlog.sysml:3296). DoR holds.
    part modelAndWriteAreMembersRefineGateR1 : TestResult { :>> id = "ddb94df4-ea38-469e-9192-3710ad55d809"; :>> outcome = VerdictKind::proposed; :>> judgedAgainst = "0e9f499"; :>> judgedAt = "2026-09-14"; :>> judgedBy = "claudeFable5"; }
    verification modelAndWriteAreMembersStandupGate : Test { :>> id = "4049942c-dcf4-426a-8c72-1ac476386c1d"; :>> title = "Sprint 718 standup gate"; :>> createdAt = "2026-09-15"; :>> createdBy = "claudeFable5"; :>> method = VerificationMethod::inspect; :>> procedureText = "Order: keel-fs (fsx::write_atomic) first; keel-model's Cargo.toml and lib.rs; git-move the read modules and rewrite their crate:: paths; cut Model, ItemInfo, Edge, ViewError and the model builders out of view/mod.rs into keel-model::model, the item and issue queries into keel-model::queries, the claim read side into keel-model::claims, sync's divergence helpers into gitfacts; keel-write's Cargo.toml and lib.rs; move the write modules; lib.rs re-exports under the old paths; view/mod.rs, sync.rs and claim.rs import what left them; the burndown composition into reports::orient; clippy across all targets clean; the literal paths that name a moved file follow it (deliverable manifest, code registry by superseding element, control structure source, facts.py, indicator-triggers, census probe, post-commit comment); the locked build-skill paragraph under its own marked Decision; then the DoD probes and keel verify"; }
    // RAN: // RAN: order held as planned in the sprint's standup text: keel-fs first (members/keel-fs/src/fsx.rs), keel-model (16 read modules plus model.rs, queries.rs, claims.rs cut out of view/mod.rs and claim.rs), keel-write (write, scaffold, reverify, claim, intake_write), keel-cli/src/lib.rs re-exports every module at its old path; the literal paths that name a moved file followed it (.engine/deliverable-manifest.txt, code-registry by four superseding elements, view/control_structure.rs:150, scripts/exec_brief/facts.py, .engine/contracts/indicator-triggers.toml:30, scripts/probes/receipt_shape_census.py:14, .githooks/post-commit:7); the locked build-skill paragraph rides D0486 (process-change, held). No blocker surfaced.
    part modelAndWriteAreMembersStandupGateR1 : TestResult { :>> id = "94daf933-44a2-40a9-8651-af5c8a1582d4"; :>> outcome = VerdictKind::proposed; :>> judgedAgainst = "0e9f499"; :>> judgedAt = "2026-09-14"; :>> judgedBy = "claudeFable5"; }
    verification modelAndWriteAreMembersImplementGate : Test { :>> id = "3989f435-88e6-456d-876a-1fa673c776ab"; :>> title = "Sprint 718 implement gate"; :>> createdAt = "2026-09-15"; :>> createdBy = "claudeFable5"; :>> method = VerificationMethod::test; :>> procedureText = "The implement gate is the DoD's own probes plus the ladder: cargo build --release from the workspace root; the two known-positive Fresh reads; keel --help cmp against the pre-move render; keel version guards line unchanged; python scripts/modgraph.py --check exit 0; cargo clippy --release --all-targets -- -D warnings clean; keel verify . with the D0388 pair (validate, guard, clippy, pair, suite --touched) green"; }
    // RAN: // RAN: cargo build --release (exit 0, build6.log); cargo build --verbose known-positives: an edit to keel-cli/src/view/mod.rs left keel-fs, keel-model and keel-write Fresh (probe-view.log) and an edit to members/keel-write/src/write.rs left keel-model and keel-fs Fresh (probe-write.log); keel --help cmp against the pre-move render IDENTICAL (14593 bytes both); keel version -> guards: 75 (66 hard-blocking, 9 warning-only), unchanged; python scripts/modgraph.py --check -> layering holds (74 modules, 212 edges), exit 0; cargo clippy --release --all-targets -- -D warnings exit 0 (clippy8.log, workspace-wide); keel verify . --probe 'python scripts/modgraph.py --check,cargo test --release -p keel-cli --lib no_member_test_anchors_on_a_cwd_relative_path' -> pass, every rung green in 626 s, touched 880 passed 0 failed in 596 s under cargo-nextest 0.9.144, receipt .keel/metrics/verify-receipt.toml head 0e9f499.
    part modelAndWriteAreMembersImplementGateR1 : TestResult { :>> id = "6761c7ca-de47-4b1b-9fc5-ec38df787310"; :>> outcome = VerdictKind::pass; :>> judgedAgainst = "0e9f499"; :>> judgedAt = "2026-09-14"; :>> judgedBy = "claudeFable5"; }
    verification modelAndWriteAreMembersReviewGate : Test { :>> id = "222bcb3f-1c17-4fee-a6b4-326367cd7435"; :>> title = "Sprint 718 review gate — three passes per D0172"; :>> createdAt = "2026-09-15"; :>> createdBy = "claudeFable5"; :>> method = VerificationMethod::inspect; :>> procedureText = "Three passes (D0172). Correctness: every pub item the rest of keel-cli used is reachable at its old path (the release build and all-targets clippy are the proof - no caller outside the members changed except imports); the members' pub promotions carry must_use, Errors and Panics docs rather than a blanket allow, and the two lints allowed at each member root name why. Honesty: the superseded code-registry elements no longer report their old path as MISSING drift - arch_model drops a #Supersede target, with a test over this repo's four pairs. pin_skew, which read engine-version.toml from write.rs after the move, is back at lib level where HEAD had it (keel-cli/src/lib.rs:40) - the lock-discipline scan no_public_write_reads_outside_the_lock is what caught it. Scope: view keeps its composition, the guards keep theirs; only what the read model and the write API own moved, plus the sync git helper that gitfacts already wrapped. Control added (D0047): touched.rs test no_member_test_anchors_on_a_cwd_relative_path scans every members/*/src file for the four cwd-relative anchor shapes, probed red by mutation (a Path::new('..') appended to keel-fs/src/lib.rs) and green on the reverted tree"; }
    // RAN: // RAN: Review at 0e9f499, three passes (D0172). Correctness: every pub item keel-cli used is reachable at its old path - the release build and workspace all-targets clippy are the proof; the members' pub promotions carry must_use / Errors / Panics docs, and the two lints allowed at each member root (implicit_hasher, too_long_first_doc_paragraph) name why in lib.rs. pin_skew, moved into write.rs, was flagged by no_public_write_reads_outside_the_lock as a public fn reading outside the lock and is back at lib level (members/keel-write/src/lib.rs:39) where HEAD had it (keel-cli/src/lib.rs:40). Honesty: arch_model drops a #Supersede target so the four superseded registry elements no longer report MISSING drift (view/mod.rs, test a_superseded_element_leaves_the_registry_and_its_successor_stays); issue556 tracks it, resolved by dcArchDriftDropsSupersededElements (its DoD names the test and the drift read). The first triage of issue556 named this Story as resolver; record issue accepted it and the pre-commit guards (issues, resolver-kind) aborted the commit - issue558 tracks that write-time gap, resolved by dcRecordIssueRefusesANonResolverKind: the write now reads the guard's own predicate (guards::resolver_kind_holds), probed by tests/record_issue_refuses_a_non_resolver.rs (Story refused, action and Decision accepted). Scope: view keeps its composition and the guards theirs; only what the read model and write API own moved. Control added (D0047): touched.rs test no_member_test_anchors_on_a_cwd_relative_path over members/*/src, probed red by mutation (Path::new('..') appended to keel-fs/src/lib.rs, FAILED) and green on the reverted tree; issue557 tracks the recurrence, resolved by dcOneRepoRootHelper.
    part modelAndWriteAreMembersReviewGateR1 : TestResult { :>> id = "ab32c386-0073-4165-8da2-e6b1eadd68c6"; :>> outcome = VerdictKind::proposed; :>> judgedAgainst = "0e9f499"; :>> judgedAt = "2026-09-14"; :>> judgedBy = "claudeFable5"; }
    verification modelAndWriteAreMembersCloseOutGate : Test { :>> id = "b9d5c8c4-3022-49a2-bdaa-31aeef5353a7"; :>> title = "Sprint 718 closeOut gate (autonomous, D0049)"; :>> createdAt = "2026-09-15"; :>> createdBy = "claudeFable5"; :>> method = VerificationMethod::inspect; :>> procedureText = "Close-out at the landing commit after the CI conclusion reads success: git status -sb level with origin, gh run conclusion, the DoD result recorded against dcModelAndWriteAreMembersDoD at that sha, D0486 (process-change, the build-skill paragraph) held proposed for the human"; }
    // RAN: Close-out read at cfb1cb8: git status -sb level with origin (main...origin/main, no ahead/behind); gh run conclusion success at 4d38dd7 (the landing commit) and at cfb1cb8; the DoD result storyModelAndWriteAreMembersDoDR1 recorded; d0486 was ACCEPTED by the human from chat on 2026-09-14 ('Accept all proposals'), so the held paragraph clause is no longer waiting. The red run this close-out waited on (d110d0a, CI failure on a script probe anchored to a moved module) was resolved by sprint 719.
    part modelAndWriteAreMembersCloseOutGateR1 : TestResult { :>> id = "d6387df0-3469-4062-b8e2-d42468a7f294"; :>> outcome = VerdictKind::proposed; :>> judgedAgainst = "cfb1cb8"; :>> judgedAt = "2026-09-14"; :>> judgedBy = "claudeFable5"; }
    verification modelAndWriteAreMembersRetroGate : Test { :>> id = "f0b891d5-a882-4a8f-8f68-85c6fcffa7ca"; :>> title = "Sprint 718 retro gate (autonomous, D0049)"; :>> createdAt = "2026-09-15"; :>> createdBy = "claudeFable5"; :>> method = VerificationMethod::analyze; :>> procedureText = "Retro: avoidable issues scanned; what the extraction found that the plan did not predict. (1) keel show arch drift counted a #Supersede-retired CodeElement as MISSING drift after its successor was authored: fixed in this sprint (arch_model drops supersede targets, test a_superseded_element_leaves_the_registry_and_its_successor_stays) and tracked as an Issue resolved by this sprint's story. (2) the Model type and the item queries sat in view/mod.rs, so the read model could not leave without cutting a view file in half - predicted by D0479's layering, not by the DoD's module list; no new item, the DoD's own known-positive (view edit rebuilds no member) is what proves the cut landed on the right side. (3) a test fixture (scaffold temp_root) lived under cfg(test) and a dependent crate's tests could not reach it; now a doc(hidden) test_support module - no new item, the all-targets clippy rung is the control. (4) D0484's enumerated member list went stale on the very next extraction, as its consequences clause predicted; D0486 names the layering and Cargo.toml as the one list, so a member added inside a layer touches no locked prose - no new item. (5) eight member unit tests keyed on a cwd-relative anchor (Path::new('..'), read_to_string('src/...'), CARGO_MANIFEST_DIR joined with ..) broke two levels down - the SAME class as sprint 714's item (1), which was fixed by hand and left uncontrolled; a second occurrence is the D0047 line, so this sprint adds the scan no_member_test_anchors_on_a_cwd_relative_path over members/*/src as the control, tracks the recurrence as an Issue, and records dcOneRepoRootHelper (chartered by D0479, after this item) to collapse the nine local repo_root() copies onto one keel_fs helper and widen the scan to keel-cli/src's sixteen remaining anchors before the next move inherits them. (6) pin_skew landed in write.rs and a public fn reading a file there is exactly what no_public_write_reads_outside_the_lock forbids - moved back to lib level, no new item, the scan is the control that fired"; }
    // RAN: Retro read: the sprint extracted three members (keel-fs, keel-model, keel-write) and d0484 locked paragraph naming eight crates went stale on the same extraction - d0486 names the layering and the manifest as the one list; accepted 2026-09-14. Finding carried forward: the landing CI read failure (d110d0a) on receipt_shape_census.py anchoring keel-cli/src - issue559, resolved by sprint 719 (module_home.py). No new item beyond issue559.
    part modelAndWriteAreMembersRetroGateR1 : TestResult { :>> id = "e43effb7-7bb4-4fae-adc3-5d20921b8d97"; :>> outcome = VerdictKind::proposed; :>> judgedAgainst = "cfb1cb8"; :>> judgedAt = "2026-09-14"; :>> judgedBy = "claudeFable5"; }
}
