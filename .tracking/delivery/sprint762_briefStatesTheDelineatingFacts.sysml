// ProjectDeliveryS762 — Sprint 762: The human said on 2026-09-22 (st195) that the runner-direction brief gave prose about choosing instead of the facts that delineate each decision, and named the process they want: relevant content plain, a few decision-driving metrics, the consequential facts per option, less recommendation. This sprint records that shape in the asi-templates skill (D0552), rebuilds the brief to it with the three open asks and the four answered listed once, and republishes it at its URL.. EXECUTE. 1 pts.
package ProjectDeliveryS762 {
    private import EngineElement::*;
    private import EngineWork::*;
    private import EngineVerification::*;
    private import EngineRelationships::*;

    #CharteredBy dependency from briefStatesTheDelineatingFactsStory to d0552;
    #Delivers dependency from briefStatesTheDelineatingFactsStory to dcBriefStatesTheDelineatingFacts;

    part briefStatesTheDelineatingFactsStory : Story {
        :>> id = "07949919-013e-4bb6-9f93-1ffb9f573679";
        :>> title = "Sprint 762: The human said on 2026-09-22 (st195) that the runner-direction brief gave prose about choosing instead of the facts that delineate each decision, and named the process they want: relevant content plain, a few decision-driving metrics, the consequential facts per option, less recommendation. This sprint records that shape in the asi-templates skill (D0552), rebuilds the brief to it with the three open asks and the four answered listed once, and republishes it at its URL. (1 pts)";
        :>> createdAt = "2026-09-22"; :>> createdBy = "claudeFable5"; :>> kind = WorkKind::code; :>> priority = WorkPriority::p0; :>> owner = "claudeFable5"; :>> estimatedPoints = 1;
    }

    action def DeliveryRunS762 {
        action storyBriefStatesTheDelineatingFacts;
        verification storyBriefStatesTheDelineatingFactsDoD : Test { :>> id = "04888283-bbce-4785-be91-515dd25ee87e"; :>> method = VerificationMethod::test; :>> procedureText = "The skill's executive-brief section carries the 2026-09-22 words and the per-ask shape in .engine/skills and the .claude mirror with keel sync-claude --check clean; the brief is rebuilt with three tabs of facts, option tables and one what-would-change line each, passes check_templates.py --brief, and is republished at its URL; keel gate validate, guard and check-engine are green on the committed tree."; }
        // RAN: grep -c '2026-09-22, on a page' .engine/skills/asi-templates/SKILL.md and .claude/skills/asi-templates/SKILL.md -> 1 each; keel sync-claude --check clean; check_templates.py --brief clean on the rebuilt page; page republished version 4; validate, check-engine, guard green.
        part storyBriefStatesTheDelineatingFactsDoDR1 : TestResult { :>> id = "306eabf8-3b9c-4467-a9a4-7356a4de2afe"; :>> outcome = VerdictKind::pass; :>> judgedAgainst = "9675a3a56e5142598d7736f75725f318033e340d"; :>> judgedAt = "2026-09-22"; :>> judgedBy = "claudeFable5"; }
    }

    verification briefStatesTheDelineatingFactsRefineGate : Test { :>> id = "fe5f52a5-8049-45d4-8b62-07d60a6e0b49"; :>> title = "Sprint 762 refine gate (DoR)"; :>> createdAt = "2026-09-22"; :>> createdBy = "claudeFable5"; :>> method = VerificationMethod::inspect; :>> procedureText = "A correction from the human's use of the published page, on the asi-templates surface whose contract already takes its clauses from their words (D0404-D0406, D0550). One refinement: the answered asks are shown once in a table with the human's word and leave the tabs, as the decision-surfacing process says an answered item leaves the page. Sized 1 point: one skill paragraph, one builder, one rebuild."; }
    // RAN: st195 read verbatim from .tracking/intake/intake-2026-09-22.sysml; dcBriefStatesTheDelineatingFacts authored with record task before the sprint was scaffolded; DoR: estimatedPoints 1, #CharteredBy d0552 and #Delivers dcBriefStatesTheDelineatingFacts on the Story, DoD in the fill.
    part briefStatesTheDelineatingFactsRefineGateR1 : TestResult { :>> id = "36a7755a-9dc2-482e-8b78-948096ad6cf0"; :>> outcome = VerdictKind::proposed; :>> judgedAgainst = "9675a3a56e5142598d7736f75725f318033e340d"; :>> judgedAt = "2026-09-22"; :>> judgedBy = "claudeFable5"; }
    verification briefStatesTheDelineatingFactsStandupGate : Test { :>> id = "45dff2c0-0101-4d38-be14-ad6098f2aad1"; :>> title = "Sprint 762 standup gate"; :>> createdAt = "2026-09-22"; :>> createdBy = "claudeFable5"; :>> method = VerificationMethod::inspect; :>> procedureText = "Two choices. The facts on each tab were taken from the panel's verified findings and the tree - the launcher's auth rule, the Admin API's key surface, the bound-step count, the defect classification - never typed as prose. And the recommendation was dropped from every tab; the option table carries what each gives and costs, and the human's own words say that is enough."; }
    // RAN: every fact on the three tabs traced to a panel finding or a tree read: serve.rs:1212 (no API key), the Admin API key surface (list and update only), 13 of 191 steps with checkedBy, issue_classes.txt N rows (148 of 669), D0275 project-migration; no recommendation line on any tab.
    part briefStatesTheDelineatingFactsStandupGateR1 : TestResult { :>> id = "c46df305-8b89-47f5-acae-e909501ff7e9"; :>> outcome = VerdictKind::proposed; :>> judgedAgainst = "9675a3a56e5142598d7736f75725f318033e340d"; :>> judgedAt = "2026-09-22"; :>> judgedBy = "claudeFable5"; }
    verification briefStatesTheDelineatingFactsImplementGate : Test { :>> id = "937af1a4-a76f-43c0-ab88-f759499489ba"; :>> title = "Sprint 762 implement gate"; :>> createdAt = "2026-09-22"; :>> createdBy = "claudeFable5"; :>> method = VerificationMethod::test; :>> procedureText = "RAN build_panel_brief2.py -> 3 tabs, each with a facts list, two exhibits, an option table, one changes-this line, options and a keyed note; python scripts/check_templates.py --brief -> brief contract: clean; republished at the URL (version 4); the paragraph added to .engine/skills/asi-templates/SKILL.md and mirrored; keel sync-claude --check clean; D0552 recorded with the process-change marker and accepted on the human's st195 words; st195 recorded verbatim."; }
    // RAN: python build_panel_brief2.py -> 3 tabs, 41006 bytes; python scripts/check_templates.py --brief runner_direction_verdict.html -> brief contract: clean; republished at https://claude.ai/artifact/3e35AtqqdYE7sVPK3fpfkP (version 4); the 2026-09-22 paragraph added to .engine/skills/asi-templates/SKILL.md and .claude/skills/asi-templates/SKILL.md; keel sync-claude --check -> keel-owned subset matches; D0552 recorded with the process-change marker and accepted on the st195 words; st195 recorded.
    part briefStatesTheDelineatingFactsImplementGateR1 : TestResult { :>> id = "5ca61416-c5d8-4ab6-af07-3e5b11026abf"; :>> outcome = VerdictKind::pass; :>> judgedAgainst = "9675a3a56e5142598d7736f75725f318033e340d"; :>> judgedAt = "2026-09-22"; :>> judgedBy = "claudeFable5"; }
    verification briefStatesTheDelineatingFactsReviewGate : Test { :>> id = "df7936e1-b86d-424a-9e49-97401e81327a"; :>> title = "Sprint 762 review gate — three passes per D0172"; :>> createdAt = "2026-09-22"; :>> createdBy = "claudeFable5"; :>> method = VerificationMethod::inspect; :>> procedureText = "Content: every fact on the page names a verifiable source in the panel record or the tree; no tab carries scaffolding words; the answered table quotes the human's four answers in short form with the verbatim acceptance in the Decision records. Structure: title with a verb, ask under 70 words, three tabs each with two exhibits and one note, provenance strip; checker clean. Record: D0552 says NOT A FORK is not needed because it carries the marker and is held until accepted, and it was accepted on the human's own words; the DoD names its checks."; }
    // RAN: grep of the skill for the 2026-09-22 paragraph in source and mirror; check_templates.py --brief clean; the answered table names the four decided asks once with a short form of the human's word, the verbatim acceptance living in D0543, D0544, D0545, D0547; keel gate validate . clean; check-engine clean; guard --no-receipt ALL PASS.
    part briefStatesTheDelineatingFactsReviewGateR1 : TestResult { :>> id = "c470c3e5-1dcf-46fc-8f93-2efccc51e4bc"; :>> outcome = VerdictKind::proposed; :>> judgedAgainst = "9675a3a56e5142598d7736f75725f318033e340d"; :>> judgedAt = "2026-09-22"; :>> judgedBy = "claudeFable5"; }
    verification briefStatesTheDelineatingFactsCloseOutGate : Test { :>> id = "02435ed0-38af-48b3-8156-f3e11f1b554c"; :>> title = "Sprint 762 closeOut gate (autonomous, D0049)"; :>> createdAt = "2026-09-22"; :>> createdBy = "claudeFable5"; :>> method = VerificationMethod::inspect; :>> procedureText = "Delivered: the skill paragraph in source and mirror, D0552, the rebuilt brief at its URL, dcBriefStatesTheDelineatingFacts. Not delivered on purpose: no checker clause - the shape is a writing rule the skill carries and the per-ask note clause already holds the control the human asked for permanently."; }
    // RAN: git status --short lists the two SKILL.md files, 0552-briefStatesTheDelineatingFacts.sysml, sprint762 file, backlog.sysml, intake-2026-09-22.sysml; validate, check-engine and guard exit 0. Delivered the skill paragraph, D0552, the rebuilt brief at its URL, dcBriefStatesTheDelineatingFacts; no checker clause by design.
    part briefStatesTheDelineatingFactsCloseOutGateR1 : TestResult { :>> id = "ffa7d030-1fdf-4eaf-a10e-9d7097914c1d"; :>> outcome = VerdictKind::proposed; :>> judgedAgainst = "9675a3a56e5142598d7736f75725f318033e340d"; :>> judgedAt = "2026-09-22"; :>> judgedBy = "claudeFable5"; }
    verification briefStatesTheDelineatingFactsRetroGate : Test { :>> id = "298772e0-5a72-4100-9cc6-6183ce5cdade"; :>> title = "Sprint 762 retro gate (autonomous, D0049)"; :>> createdAt = "2026-09-22"; :>> createdBy = "claudeFable5"; :>> method = VerificationMethod::analyze; :>> procedureText = "Retro held; avoidable-issue scan over the sprint: one finding, no avoidable issue. The scaffolding words came from the standing builder's shape (True, Mine, Decides it) copied forward without asking whether they served the reader; the human's words now sit in the skill where the next builder reads them, so no new item is needed beyond dcBriefStatesTheDelineatingFacts, which this commit adds."; }
    // RAN: the retro text names dcBriefStatesTheDelineatingFacts (added by this commit) and says no new item is needed; keel gate guard --no-receipt ALL PASS with retro-backlog among the passes.
    part briefStatesTheDelineatingFactsRetroGateR1 : TestResult { :>> id = "e6c03472-4fd8-4c1a-aaba-b1962adb568e"; :>> outcome = VerdictKind::proposed; :>> judgedAgainst = "9675a3a56e5142598d7736f75725f318033e340d"; :>> judgedAt = "2026-09-22"; :>> judgedBy = "claudeFable5"; }
}
