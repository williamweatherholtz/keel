// ProjectDeliveryS736 — Sprint 736: the governance processes are a member - dcProcessIsAMember, the sixth D0479 extraction. process_cmd.rs, library.rs, adoption_check.rs, migrate.rs, workspace.rs, sync.rs, status.rs and currency.rs leave keel-cli/src for members/keel-process/src; the validate authority (Report, check_files, validate_root, validate_engine_instances and their tests) descends from keel-cli/src/lib.rs to members/keel-model/src/validate.rs so the workspace gate can reach it from below the binary; currency::cmd takes its GitHub pull as a parameter so the member depends on neither the intake (D0480: keel-issues') nor the server. The member sits ABOVE keel-guards, keel-suite, keel-view and keel-write because workspace, status and sync RUN the gates and the touched set (cargo tree -p keel-process --depth 1); D0507 records why that is the layering the DoD's own probe asks for. Every old crate:: path resolves through keel-cli's lib.rs re-exports.. EXECUTE. 5 pts.
package ProjectDeliveryS736 {
    private import EngineElement::*;
    private import EngineWork::*;
    private import EngineVerification::*;
    private import EngineRelationships::*;

    #CharteredBy dependency from processIsAMemberStory to d0479;

    part processIsAMemberStory : Story {
        :>> id = "90779e99-a987-4d43-b933-47ad430f5271";
        :>> title = "Sprint 736: the governance processes are a member - dcProcessIsAMember, the sixth D0479 extraction. process_cmd.rs, library.rs, adoption_check.rs, migrate.rs, workspace.rs, sync.rs, status.rs and currency.rs leave keel-cli/src for members/keel-process/src; the validate authority (Report, check_files, validate_root, validate_engine_instances and their tests) descends from keel-cli/src/lib.rs to members/keel-model/src/validate.rs so the workspace gate can reach it from below the binary; currency::cmd takes its GitHub pull as a parameter so the member depends on neither the intake (D0480: keel-issues') nor the server. The member sits ABOVE keel-guards, keel-suite, keel-view and keel-write because workspace, status and sync RUN the gates and the touched set (cargo tree -p keel-process --depth 1); D0507 records why that is the layering the DoD's own probe asks for. Every old crate:: path resolves through keel-cli's lib.rs re-exports. (5 pts)";
        :>> createdAt = "2026-09-17"; :>> createdBy = "claudeFable5"; :>> kind = WorkKind::code; :>> priority = WorkPriority::p0; :>> owner = "claudeFable5"; :>> estimatedPoints = 5;
    }

    action def DeliveryRunS736 {
        action storyProcessIsAMember;
        verification storyProcessIsAMemberDoD : Test { :>> id = "d0e14682-4c52-45ec-ad02-9bfb7fea6810"; :>> method = VerificationMethod::test; :>> procedureText = "DELIVERED BACKLOG ITEMS: dcProcessIsAMember. DONE MEANS: members/keel-process holds the eight modules with the member lint preamble and shares keel-cli's build.rs for KEEL_BUILD_COMMIT; keel-cli/src holds none of the eight and its lib.rs re-exports each (pub use keel_process::process_cmd; library; adoption_check; migrate; workspace; sync; status; currency) plus the four validate names at their old paths; members/keel-model/src/validate.rs holds the descended authority and its engine_instance_tests; main.rs hands currency::cmd keel_cli::github_ingest::pull_cmd; the two integration tests that include_str! adoption_check.rs read the member's path; the root manifest lists members/keel-process before keel-cli and keel-cli's manifest depends on it; scripts/extract_process.py is the idempotent transform (dry-run default, 99 crate:: references rewritten across eight files with a length-delta reconciliation, three anchored slices for the descent, re-run says already applied); cargo clippy --release --workspace --all-targets -D warnings clean; keel --help byte-identical to the pre-move render (cmp help_before736.txt help_after736.txt, 15089 bytes) and keel version's guard line unchanged (75: 66 hard-blocking, 9 warning-only); python scripts/modgraph.py --check and python scripts/module_home.py --probe hold. Known-positive, chosen before the tree is read (the DoD's own words): touching keel-cli/src/serve.rs leaves keel-process Fresh under cargo build --release --verbose while keel-cli recompiles, and advance (cursor unit tests), activate (activation_round_trip_loses_nothing, surface_states_its_state), show status (status_distinguishes_unknown) and the member's 29 unit tests pass (pos736.py). Known-negative: a pub use keel_cli::serve planted in the member's lib.rs fails cargo check -p keel-process naming the undeclared crate keel_cli, lib.rs restored bytes and mtime on every path (neg736.py). The DoD's layering prose (keel-view and below; activation and onboard among the modules) and its Fresh probe do not both hold - workspace.rs calls keel_guards::run_all_timed and sync.rs keel_suite::touched::before_gate, and activation/onboard have been keel-model's since sprint 718 - so the probe is the contract and D0507 records the layering."; }
        // RAN: TOUCHED RECEIPT: outcome=pass passed=890 failed=0 seconds=787 at=1789649510 launch=1789648259 (at>launch: ok)
        part storyProcessIsAMemberDoDR1 : TestResult { :>> id = "34157af0-b6f6-492c-8d95-deab41e9facd"; :>> outcome = VerdictKind::pass; :>> judgedAgainst = "01f7ad00"; :>> judgedAt = "2026-09-17"; :>> judgedBy = "claudeFable5"; }
    }

    verification processIsAMemberRefineGate : Test { :>> id = "feb22a40-0fa1-41cd-9736-aec80620cbaa"; :>> title = "Sprint 736 refine gate (DoR)"; :>> createdAt = "2026-09-17"; :>> createdBy = "claudeFable5"; :>> method = VerificationMethod::inspect; :>> procedureText = "DoR: dcProcessIsAMember is the first line of keel show whats-next at 01f7ad00 (brief 42 landed, CI conclusion success). Chartered by D0479 (accepted) through its #CharteredBy edge; #DependsOn dcViewIsAMember, done. Sized 5 - eight files moved with a codemod (5,889 lines), one new member manifest sharing build.rs, one descent of the validate authority in three anchored slices, one signature inversion (currency's pull parameter) with its main.rs call site, two include_str! repoints, and the D0388 pair as two scripts. No locked path in the diff, so no marked Decision and no brief. Blocking dependencies: none."; }
    // RAN: validate=pass guard=pass clippy=pass probe=pass touched=pass
    part processIsAMemberRefineGateR1 : TestResult { :>> id = "923a17ce-9ef6-4138-89b8-5432a6d83b29"; :>> outcome = VerdictKind::proposed; :>> judgedAgainst = "01f7ad00"; :>> judgedAt = "2026-09-17"; :>> judgedBy = "claudeFable5"; }
    verification processIsAMemberStandupGate : Test { :>> id = "4f11625e-adef-4bd8-8d89-ac05aade2910"; :>> title = "Sprint 736 standup gate"; :>> createdAt = "2026-09-17"; :>> createdBy = "claudeFable5"; :>> method = VerificationMethod::inspect; :>> procedureText = "Owner claudeFable5. Blocker: none - brief 42 landed in 01f7ad00, no ladder or land is running. Order: (1) scripts/extract_process.py: git mv the eight files, rewrite crate:: paths through MODULE_MAP, pre-edit currency.rs's signature and call, write the member's Cargo.toml and lib.rs, slice validate out of keel-cli/src/lib.rs into keel-model, edit the root and keel-cli manifests, lib.rs re-exports, main.rs's currency call and the two include_str! tests; dry-run reconciled, then --apply. (2) cargo build --release, clippy --workspace --all-targets, keel --help against help_before736.txt, keel version, cargo test on keel-process and the descended validate tests. (3) pos736/neg736; pair736.txt; modgraph --check; module_home --probe. (4) doc-sync, sync-claude --check. (5) D0507 (unmarked, auto-accepted under d0207), the sprint with the retro filled, issue591 with its resolver dcSourceCitationsOnTheLivingDocsResolve declared after dcSuiteMeasuresTheWorkspace; verifier with the pair file; recorder --owed 7; land; CI conclusion."; }
    // RAN: validate=pass guard=pass clippy=pass probe=pass touched=pass
    part processIsAMemberStandupGateR1 : TestResult { :>> id = "8c12fd15-d28d-4d31-b68a-d3e64c3c8b8e"; :>> outcome = VerdictKind::proposed; :>> judgedAgainst = "01f7ad00"; :>> judgedAt = "2026-09-17"; :>> judgedBy = "claudeFable5"; }
    verification processIsAMemberImplementGate : Test { :>> id = "e20c67b3-a474-44ee-8479-8cae9a47b339"; :>> title = "Sprint 736 implement gate"; :>> createdAt = "2026-09-17"; :>> createdBy = "claudeFable5"; :>> method = VerificationMethod::test; :>> procedureText = "The implement gate is the DoD's own probes plus the ladder: cargo build --release clean after two one-shot fixes (a missing `use keel_parser::ast::Package` in the moved validate slice; KEEL_BUILD_COMMIT undefined in the member until its manifest took keel-cli's build.rs); cargo clippy --release --workspace --all-targets -- -D warnings Finished clean after the include_str! repoints; cmp help_before736.txt help_after736.txt byte-identical (15089 bytes); keel version guards line 75 (66 hard-blocking, 9 warning-only); cargo test --release -p keel-process --lib 29 passed, -p keel-model --lib -- validate:: 3 passed; python pos736.py exit 0 (Fresh keel-process, keel-cli recompiled, advance/activate/status tests pass); python neg736.py exit 0 (cargo check rc 101 naming keel_cli, lib.rs restored); python scripts/modgraph.py --check exit 0; python scripts/module_home.py --probe 0 failures; keel verify . --probe-from pair736.txt (validate, guard, clippy, the pair, suite --touched) green."; }
    // RAN: validate=pass guard=pass clippy=pass probe=pass touched=pass
    part processIsAMemberImplementGateR1 : TestResult { :>> id = "562f8f3d-1eb6-423d-9436-cd395e48d0c5"; :>> outcome = VerdictKind::pass; :>> judgedAgainst = "01f7ad00"; :>> judgedAt = "2026-09-17"; :>> judgedBy = "claudeFable5"; }
    verification processIsAMemberReviewGate : Test { :>> id = "5692d1a9-c28a-43da-b7f4-dd67631f35c5"; :>> title = "Sprint 736 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every moved test passes in its new crate (29 in keel-process, 3 descended validate tests in keel-model), every caller of the eight modules and of the four validate names resolves through a re-export, main.rs's one changed call passes the same function currency called before, and the binary's help and guard count are byte-for-byte the pre-move ones. Honesty: the negative plants in the MEMBER's lib.rs and asserts the compiler names the crate the member must not know, not merely that the build fails; the positive touches a file the member must not depend on and reads Fresh from cargo's own verbose line. Scope: no locked path (is_locked_path: .engine/{processes,skills,workflows,rules,contracts}, .githooks/, .github/workflows, members/keel-guards/src, adherence.rs, guard_names.rs) is in the diff (git status: keel-cli, members/keel-model, members/keel-process, two tests, three manifests, the codemod, D0507, .tracking); the one locked-path edit the doc-sync wanted (a stale citation in the project-migration skill) was reverted out of this commit and is issue591."; }
    // RAN: validate=pass guard=pass clippy=pass probe=pass touched=pass
    part processIsAMemberReviewGateR1 : TestResult { :>> id = "2b4480ea-0675-4ee0-8a9f-3e2fca2edc68"; :>> outcome = VerdictKind::proposed; :>> judgedAgainst = "01f7ad00"; :>> judgedAt = "2026-09-17"; :>> judgedBy = "claudeFable5"; }
    verification processIsAMemberCloseOutGate : Test { :>> id = "d1e63195-66ee-43da-b29a-77ad276c3f52"; :>> title = "Sprint 736 closeOut gate (autonomous, D0049)"; :>> createdAt = "2026-09-17"; :>> createdBy = "claudeFable5"; :>> method = VerificationMethod::inspect; :>> procedureText = "Landed when the verifier's receipt reads DISCREPANCIES: NONE and its probe rung row names pair736.txt, the recorder's report passes check_report.py --owed 7, git status -sb is clean after keel land and gh run list names the landing commit with conclusion success. The DoD result is recorded against dcProcessIsAMemberDoD at that sha; D0507 was accepted at record time under standing consent d0207 (no marker, no fork), so the authority queue's pending set is unchanged and no brief is published (decision-surfacing: same set, nothing); issue591's resolution is computed from its #Resolves edge to dcSourceCitationsOnTheLivingDocsResolve."; }
    // RAN: validate=pass guard=pass clippy=pass probe=pass touched=pass
    part processIsAMemberCloseOutGateR1 : TestResult { :>> id = "caf7b101-bfcd-4c77-ae24-bc5de3d8e825"; :>> outcome = VerdictKind::proposed; :>> judgedAgainst = "01f7ad00"; :>> judgedAt = "2026-09-17"; :>> judgedBy = "claudeFable5"; }
    verification processIsAMemberRetroGate : Test { :>> id = "606d3d71-ae93-4980-8878-a666769ebf22"; :>> title = "Sprint 736 retro gate (autonomous, D0049)"; :>> createdAt = "2026-09-17"; :>> createdBy = "claudeFable5"; :>> method = VerificationMethod::analyze; :>> procedureText = "Written at close-out, before the verifier is dispatched; avoidable issues scanned (issue011), each finding a tracked item or the reason it is not. (1) A skill cites source by line and nothing holds the citation to the tree: .engine/skills/project-migration/SKILL.md:10 says migrate.rs:664-666 for check_preconditions, which sat at 805-807 before this sprint and moves to members/keel-process with it; the fix is one line under the keystone lock, so it cannot ride a commit whose Decision says no locked path is edited -> issue591, new item dcSourceCitationsOnTheLivingDocsResolve declared after dcSuiteMeasuresTheWorkspace (D0052), chartered by D0471 beside tool-reference and cli-reference: a source-reference guard whose known-positive is this line. (2) The DoD's layering prose (keel-view and below; activation and onboard in the member) contradicted its own Fresh probe: workspace.rs runs the guards, sync.rs runs the touched set, and activation/onboard have been keel-model's since sprint 718. The probe won; D0507 records the layering and the validate descent that lets the workspace gate compile below the binary. Not tracked: D0507 is the record and its rationale is the rule, the third sprint running (734, 735) to read it. (3) The member needed keel-cli's build.rs for KEEL_BUILD_COMMIT (migrate.rs reads it) - the third member to share it after keel-guards and keel-write. Not tracked: the failure is loud at build (env! is a compile error), and the codemod's CARGO template carries the line so a re-run lands it; a fourth sharer is the trigger to lift the build script to the workspace. (4) Two integration tests read adoption_check.rs by include_str!('../src/...') and clippy --all-targets found the dangling path after the move; the codemod was extended to repoint them. Not tracked: the control (clippy under --all-targets, sprint 733 (7)) fired and the transform now carries the fix; the next codemod greps keel-cli/tests for include_str! of every file it moves before it writes, a step this one did by hand. (5) The validate slice moved without its `use keel_parser::ast::Package` because lib.rs's import line held names the slice and the orient API shared; the build named it once and VALIDATE_HEAD in the codemod carries it. Not tracked: one-shot, caught before --apply was re-run (migration skill gate 2). (6) advance is cursor.rs, which did not move and has seven unit tests and no end-to-end test, so the DoD's 'their integration tests pass' holds for activate and status by integration test and for advance by unit test only. Not tracked as a new item: the verification lens (EXAMINED vs EXERCISED) is the standing control for a command with no exercised test, and the module is keel-cli's still; the next sprint to move cursor.rs writes the probe. (7) The pre-bash hook and the D0224 rule held: every paragraph in this sprint went through a file (d0507.md, issue591.md, this fill). Non-finding, recorded because sprint 735 (6) recorded the skill drift it fixed and this sprint's doc-sync could not: the drift is issue591's, not a reminder."; }
    // RAN: validate=pass guard=pass clippy=pass probe=pass touched=pass
    part processIsAMemberRetroGateR1 : TestResult { :>> id = "9c96edeb-2399-4f16-999d-7d19124db948"; :>> outcome = VerdictKind::proposed; :>> judgedAgainst = "01f7ad00"; :>> judgedAt = "2026-09-17"; :>> judgedBy = "claudeFable5"; }
}
