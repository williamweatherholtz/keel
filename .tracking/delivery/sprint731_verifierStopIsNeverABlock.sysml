// ProjectDeliveryS731 — Sprint 731: dcVerifierStopIsNeverABlock, the correction for issue578 - sprint 730's verifier stopped over a tree the PRIMARY had left red, was blocked six times by the subagent-stop hook with the turn gate's instruction to make it green, and rewrote a .tracking record to obey. Two held safety-change Decisions: D0501 moves the subagent baseline from the session's first fire to the agent's own start (SubagentStart, else its first fire naming its agent_id), and D0502 takes the verifier off the blocking path - its moved tree becomes a refused-class ledger line under verifier:tree-written, counted beside recorder:tree-red. EXECUTE. 3 pts.. EXECUTE. 3 pts.
package ProjectDeliveryS731 {
    private import EngineElement::*;
    private import EngineWork::*;
    private import EngineVerification::*;
    private import EngineRelationships::*;

    #CharteredBy dependency from verifierStopIsNeverABlockStory to d0502;

    part verifierStopIsNeverABlockStory : Story {
        :>> id = "0073040c-ba8f-4254-a452-71de1f6a02ab";
        :>> title = "Sprint 731: dcVerifierStopIsNeverABlock, the correction for issue578 - sprint 730's verifier stopped over a tree the PRIMARY had left red, was blocked six times by the subagent-stop hook with the turn gate's instruction to make it green, and rewrote a .tracking record to obey. Two held safety-change Decisions: D0501 moves the subagent baseline from the session's first fire to the agent's own start (SubagentStart, else its first fire naming its agent_id), and D0502 takes the verifier off the blocking path - its moved tree becomes a refused-class ledger line under verifier:tree-written, counted beside recorder:tree-red. EXECUTE. 3 pts. (3 pts)";
        :>> createdAt = "2026-09-17"; :>> createdBy = "claudeFable5"; :>> kind = WorkKind::code; :>> priority = WorkPriority::p0; :>> owner = "claudeFable5"; :>> estimatedPoints = 3;
    }

    action def DeliveryRunS731 {
        action storyVerifierStopIsNeverABlock;
        verification storyVerifierStopIsNeverABlockDoD : Test { :>> id = "94867e27-01a5-4e67-8560-29bad44012c2"; :>> method = VerificationMethod::test; :>> procedureText = "DELIVERED BACKLOG ITEMS: dcVerifierStopIsNeverABlock. DONE MEANS: the subagent-stop hook never blocks an agent of type verifier; a verifier whose own start fingerprint moved is ledgered refused-class under control verifier:tree-written so control-census and enforcement-report count it; every other agent is gated against the fingerprint written at its own start (agent-{agent_id}.fp, SubagentStart else first fire) and only an agent no fire named falls back to the session baseline; the recorder keeps its block under recorder:tree-red; SubagentStart is registered in the one home keel sync-claude renders from; control-events.toml, EMITTED_LEDGER, cliHook (by #Supersede edge) and cli_facts.rs name subagent-start; control-map.sysml declares hook-rule verifier:tree-written; delegated-ceremony.sysml, the skill in both homes and CLAUDE.md name both controls; D0501 and D0502 are co-committed. Known-positive, chosen before the tree is read: cargo test --release -p keel-cli --bin keel subagent_stop_route_tests - a verifier payload over a tree that differs from the session baseline but not from its own start routes silent, no block, no refused line; a verifier whose own fingerprint moved routes to verifier:tree-written. Known-negative: the same test module - a recorder over a moved tree routes to the gate and its block relabels to recorder:tree-red; a payload with no agent_type over a moved tree routes to the gate keeping the gate's control."; }
        // RAN: verify . --probe-from pair731.txt: outcome=pass; gate check-engine: .engine instance files validated clean; sync-claude --check: claude-surface matches binary's generator
        part storyVerifierStopIsNeverABlockDoDR1 : TestResult { :>> id = "73f1eb53-d49c-4578-a924-5e257d319712"; :>> outcome = VerdictKind::pass; :>> judgedAgainst = "ebb0214"; :>> judgedAt = "2026-09-16"; :>> judgedBy = "claudeFable5"; }
    }

    verification verifierStopIsNeverABlockRefineGate : Test { :>> id = "633ec1fd-32a1-4f52-8248-73b8c6730d35"; :>> title = "Sprint 731 refine gate (DoR)"; :>> createdAt = "2026-09-17"; :>> createdBy = "claudeFable5"; :>> method = VerificationMethod::inspect; :>> procedureText = "Chartered by D0502 (HELD proposed under D0337 with D0501: both carry a SafetyChange marker, the subagent-stop hook is a hazard control and its interval and one agent's path change; the code and the record land together under the D0209 cl.2 lock and the human signs the record). Scope: one backlog item, 3 pts - a dispatcher write, one route function with its tests, a hook registration, four declaration homes and doc-sync. DoR: points set, #CharteredBy edge to d0502, no blocking dependency (D0500 landed in 9e645ee), the D0388 pair named above before the tree is read."; }
    // RAN: verify . --probe-from pair731.txt: outcome=pass; validate=pass guard=pass clippy=pass probe=pass touched=pass; first red line: none
    part verifierStopIsNeverABlockRefineGateR1 : TestResult { :>> id = "25b65f44-af64-4c8d-82fb-76d6604f9eba"; :>> outcome = VerdictKind::proposed; :>> judgedAgainst = "ebb0214"; :>> judgedAt = "2026-09-16"; :>> judgedBy = "claudeFable5"; }
    verification verifierStopIsNeverABlockStandupGate : Test { :>> id = "17eca7b9-b377-4e91-92fd-c70e98e84578"; :>> title = "Sprint 731 standup gate"; :>> createdAt = "2026-09-17"; :>> createdBy = "claudeFable5"; :>> method = VerificationMethod::inspect; :>> procedureText = "Owner claudeFable5. Blocker: none - brief 37 landed in ebb0214 and no ladder or land is running. Order this sprint, the correction issue578 asks of the primary independent of the hook: the retro is filled BEFORE the verifier is dispatched, so the verifier climbs a tree whose only red is a real defect."; }
    // RAN: verify . --probe-from pair731.txt: outcome=pass; validate=pass guard=pass clippy=pass probe=pass touched=pass; first red line: none
    part verifierStopIsNeverABlockStandupGateR1 : TestResult { :>> id = "1c90b33a-0a96-4e9c-bdac-76a0b5d28edc"; :>> outcome = VerdictKind::proposed; :>> judgedAgainst = "ebb0214"; :>> judgedAt = "2026-09-16"; :>> judgedBy = "claudeFable5"; }
    verification verifierStopIsNeverABlockImplementGate : Test { :>> id = "1afa91de-a012-4bab-aae0-b6fa115a4be3"; :>> title = "Sprint 731 implement gate"; :>> createdAt = "2026-09-17"; :>> createdBy = "claudeFable5"; :>> method = VerificationMethod::test; :>> procedureText = "keel-cli/src/main.rs: cmd_hook writes agent-{agent_id}.fp on the first fire carrying an agent_id that is not a subagent-stop; hook_subagent_stop resolves its baseline through subagent_baseline (own start, else session) and routes through subagent_stop_route before the gate runs - Verifier over an unmoved start returns 0 silently, Verifier over a moved start emits a systemMessage and notes the refused-class verdict under verifier:tree-written, any other type runs hook_stop and relabels a recorder's block as before; a subagent-start event returns 0 (the dispatcher already wrote the baseline). keel-cli/src/claude_surface.rs: SubagentStart registered, is_keel_hook recognises hook subagent-start, the events test counts seven. .engine/contracts/control-events.toml [subagent-start]; guards.rs EMITTED_LEDGER 15 entries. .engine/cli/commands.sysml cliHook2 with a #Supersede edge to cliHook; cli_facts.rs invocation agrees. .tracking/architecture/control-map.sysml ctlVerifierTreeWritten (hook-rule: verifier:tree-written) discharging the hazard ctlTurnBoundaryGate discharges. .engine/processes/delegated-ceremony.sysml dcyRedTreeIsARefusal names both controls; the skill in .engine/skills and .claude/skills (sync-claude) and CLAUDE.md agree."; }
    // RAN: verify . --probe-from pair731.txt: outcome=pass; validate=pass guard=pass clippy=pass probe=pass touched=pass; first red line: none
    part verifierStopIsNeverABlockImplementGateR1 : TestResult { :>> id = "520eb3b6-9d19-4be4-9997-25323de4efd8"; :>> outcome = VerdictKind::pass; :>> judgedAgainst = "ebb0214"; :>> judgedAt = "2026-09-16"; :>> judgedBy = "claudeFable5"; }
    verification verifierStopIsNeverABlockReviewGate : Test { :>> id = "2b4e0e86-2948-4b33-9d2c-4b3882fe1229"; :>> title = "Sprint 731 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172: the route function's four arms against D0502's decision text; the baseline file is written on no subagent-stop payload (the issue the 2026-08 comment already found by running the branch); the declaration homes agree by the guards that hold them (control-event-coverage, cli-surface-declared, doc-sync, claude-surface-drift)."; }
    // RAN: verify . --probe-from pair731.txt: outcome=pass; validate=pass guard=pass clippy=pass probe=pass touched=pass; first red line: none
    part verifierStopIsNeverABlockReviewGateR1 : TestResult { :>> id = "ea616851-971e-4af9-9bed-5cbdcc48256a"; :>> outcome = VerdictKind::proposed; :>> judgedAgainst = "ebb0214"; :>> judgedAt = "2026-09-16"; :>> judgedBy = "claudeFable5"; }
    verification verifierStopIsNeverABlockCloseOutGate : Test { :>> id = "aefb0b5d-b798-4958-9483-6ddd538fe7d5"; :>> title = "Sprint 731 closeOut gate (autonomous, D0049)"; :>> createdAt = "2026-09-17"; :>> createdBy = "claudeFable5"; :>> method = VerificationMethod::inspect; :>> procedureText = "Landed when the verifier's receipt reads DISCREPANCIES: NONE and its probe rung row names the pair file, the recorder's report passes check_report.py --owed 8, git status -sb is clean after keel land and gh run list names the landing commit with conclusion success. issue578 resolves by the #Resolves edge from dcVerifierStopIsNeverABlock, computed."; }
    // RAN: verify . --probe-from pair731.txt: outcome=pass; validate=pass guard=pass clippy=pass probe=pass touched=pass; first red line: none
    part verifierStopIsNeverABlockCloseOutGateR1 : TestResult { :>> id = "d0c2b2fc-8385-4e9f-a515-566a2452f855"; :>> outcome = VerdictKind::proposed; :>> judgedAgainst = "ebb0214"; :>> judgedAt = "2026-09-16"; :>> judgedBy = "claudeFable5"; }
    verification verifierStopIsNeverABlockRetroGate : Test { :>> id = "06222284-c7e8-45e5-ac56-0e16b264460e"; :>> title = "Sprint 731 retro gate (autonomous, D0049)"; :>> createdAt = "2026-09-17"; :>> createdBy = "claudeFable5"; :>> method = VerificationMethod::analyze; :>> procedureText = "Avoidable issues scanned (issue011). One finding, the issue this sprint corrects, and one about the primary. (1) issue578 itself: the subagent-stop hook's session baseline plus its block turned a red the primary left into a subagent write; D0501 and D0502 are the controls, and the ledger row verifier:tree-written is what makes a recurrence a counted fact instead of a transcript line. (2) The dispatch order was the primary's: sprint 730's verifier was dispatched before the retro was filled, over a tree guard:retro-backlog had already marked red. No new item for (2), already tracked by dcVerifierStopIsNeverABlock: a hook that never blocks the verifier removes the consequence, and the ordering itself is now written in this sprint's standup step where the next sprint's fill copies it from; a guard on dispatch order would read conversational sequence, which no gate can (D0151). No third finding: the D0500 pair file is used for the first time this sprint and the retro will name any friction it shows when the verifier's receipt is read."; }
    // RAN: verify . --probe-from pair731.txt: outcome=pass; validate=pass guard=pass clippy=pass probe=pass touched=pass; first red line: none
    part verifierStopIsNeverABlockRetroGateR1 : TestResult { :>> id = "9dd405cf-2caa-4555-8e9e-5c1f58e1994e"; :>> outcome = VerdictKind::proposed; :>> judgedAgainst = "ebb0214"; :>> judgedAt = "2026-09-16"; :>> judgedBy = "claudeFable5"; }
}
