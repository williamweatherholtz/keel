// ProjectDeliveryS755 — Sprint 755: The verifier's receipt is read against the ladder that ended: check_receipt.py runs keel verify --wait, then holds the receipt's LADDER line, five rung verdicts and TOUCHED RECEIPT counts to verify-receipt.toml and touched-receipt.toml, refusing a receipt that says the ladder did not end, describes another run, or disagrees with the files (D0538; issue603). EXECUTE. 3 pts.
package ProjectDeliveryS755 {
    private import EngineElement::*;
    private import EngineWork::*;
    private import EngineVerification::*;
    private import EngineRelationships::*;

    #CharteredBy dependency from verifierReceiptIsCheckedAgainstTheLadderStory to d0538;
    #Delivers dependency from verifierReceiptIsCheckedAgainstTheLadderStory to dcVerifierReceiptIsCheckedAgainstTheLadder;

    part verifierReceiptIsCheckedAgainstTheLadderStory : Story {
        :>> id = "7b40cc7a-e263-4983-b80e-f4223195248d";
        :>> title = "Sprint 755: The verifier's receipt is read against the ladder that ended: check_receipt.py runs keel verify --wait, then holds the receipt's LADDER line, five rung verdicts and TOUCHED RECEIPT counts to verify-receipt.toml and touched-receipt.toml, refusing a receipt that says the ladder did not end, describes another run, or disagrees with the files (D0538; issue603) (3 pts)";
        :>> createdAt = "2026-09-20"; :>> createdBy = "claudeFable5"; :>> kind = WorkKind::code; :>> priority = WorkPriority::p0; :>> owner = "claudeFable5"; :>> estimatedPoints = 3;
    }

    action def DeliveryRunS755 {
        action storyVerifierReceiptIsCheckedAgainstTheLadder;
        verification storyVerifierReceiptIsCheckedAgainstTheLadderDoD : Test { :>> id = "0a511392-54e2-41bf-be22-4b800019602d"; :>> method = VerificationMethod::test; :>> procedureText = "DELIVERED BACKLOG ITEM: dcVerifierReceiptIsCheckedAgainstTheLadder. DONE MEANS: the task's DoD passes as written - .engine/skills/delegated-ceremony/references/check_receipt.py, given the verifier receipt and --root --keel, runs keel verify --wait ROOT and refuses when the ladder has no verdict (in flight, KILLED, no receipt), when the receipt says KILLED/running/killed while --wait reports an ended ladder (naming the rung and exit --wait printed), when the receipt's LADDER at= is another run's, when outcome/stopped_at or any [[rung]] verdict differs from verify-receipt.toml, or when the TOUCHED RECEIPT at=/outcome/passed/failed differ from touched-receipt.toml for a ladder that reached that rung; refusals() is pure over the --wait text, its exit and the two decoded receipts; fixtures under references/fixtures hold sprint 743's receipt as returned (positive-sprint743-killed-while-ended.txt, refused naming stopped at touched fail (101)), its corrected render (negative-sprint743-rendered-fail.txt, passes), the one-line KILLED render and the following run's receipt (positive-sprint743-other-run-quoted.txt, refused naming at=1789728746 against at=1789725917), the --wait output and the two toml receipts; --probe reports every pair holds over four rows; the verifier brief runs the check as its last step and returns its verdict line, dcyDispatchRecorder's trigger names a passed check, dcyVerifierReceipt's actionText, the test-verify skill, guards.md's account of the skill and CLAUDE.md name it; sync-claude --check matches. Verified by the verifier ladder with the two sprint 743 fixture probes as the D0388 pair and keel gate guard green at the landing tree."; }
        // RAN: validate=pass guard=pass clippy=pass probe=pass touched=pass
        part storyVerifierReceiptIsCheckedAgainstTheLadderDoDR1 : TestResult { :>> id = "a15897da-c85c-44ce-81c4-8eb04f1d6921"; :>> outcome = VerdictKind::pass; :>> judgedAgainst = "301b6a71"; :>> judgedAt = "2026-09-20"; :>> judgedBy = "claudeFable5"; }
    }

    verification verifierReceiptIsCheckedAgainstTheLadderRefineGate : Test { :>> id = "380a54d4-8f71-4ca8-9fbd-5ca27311044d"; :>> title = "Sprint 755 refine gate (DoR)"; :>> createdAt = "2026-09-20"; :>> createdBy = "claudeFable5"; :>> method = VerificationMethod::inspect; :>> procedureText = "One backlog item, sized 3: a new Python check with a pure refusals() over five inputs, a --wait runner, seven fixtures (four receipts, one --wait transcript, two reconstructed toml receipts), a four-row probe table, one process trigger and actionText, two skill briefs, and three doc surfaces. DoR: estimatedPoints 3; #CharteredBy d0538 (proposed, #ProspectiveChange, held for the human - the code change rides it as the co-committed Decision); #Delivers dcVerifierReceiptIsCheckedAgainstTheLadder; no blocking dependency; the DoD exists in the backlog with its own known-positive and known-negative named before the tree was read."; }
    // RAN: validate=pass guard=pass clippy=pass probe=pass touched=pass
    part verifierReceiptIsCheckedAgainstTheLadderRefineGateR1 : TestResult { :>> id = "6d7ecde5-e666-4250-91c4-f0dd08073500"; :>> outcome = VerdictKind::proposed; :>> judgedAgainst = "301b6a71"; :>> judgedAt = "2026-09-20"; :>> judgedBy = "claudeFable5"; }
    verification verifierReceiptIsCheckedAgainstTheLadderStandupGate : Test { :>> id = "02508912-4f01-4903-9241-00d4f7b31f34"; :>> title = "Sprint 755 standup gate"; :>> createdAt = "2026-09-20"; :>> createdBy = "claudeFable5"; :>> method = VerificationMethod::inspect; :>> procedureText = "keel verify --wait is the fact and the receipt is the claim: --wait blocks while the writer's pid lives, so the check cannot run before the ladder ends - the sprint 743 shape - and its exit is the ladder's own. The receipt is pinned to one run by at=, not head: sprint 743's tree held two ladders at head 66f74bd0 fifty minutes apart, fail (101) then pass, and only the timestamp tells them apart. Every refusal names both sides (receipt value; file value) so a refused receipt says what to relaunch or re-render. Residual named in D0538: the toml fixtures are reconstructions from the --wait table and the sprint's recorded counts; the original verify-receipt.toml was overwritten by the next ladder. Impediment: none."; }
    // RAN: validate=pass guard=pass clippy=pass probe=pass touched=pass
    part verifierReceiptIsCheckedAgainstTheLadderStandupGateR1 : TestResult { :>> id = "7b2bf2e1-cc03-497e-8a6c-21fa7c42482c"; :>> outcome = VerdictKind::proposed; :>> judgedAgainst = "301b6a71"; :>> judgedAt = "2026-09-20"; :>> judgedBy = "claudeFable5"; }
    verification verifierReceiptIsCheckedAgainstTheLadderImplementGate : Test { :>> id = "a0ac4ba4-6acd-4bd9-8265-a774ef0dfeac"; :>> title = "Sprint 755 implement gate"; :>> createdAt = "2026-09-20"; :>> createdBy = "claudeFable5"; :>> method = VerificationMethod::test; :>> procedureText = "python .engine/skills/delegated-ceremony/references/check_receipt.py --probe: probe: every pair holds (4 rows; the sprint 743 receipt as returned refused with 7 lines, first naming stopped at touched fail (101); the corrected render 0 refusals; the one-line KILLED render 2 refusals; the following run's receipt 8 refusals, first naming at=1789728746 against at=1789725917). D0538 recorded proposed with the process-change marker; sprint 755 recorded with --charter d0538. Doc-sync: delegated-ceremony SKILL.md verifier brief and refusal section, test-verify SKILL.md step 7, delegated-ceremony.sysml dcyVerifierReceipt actionText and dcyDispatchRecorder trigger, guards.md skill account, CLAUDE.md subagents paragraph; keel sync-claude . regenerated the .claude copies and --check matches. gate validate, check-engine and guard --no-receipt read back green."; }
    // RAN: validate=pass guard=pass clippy=pass probe=pass touched=pass
    part verifierReceiptIsCheckedAgainstTheLadderImplementGateR1 : TestResult { :>> id = "f2aaf163-a178-4363-9bcf-81d4b3d145ae"; :>> outcome = VerdictKind::pass; :>> judgedAgainst = "301b6a71"; :>> judgedAt = "2026-09-20"; :>> judgedBy = "claudeFable5"; }
    verification verifierReceiptIsCheckedAgainstTheLadderReviewGate : Test { :>> id = "ec065c9a-ccb8-44cc-9585-122225e71b64"; :>> title = "Sprint 755 review gate — three passes per D0172"; :>> createdAt = "2026-09-20"; :>> createdBy = "claudeFable5"; :>> method = VerificationMethod::inspect; :>> procedureText = "Three passes per D0172. Code read back: parse_receipt reads the LADDER kv after ->, the rung line, and the TOUCHED RECEIPT kv; parse_wait reads has ended (head, at), the rung table and the summary line; refusals() returns early on no ended ladder and on a moved verify-receipt.toml so the later comparisons never read a file from another run; a header with no at= is its own refusal so a hand-typed LADDER line cannot pass by omission; the touched comparison fires only when stopped_at is none or touched. Ceremony: D0538 is proposed with the process-change marker and held for the human; a new check on the verifier's receipt and a new trigger on dcyDispatchRecorder are enforcement changes, so the Decision is co-committed under the CR prefix. FINDING for the retro: the backlog DoD's known-positive/known-negative labels are the reverse of the fixture convention check_report.py established (positive-* = refused, negative-* = passes); the fixtures follow the convention and the DoD's two cases are both pinned, under the other names."; }
    // RAN: validate=pass guard=pass clippy=pass probe=pass touched=pass
    part verifierReceiptIsCheckedAgainstTheLadderReviewGateR1 : TestResult { :>> id = "1195e62b-36fd-41aa-8b69-2da705295879"; :>> outcome = VerdictKind::proposed; :>> judgedAgainst = "301b6a71"; :>> judgedAt = "2026-09-20"; :>> judgedBy = "claudeFable5"; }
    verification verifierReceiptIsCheckedAgainstTheLadderCloseOutGate : Test { :>> id = "79a3f7c1-b1d7-405e-ace2-abbc16715d7b"; :>> title = "Sprint 755 closeOut gate (autonomous, D0049)"; :>> createdAt = "2026-09-20"; :>> createdBy = "claudeFable5"; :>> method = VerificationMethod::inspect; :>> procedureText = "The task's DoD result and the six gate results are recorded from the verifier's rendered receipt, itself passed by check_receipt.py before the recorder was dispatched - this sprint's control gated its own ceremony; issue603 resolves when the DoD passes. Doc-sync rode the change. The check's probe table is the regression suite for the four receipt fixtures; no code under keel-cli or members changed, so the touched test set is the members the ladder names for the .engine stems."; }
    // RAN: validate=pass guard=pass clippy=pass probe=pass touched=pass
    part verifierReceiptIsCheckedAgainstTheLadderCloseOutGateR1 : TestResult { :>> id = "1d1a27c3-585b-4126-bedb-62a7260f8434"; :>> outcome = VerdictKind::proposed; :>> judgedAgainst = "301b6a71"; :>> judgedAt = "2026-09-20"; :>> judgedBy = "claudeFable5"; }
    verification verifierReceiptIsCheckedAgainstTheLadderRetroGate : Test { :>> id = "150f1048-7525-4a21-a6b2-b1ed4ae48c55"; :>> title = "Sprint 755 retro gate (autonomous, D0049)"; :>> createdAt = "2026-09-20"; :>> createdBy = "claudeFable5"; :>> method = VerificationMethod::analyze; :>> procedureText = "Three findings, avoidable issues scanned (issue603, issue575). Finding one: the DoD text labelled the passing receipt known-positive and the refused one known-negative, the reverse of the convention every check_report.py fixture uses; the D0388 pair is meaningful either way, but a DoD written against one convention and fixtures against the other made the pair file's two lines need reading twice. NOT A PROCESS CHANGE: the convention is already the code's; the DoD author (me) misapplied it. Finding two: sprint 743's own verify-receipt.toml is gone - the ladder receipt is one file overwritten by every launch, so a receipt dispute older than one ladder is reconstructed from the transcript. Whether the ladder receipt is kept per launch (as the touched log already is, touched-<epoch>.log) is tracked as issue665 with resolver dcLadderReceiptIsKeptPerLaunch (verify-<at>.toml and touched-<at>.toml beside the live files). NOT A PROCESS CHANGE: the retro names the gap; the change is the resolver's, under its own Decision. Finding three, from this sprint's own second verifier run: the receipt check_receipt.py passed (ladder at=1789916017, 918 passed, 0 failed) also carried launch=1789914168 and a test result line quoting 917 passed, 1 failed - the first run's - because the verifier's launch rewrote neither verify-launch.epoch nor verify-touched.out and the renderer holds neither to the ladder's launch (at - seconds); check_receipt.py checks the toml-backed fields only, so the contradiction sat on one page unrefused. Tracked as issue666 with resolver dcRendererHoldsItsAuxiliarySourcesToTheLadder. NOT A PROCESS CHANGE: the controls named are the resolver's; the verdict recorded here rests on the two toml receipts the check read."; }
    // RAN: validate=pass guard=pass clippy=pass probe=pass touched=pass
    part verifierReceiptIsCheckedAgainstTheLadderRetroGateR1 : TestResult { :>> id = "6ba33673-3ed7-4ce4-8c96-e07748d51595"; :>> outcome = VerdictKind::proposed; :>> judgedAgainst = "301b6a71"; :>> judgedAt = "2026-09-20"; :>> judgedBy = "claudeFable5"; }
}
