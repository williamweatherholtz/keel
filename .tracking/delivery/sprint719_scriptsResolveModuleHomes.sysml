// ProjectDeliveryS719 — Sprint 719: Sprint 719: dcScriptsResolveModuleHomesFromTheManifest, the fix for the CI red that sprint 718's landing commit left at d110d0a. One resolver (scripts/module_home.py) answers where a Rust module lives from Cargo.toml's member list; the four probe and census scripts and facts.py resolve through it instead of anchoring keel-cli/src; the binary's proof census widens its corpus to every member the same way; the resolver's probe is a CI script probe whose scan refuses the next anchor. EXECUTE. 2 pts.. EXECUTE. 2 pts.
package ProjectDeliveryS719 {
    private import EngineElement::*;
    private import EngineWork::*;
    private import EngineVerification::*;
    private import EngineRelationships::*;

    #CharteredBy dependency from scriptsResolveModuleHomesStory to d0479;

    part scriptsResolveModuleHomesStory : Story {
        :>> id = "355b4dc1-321e-4056-afe5-1338723eda19";
        :>> title = "Sprint 719: Sprint 719: dcScriptsResolveModuleHomesFromTheManifest, the fix for the CI red that sprint 718's landing commit left at d110d0a. One resolver (scripts/module_home.py) answers where a Rust module lives from Cargo.toml's member list; the four probe and census scripts and facts.py resolve through it instead of anchoring keel-cli/src; the binary's proof census widens its corpus to every member the same way; the resolver's probe is a CI script probe whose scan refuses the next anchor. EXECUTE. 2 pts. (2 pts)";
        :>> createdAt = "2026-09-15"; :>> createdBy = "claudeFable5"; :>> kind = WorkKind::code; :>> priority = WorkPriority::p0; :>> owner = "claudeFable5"; :>> estimatedPoints = 2;
    }

    action def DeliveryRunS719 {
        action storyScriptsResolveModuleHomes;
        verification storyScriptsResolveModuleHomesDoD : Test { :>> id = "cd920968-f1f0-41bc-aa11-829bd5e61931"; :>> method = VerificationMethod::test; :>> procedureText = "DELIVERED BACKLOG ITEMS: dcScriptsResolveModuleHomesFromTheManifest. Done means: scripts/module_home.py exists with module_home, rust_sources and --probe; no line in scripts/**/*.py or .engine/tools/*.py anchors a .rs file under keel-cli/src (the probe's scan, run as a CI script probe); receipt_shape_census.py, guard_dispatch_order.py, issue400_reproduction.py, guard_proof_census.py and facts.py resolve their modules through it; control_proof.rs corpus_bodies walks every workspace member's src; the binary's controlProof and the script's census agree on this tree; every CI script probe passes locally and CI's conclusion at the landing commit reads success"; }
        // RAN: // RAN: python scripts/module_home.py --probe pass this tree: no script anchors a .rs file under keel-cli/src - none module_home probe: 0 failure(s) // RAN: grep -rl module_home scripts .engine/tools --include=*.py scripts/exec_brief/facts.py scripts/module_home.py scripts/probes/guard_dispatch_order.py scripts/probes/issue400_reproduction.py scripts/probes/receipt_shape_census.py .engine/tools/guard_proof_census.py // RAN: gh run list --limit 2 --json conclusion,status,headSha (4d38dd7 = sprint 719's landing commit) [{'conclusion':'success','headSha':'cfb1cb853cb880d72fe8d5d060bfdf5ee688247d','status':'completed'},{'conclusion':'success','headSha':'4d38dd79c72aa3689dfacdef13f8dc7c609c990a','status':'completed'}]
        part storyScriptsResolveModuleHomesDoDR1 : TestResult { :>> id = "5decf975-a46a-4411-968d-ad015907c5b3"; :>> outcome = VerdictKind::pass; :>> judgedAgainst = "4d38dd7"; :>> judgedAt = "2026-09-14"; :>> judgedBy = "claudeFable5"; }
    }

    verification scriptsResolveModuleHomesRefineGate : Test { :>> id = "b79194fb-2255-469f-b802-fb8477f15a03"; :>> title = "Sprint 719 refine gate (DoR)"; :>> createdAt = "2026-09-15"; :>> createdBy = "claudeFable5"; :>> method = VerificationMethod::inspect; :>> procedureText = "DoR: the item is chartered by D0479 (accepted) through its #CharteredBy edge and depends on dcModelAndWriteAreMembers (delivered by sprint 718); sized 2 (one Python module with a probe, six consumer edits, one Rust corpus widening with a fixture test). It is worked ahead of the ranked frontier's first four because CI at HEAD is red on exactly this defect and sprint 718's closeOut gate procedure requires a green conclusion first - a red main blocks every later landing"; }
    // RAN: DoR held: keel show whats-next at d110d0a lists dcModelAndWriteAreMembers delivered and dcScriptsResolveModuleHomesFromTheManifest carries #CharteredBy to d0479 (accepted) and #DependsOn to dcModelAndWriteAreMembers (backlog.sysml edges beside dcOneRepoRootHelper's); sized 2 against the sprint-planning table (one Python module with a fixture probe, six consumer edits, one Rust corpus widening with a fixture test); DoD authored in the item (dcScriptsResolveModuleHomesFromTheManifestDoD) with the D0388 pair named before the tree was read. Worked ahead of the frontier's first four because gh run list at d110d0a read conclusion failure (run 34917362100) and sprint 718's closeOut procedure requires success first.
    part scriptsResolveModuleHomesRefineGateR1 : TestResult { :>> id = "d5ef9a98-cf42-44ca-9d44-fd0e852060b7"; :>> outcome = VerdictKind::proposed; :>> judgedAgainst = "d110d0a"; :>> judgedAt = "2026-09-14"; :>> judgedBy = "claudeFable5"; }
    verification scriptsResolveModuleHomesStandupGate : Test { :>> id = "a4cc0eb6-5826-4815-940f-ae738166d361"; :>> title = "Sprint 719 standup gate"; :>> createdAt = "2026-09-15"; :>> createdBy = "claudeFable5"; :>> method = VerificationMethod::inspect; :>> procedureText = "Order: the resolver with its fixture probe first, run before any consumer changes so the tree scan names every anchor (it named twelve across five files); the consumers; the Rust corpus with its known-positive/known-negative fixture test; release build and the two censuses compared; the CI probe loop run locally; then the record"; }
    // RAN: Order followed as planned: scripts/module_home.py with --probe first (fixture workspace, regex pair, real-tree scan); the scan on the untouched tree named twelve anchors across five files (facts.py 8, receipt_shape_census.py, guard_dispatch_order.py, issue400_reproduction.py, guard_proof_census.py); the five consumers patched (SP/s719/patch_consumers.py, facts.py's cliFamilyCensus fallback now names the module); control_proof.rs corpus_bodies widened over Cargo.toml [workspace] members with the fixture test the_corpus_is_every_workspace_member_not_keel_cli_alone (SP/s719/patch_control_proof.py); cargo build --release, keel-serve.exe and keel-verify.exe refreshed; keel show controls --json controlProof against python .engine/tools/guard_proof_census.py compared; the CI script-probe loop replicated locally (SP/s719/ci_probe_loop.py); issue559, two backlog items and this sprint recorded. One unplanned step: guard instruments-declared refused the new script until fbModuleHome/snModuleHome were authored in engine-instruments.sysml, and guard sprint-closure refused the tree until sprint 718's DoD result (whose criteria name no CI condition) was recorded at d110d0a.
    part scriptsResolveModuleHomesStandupGateR1 : TestResult { :>> id = "d550856f-aabb-409c-813c-51c47006ab37"; :>> outcome = VerdictKind::proposed; :>> judgedAgainst = "d110d0a"; :>> judgedAt = "2026-09-14"; :>> judgedBy = "claudeFable5"; }
    verification scriptsResolveModuleHomesImplementGate : Test { :>> id = "f5cea7dc-4aed-4b29-9ab5-a5621ce62452"; :>> title = "Sprint 719 implement gate"; :>> createdAt = "2026-09-15"; :>> createdBy = "claudeFable5"; :>> method = VerificationMethod::test; :>> procedureText = "The implement gate is the DoD's own probes plus the ladder: python scripts/module_home.py --probe exit 0 with the tree scan clean; the three probe scripts green; cargo test -p keel-cli --lib control_proof green including the_corpus_is_every_workspace_member_not_keel_cli_alone; cargo build --release; keel show controls --json controlProof against .engine/tools/guard_proof_census.py equal on testFunctionsScanned, proven, unproven, undetermined; the CI script-probe loop replicated locally green; keel verify . with the D0388 pair green"; }
    // RAN: // RAN: python scripts/module_home.py --probe -> 0 failure(s) (fixture pair: only_a -> a/src/only_a.rs, deep -> members/b/src/deep/mod.rs; absent -> None; both refused naming 2 crates; the os.path.join and pathlib anchor shapes caught, the resolver call passed; this tree: reverify -> members/keel-write/src/reverify.rs, guards -> keel-cli/src/guards.rs, view -> keel-cli/src/view/mod.rs; no script anchors a .rs file under keel-cli/src); cargo test --release -p keel-cli --lib control_proof -> 8 passed 0 failed including the_corpus_is_every_workspace_member_not_keel_cli_alone; cargo build --release exit 0; keel show controls . --json controlProof testFunctionsScanned 915 proven 32 unproven 26 undetermined 17 against python .engine/tools/guard_proof_census.py -> 915 scanned, 58 named (32 + 26), 17 named nowhere - EQUAL; SP/s719/ci_probe_loop.py (the D0394 discovery replicated) -> 6 script probe(s) passed; keel verify . --probe 'python scripts/module_home.py --probe,cargo test --release -p keel-cli --lib the_corpus_is_every_workspace_member_not_keel_cli_alone' -> pass, every rung green in 605 s (validate 0 s, guard 5 s, clippy 34 s, probe 1 s, touched 564 s), keel suite --touched 834 passed 0 failed in 562 s, receipt .keel/metrics/verify-receipt.toml. Two earlier ladder runs stopped at guard: instruments-declared on the undeclared scripts/module_home.py (Sensor snModuleHome authored) and sprint-closure on sprint 718's Story without a DoD result (recorded at d110d0a).
    part scriptsResolveModuleHomesImplementGateR1 : TestResult { :>> id = "f1cee4db-0553-4599-853c-f841ebaab08c"; :>> outcome = VerdictKind::pass; :>> judgedAgainst = "d110d0a"; :>> judgedAt = "2026-09-14"; :>> judgedBy = "claudeFable5"; }
    verification scriptsResolveModuleHomesReviewGate : Test { :>> id = "727e13cf-d3fd-42cd-9c18-bf757f40cc7b"; :>> title = "Sprint 719 review gate — three passes per D0172"; :>> createdAt = "2026-09-15"; :>> createdBy = "claudeFable5"; :>> method = VerificationMethod::inspect; :>> procedureText = "Three passes (D0172). Correctness: module_home refuses ambiguity rather than picking a crate, returns None rather than raising for an absent module so each caller keeps its own failure text, and reads the member list from the manifest so a new member needs no edit; the Rust corpus falls back to keel-cli/src only when no root manifest exists, so an engine run at a foreign root still says why. Honesty: the two D0360 instruments disagreed after the script alone was widened (58/17 against 55/20) and agree again only after the binary's corpus moved too - widening one instrument and not the other would have left a false disagreement standing; facts.py's cliFamilyCensus had been null on every brief since sprint 714 took cli_facts.rs into keel-schema, and is computed again. Scope: no view, guard or write-path change; modgraph.py keeps keel-cli/src as its documented default because its graph is of that crate's modules and a moved module leaves the graph rather than breaking it. Control added (D0047): module_home.py --probe scans for the anchor shape and runs in the CI script-probe step"; }
    // RAN: Three passes (D0172) over the diff at d110d0a plus the working tree. Correctness: module_home() raises AmbiguousModule naming both homes on two hits and returns None on none (scripts/module_home.py; probe cases both_rs ambiguity and MISSING); crate_dirs reads Cargo.toml [workspace] members through tomllib with glob expansion and normpath (the first probe run failed on mixed separators for members/keel-write and was fixed there); control_proof.rs corpus_bodies falls back to keel-cli/src only with no root manifest, and the fixture test proves undetermined()==1 without the manifest and proven()==1 with it. Honesty: after the script alone was widened the two D0360 instruments disagreed (census 58 named / 17 unnamed vs binary 55 / 20); both now read one corpus and agree at 915 test functions / 32 / 26 / 17 - widening one instrument and not the other would have left a false disagreement standing; facts.py's cliFamilyCensus had been null on every brief since sprint 714 took cli_facts.rs into keel-schema and is computed again. Scope: no view, guard or write-path change; modgraph.py keeps keel-cli/src as its documented default because its graph is of that crate's modules. Control added (D0047): module_home.py --probe scans scripts/**/*.py and .engine/tools/*.py for the two anchor shapes and runs in the CI script-probe step (D0394); declared as Sensor snModuleHome with its known failure modes (a third anchor shape passes the scan - a miss, never a false positive).
    part scriptsResolveModuleHomesReviewGateR1 : TestResult { :>> id = "5aa4abfb-02d2-4cf8-86d4-3a8b51e8d0c3"; :>> outcome = VerdictKind::proposed; :>> judgedAgainst = "d110d0a"; :>> judgedAt = "2026-09-14"; :>> judgedBy = "claudeFable5"; }
    verification scriptsResolveModuleHomesCloseOutGate : Test { :>> id = "77669d43-ab5b-4b89-bec8-75b2f205a990"; :>> title = "Sprint 719 closeOut gate (autonomous, D0049)"; :>> createdAt = "2026-09-15"; :>> createdBy = "claudeFable5"; :>> method = VerificationMethod::inspect; :>> procedureText = "Close-out at the landing commit after the CI conclusion reads success: git status -sb level with origin, gh run conclusion, the DoD result recorded against dcScriptsResolveModuleHomesFromTheManifestDoD at that sha; sprint 718's closeOut and retro gates recorded at the same sha, naming the red run this sprint resolved"; }
    // RAN: Close-out read at cfb1cb8: git status -sb level with origin; gh run conclusion success at 4d38dd7 (landing) and cfb1cb8; the DoD result for storyScriptsResolveModuleHomes recorded against 4d38dd7 with the module_home probe, the grep of the six consumers and the CI conclusion as its receipt; sprint 718 closeOut and retro recorded at the same sitting naming the red run (d110d0a) this sprint resolved.
    part scriptsResolveModuleHomesCloseOutGateR1 : TestResult { :>> id = "05fcfb54-1623-4db3-8d0c-0c170f426cd8"; :>> outcome = VerdictKind::proposed; :>> judgedAgainst = "cfb1cb8"; :>> judgedAt = "2026-09-14"; :>> judgedBy = "claudeFable5"; }
    verification scriptsResolveModuleHomesRetroGate : Test { :>> id = "06216701-c8c5-48b3-bef4-257dcd9b94ba"; :>> title = "Sprint 719 retro gate (autonomous, D0049)"; :>> createdAt = "2026-09-15"; :>> createdBy = "claudeFable5"; :>> method = VerificationMethod::analyze; :>> procedureText = "Retro, avoidable-issue scan over the sprint: (1) the standup line of sprint 718 named receipt_shape_census.py:14 as a path that followed the move - that was the docstring; the constant three lines below the imports did not, so a grep for the file name was read as a grep for the anchor. The control that catches the shape rather than the name is this sprint's scan - no new item. (2) The CI script-probe step (D0394) is the only place the probe scripts run; keel verify's ladder does not include them, so the defect reached the remote before anything local fired. A local rung for the script probes is a process change to the ladder - tracked as dcScriptProbesRunInTheVerifyLadder (chartered by D0476), not done here. (3) The two D0360 instruments agreed while both were wrong the same way; agreement is not correctness, and the census reference must read a corpus it derives (the manifest) rather than one it names - fixed here, no new item. (4) facts.py emitted cliFamilyCensus as null on every brief built since sprint 714 moved cli_facts.rs the same morning (87085d2), under an except OSError whose how-text read as a computed absence; a null with a reason is honest only when the reason is the fact's, not a missing file's - the resolver returns None and the caller's how-text now names the module and the list it was resolved against, no new item. (5) AVOIDABLE: the Review and DoD claims about facts.py were read from the edit, not from a run - facts.py died at HEAD on that edit; issue560 (High), resolver dcInstrumentAnswersCarryTheirSourceHash, delivered by sprint 720 (an answer carries its instrument hash and the reader refuses drift)"; }
    // RAN: Retro read: the gate text names the avoidable-issue scan (findings 1-5; finding 5 added at this sitting: facts.py claims read from the edit, not a run - issue560 High, resolver dcInstrumentAnswersCarryTheirSourceHash, sprint 720). Finding 6, no new item: the Review result was recorded before the Implement result in this file and the ladder found reds the record had not - the D0476 ladder already stops at the first red.
    part scriptsResolveModuleHomesRetroGateR1 : TestResult { :>> id = "b43457a8-cffd-44b7-b711-cec46ae69510"; :>> outcome = VerdictKind::proposed; :>> judgedAgainst = "cfb1cb8"; :>> judgedAt = "2026-09-14"; :>> judgedBy = "claudeFable5"; }
}
