// ProjectDeliveryS753 — Sprint 753: A sprint Story names the backlog item it delivers with a #Delivers edge authored at prep, and the sprint-closure guard holds every delivered item to a DoD result once a later sprint exists (D0515; issue563, issue589). EXECUTE. 3 pts.
package ProjectDeliveryS753 {
    private import EngineElement::*;
    private import EngineWork::*;
    private import EngineVerification::*;
    private import EngineRelationships::*;

    #CharteredBy dependency from sprintNamesTheItemItDeliversStory to d0515;
    #Delivers dependency from sprintNamesTheItemItDeliversStory to dcSprintNamesTheItemItDelivers;

    part sprintNamesTheItemItDeliversStory : Story {
        :>> id = "db8573a0-6b8a-410f-adb2-20aa1a22d75a";
        :>> title = "Sprint 753: A sprint Story names the backlog item it delivers with a #Delivers edge authored at prep, and the sprint-closure guard holds every delivered item to a DoD result once a later sprint exists (D0515; issue563, issue589) (3 pts)";
        :>> createdAt = "2026-09-20"; :>> createdBy = "claudeFable5"; :>> kind = WorkKind::code; :>> priority = WorkPriority::p0; :>> owner = "claudeFable5"; :>> estimatedPoints = 3;
    }

    action def DeliveryRunS753 {
        action storySprintNamesTheItemItDelivers;
        verification storySprintNamesTheItemItDeliversDoD : Test { :>> id = "71f495a3-a39f-42ba-8524-a6e1f21ecc8c"; :>> method = VerificationMethod::test; :>> procedureText = "DELIVERED BACKLOG ITEM: dcSprintNamesTheItemItDelivers. DONE MEANS: the task's DoD passes as written - schema/core relationships.sysml declares metadata def Delivers beside CharteredBy; record sprint --fill takes a delivers key (comma-separated backlog actions, each a declared action or the write refuses by name) and writes one #Delivers edge per item beside the charter edge (scaffold.rs, unit pair: two items write two edges; an undeclared item and a missing key are refused before the write); sprint_closure in members/keel-guards/src/sprints.rs reads the edges - a delivered item whose DoD has no TestResult anywhere under .tracking is a violation naming the sprint and the item once a later sprint exists, and a Story recorded on or after 2026-09-18 with no #Delivers edge is a violation at once; the arming probe sprint_closure_actually_bites.rs carries the D0388 pair (sprint 720 delivering an open item with 721 present is red naming the item; the same with the item's DoD result is green) and the date pair; the sprint-planning skill's DoR names the edge beside the charter edge; guards.md, usage.md, guard-constraints.sysml and control-map.sysml carry the clause; the guard count stays 76. The thirteen sprints recorded on or after 2026-09-18 (740-752) carry #Delivers edges authored from each file's own DELIVERED BACKLOG ITEM(S) line - 23 edges, every target a declared action, the sprint's stated fact and not a guess from a slug. Verified by the verifier ladder and keel gate guard green at the landing tree."; }
        // RAN: keel suite --touched: pass - 925 passed in 776s over [83 binaries]; slowest land_gate land_refuses_to_push_a_workspace_carrying_a_broken_project 219.8s; 0 failed, failing []; receipt .keel/metrics/touched-receipt.toml
        part storySprintNamesTheItemItDeliversDoDR1 : TestResult { :>> id = "520e3683-3768-4af8-8bb3-6305c4bed855"; :>> outcome = VerdictKind::pass; :>> judgedAgainst = "e5ee275b"; :>> judgedAt = "2026-09-20"; :>> judgedBy = "claudeFable5"; }
    }

    verification sprintNamesTheItemItDeliversRefineGate : Test { :>> id = "1e31f759-d8c0-4c96-8efa-e3a32abe8bc6"; :>> title = "Sprint 753 refine gate (DoR)"; :>> createdAt = "2026-09-20"; :>> createdBy = "claudeFable5"; :>> method = VerificationMethod::inspect; :>> procedureText = "One backlog item, sized 3: a frozen-schema metadata def under an accepted CR (D0515), a scaffold key with validation, a guard clause reading a second corpus, five unit tests across two crates, a skill paragraph, four doc rows and a thirteen-file backfill of stated facts. DoR: estimatedPoints 3; #CharteredBy d0515 (accepted 2026-09-18 by wweatherholtz, judgedAgainst 4d00c1bc); #Delivers dcSprintNamesTheItemItDelivers - this sprint is the first to carry the edge it introduces; no blocking dependency; the DoD exists in the backlog with its own VERIFY clause."; }
    // RAN: keel suite --touched: pass - 925 passed in 776s over [83 binaries]; slowest land_gate land_refuses_to_push_a_workspace_carrying_a_broken_project 219.8s; 0 failed, failing []; receipt .keel/metrics/touched-receipt.toml
    part sprintNamesTheItemItDeliversRefineGateR1 : TestResult { :>> id = "59801e85-2e86-42fc-bf3c-0840eed52d4e"; :>> outcome = VerdictKind::proposed; :>> judgedAgainst = "e5ee275b"; :>> judgedAt = "2026-09-20"; :>> judgedBy = "claudeFable5"; }
    verification sprintNamesTheItemItDeliversStandupGate : Test { :>> id = "6fce86fe-4431-41cf-960f-b7b4c4f56701"; :>> title = "Sprint 753 standup gate"; :>> createdAt = "2026-09-20"; :>> createdBy = "claudeFable5"; :>> method = VerificationMethod::inspect; :>> procedureText = "The edge is a typed fact beside the charter edge, never a parse of the DoD's prose line (the rejected fork on the brief). The missing-edge clause applies to every sprint including the newest because the edge is authored at prep - its absence is a prep omission, not an in-progress state; the unstamped-task clause keeps the newest exempt as D0260 wrote it. The DoD result of a delivered item lives beside its DoD in the backlog, so the guard reads result names across the whole .tracking corpus once. Sprints before 2026-09-18 are history and carry no edge; the thirteen since then state their items in their DoD line and now carry them as edges. Impediment: none."; }
    // RAN: keel suite --touched: pass - 925 passed in 776s over [83 binaries]; slowest land_gate land_refuses_to_push_a_workspace_carrying_a_broken_project 219.8s; 0 failed, failing []; receipt .keel/metrics/touched-receipt.toml
    part sprintNamesTheItemItDeliversStandupGateR1 : TestResult { :>> id = "dab66fb2-8996-44a2-833a-73eb143f5b35"; :>> outcome = VerdictKind::proposed; :>> judgedAgainst = "e5ee275b"; :>> judgedAt = "2026-09-20"; :>> judgedBy = "claudeFable5"; }
    verification sprintNamesTheItemItDeliversImplementGate : Test { :>> id = "f4fe524c-0487-4936-858c-94383f3c3aec"; :>> title = "Sprint 753 implement gate"; :>> createdAt = "2026-09-20"; :>> createdBy = "claudeFable5"; :>> method = VerificationMethod::test; :>> procedureText = "cargo test -p keel-write --lib scaffold: 8 passed (two new). cargo test -p keel-cli --test sprint_closure_actually_bites: 7 passed (three new, the live-tree probe included). keel gate guard sprint-closure . PASS 774 scanned 0 violations at the working tree; gate validate 870 clean; check-engine clean; control-map-reconciled PASS 28 scanned after the gSprintClosure row; sync-claude --check matches. Release binary rebuilt and copied to keel-serve.exe; this sprint's record was written by that binary from a fill carrying the delivers key."; }
    // RAN: keel suite --touched: pass - 925 passed in 776s over [83 binaries]; slowest land_gate land_refuses_to_push_a_workspace_carrying_a_broken_project 219.8s; 0 failed, failing []; receipt .keel/metrics/touched-receipt.toml
    part sprintNamesTheItemItDeliversImplementGateR1 : TestResult { :>> id = "69e71abe-636e-45d0-9543-ffb90095c576"; :>> outcome = VerdictKind::pass; :>> judgedAgainst = "e5ee275b"; :>> judgedAt = "2026-09-20"; :>> judgedBy = "claudeFable5"; }
    verification sprintNamesTheItemItDeliversReviewGate : Test { :>> id = "699e6366-5605-4dd4-868a-454b2049f756"; :>> title = "Sprint 753 review gate — three passes per D0172"; :>> createdAt = "2026-09-20"; :>> createdBy = "claudeFable5"; :>> method = VerificationMethod::inspect; :>> procedureText = "Three passes per D0172. Code read back: delivered_items splits the fill on commas and drops empties; backlog_action_exists scans .tracking for `action <name>;`; sprint_with writes the edges immediately after the charter line; delivers_targets parses `#Delivers dependency from X to Y;` by prefix and ` to `; story_created_at takes the first createdAt after `: Story {`; the guard collects all_results over collect_sysml(.tracking) once and checks `<item>DoD` as a result-name prefix. Ceremony: D0515 accepted with a Person-judged confirmation; guard count unchanged at 76 so doc-guard-count holds; the schema change rides D0515's #ProspectiveChange as the co-committed Decision, commit prefix CR. Doc-sync in the same commit: guards.md sprint-closure row and marker vocabulary, usage.md relationship row, guard-constraints comment, control-map gSprintClosure bound to ehz4, sprint-planning SKILL.md step 4c and its .claude copy. FINDING for the retro: D0515's consequences said control-map.sysml carries the clause on the existing row - no row for sprint-closure existed; seventeen other guards have none either."; }
    // RAN: keel suite --touched: pass - 925 passed in 776s over [83 binaries]; slowest land_gate land_refuses_to_push_a_workspace_carrying_a_broken_project 219.8s; 0 failed, failing []; receipt .keel/metrics/touched-receipt.toml
    part sprintNamesTheItemItDeliversReviewGateR1 : TestResult { :>> id = "509b47c1-39ae-4832-87dc-302fc5417a7c"; :>> outcome = VerdictKind::proposed; :>> judgedAgainst = "e5ee275b"; :>> judgedAt = "2026-09-20"; :>> judgedBy = "claudeFable5"; }
    verification sprintNamesTheItemItDeliversCloseOutGate : Test { :>> id = "8a0b2e5d-fd5c-44e8-ba96-48fa2a85bcf4"; :>> title = "Sprint 753 closeOut gate (autonomous, D0049)"; :>> createdAt = "2026-09-20"; :>> createdBy = "claudeFable5"; :>> method = VerificationMethod::inspect; :>> procedureText = "The task's DoD result and the six gate results are recorded from the verifier's rendered receipt; issue563 and issue589 resolve when the DoD passes. Doc-sync rode the change. The backfill script stays in the scratchpad: it ran once, dry-run then apply, reconciled 13 files and 23 edges, and re-ran idempotent at zero."; }
    // RAN: keel suite --touched: pass - 925 passed in 776s over [83 binaries]; slowest land_gate land_refuses_to_push_a_workspace_carrying_a_broken_project 219.8s; 0 failed, failing []; receipt .keel/metrics/touched-receipt.toml
    part sprintNamesTheItemItDeliversCloseOutGateR1 : TestResult { :>> id = "a9dbdf99-e338-4ed9-8abb-4caaff8eb346"; :>> outcome = VerdictKind::proposed; :>> judgedAgainst = "e5ee275b"; :>> judgedAt = "2026-09-20"; :>> judgedBy = "claudeFable5"; }
    verification sprintNamesTheItemItDeliversRetroGate : Test { :>> id = "4d9cc01f-1f22-4ad4-aec7-7bd0c2098a6e"; :>> title = "Sprint 753 retro gate (autonomous, D0049)"; :>> createdAt = "2026-09-20"; :>> createdBy = "claudeFable5"; :>> method = VerificationMethod::analyze; :>> procedureText = "One finding, avoidable issues scanned (issue011). Finding: control-map-reconciled's guards.md row claims every enforced guard is a SystemSafetyConstraint bound to a hazard, but the code (members/keel-guards/src/enforcement.rs control_map_reconciled) reconciles control-events.toml against declared controls only; seventeen of the 76 guards had no `guard: <name>` row in control-map.sysml and the guard passed, and D0515 was written believing the sprint-closure row existed. Tracked as issue662 with resolver dcEveryGuardHasAControlMapRow: the guard gains a clause holding every GUARD_NAMES entry to a control-map row bound to a hazard, and the doc row says what the code does. NOT A PROCESS CHANGE: this retro names the item; the clause itself is that item's CR."; }
    // RAN: keel suite --touched: pass - 925 passed in 776s over [83 binaries]; slowest land_gate land_refuses_to_push_a_workspace_carrying_a_broken_project 219.8s; 0 failed, failing []; receipt .keel/metrics/touched-receipt.toml
    part sprintNamesTheItemItDeliversRetroGateR1 : TestResult { :>> id = "e3e7643f-3208-488d-a4e1-a6572646d171"; :>> outcome = VerdictKind::proposed; :>> judgedAgainst = "e5ee275b"; :>> judgedAt = "2026-09-20"; :>> judgedBy = "claudeFable5"; }
}
