// ProjectDeliveryS750 — Sprint 750: main.rs is argument dispatch: every verb body moves to the least member that can hold it by one transform, and the binary keeps only main, cmd_show and its tests (D0479, the last extraction). EXECUTE. 8 pts.
package ProjectDeliveryS750 {
    private import EngineElement::*;
    private import EngineWork::*;
    private import EngineVerification::*;
    private import EngineRelationships::*;

    #CharteredBy dependency from keelCliIsThinDispatchStory to d0479;
    #Delivers dependency from keelCliIsThinDispatchStory to dcKeelCliIsThinDispatch;

    part keelCliIsThinDispatchStory : Story {
        :>> id = "ffa7bea0-7e8e-4c3d-aee2-09764befc029";
        :>> title = "Sprint 750: main.rs is argument dispatch: every verb body moves to the least member that can hold it by one transform, and the binary keeps only main, cmd_show and its tests (D0479, the last extraction) (8 pts)";
        :>> createdAt = "2026-09-19"; :>> createdBy = "claudeFable5"; :>> kind = WorkKind::code; :>> priority = WorkPriority::p0; :>> owner = "claudeFable5"; :>> estimatedPoints = 8;
    }

    action def DeliveryRunS750 {
        action storyKeelCliIsThinDispatch;
        verification storyKeelCliIsThinDispatchDoD : Test { :>> id = "6a54e45c-5a11-4675-89b9-0ea8a2304447"; :>> method = VerificationMethod::test; :>> procedureText = "DELIVERED BACKLOG ITEM: dcKeelCliIsThinDispatch. DONE MEANS: the task's DoD passes as written - scripts/extract_verbs.py (dry-run default, --apply, idempotent on the first member file existing) moves 126 of main.rs's 129 top-level items into fourteen member verb files, placing each by the least member scripts/verb_homes.py computes (an item every member can hold follows its callers; cmd_sync_claude is placed by table), prints the reconciliation line before it writes, and refuses a slice whose start would strand a preceding doc line or attribute or whose tail ends in one (issue601); keel-cli/src/lib.rs re-exports the moved verbs as keel_cli::verbs; main.rs imports exactly the names it dispatches; nine manifests gain the direct dependencies the moved code names; keel --help is byte-identical to the pre-pass render; verb_homes --check exits 0 (3 items, 0 that only keel-cli can hold); main.rs is under 800 lines and keel-cli/src holds no module over 400; a touch of one member rebuilds that member, its dependents and keel-cli only; clippy -D warnings, the full guard set and the touched test set pass."; }
        // RAN: LADDER: outcome=pass stopped_at=none
        part storyKeelCliIsThinDispatchDoDR1 : TestResult { :>> id = "65af5a9f-79ff-4ee5-8731-8b3b12e15ecf"; :>> outcome = VerdictKind::pass; :>> judgedAgainst = "9453faf5"; :>> judgedAt = "2026-09-19"; :>> judgedBy = "claudeFable5"; }
    }

    verification keelCliIsThinDispatchRefineGate : Test { :>> id = "ac453ee2-b01f-43aa-ba82-7fc113783dff"; :>> title = "Sprint 750 refine gate (DoR)"; :>> createdAt = "2026-09-19"; :>> createdBy = "claudeFable5"; :>> method = VerificationMethod::inspect; :>> procedureText = "One backlog item, sized 8: a Python transform over 4,500 lines of Rust with placement, import rewriting and manifest edits, plus one process-change Decision (D0532) because five verb bodies land under the D0504 locked prefix. Ready when verb_homes names every item's home with no item left to keel-cli, and the slice-check pair (slice_pos.rs refused naming line 3; slice_neg.rs passes) is written before the transform reads the tree."; }
    // RAN: LADDER: validate=pass
    part keelCliIsThinDispatchRefineGateR1 : TestResult { :>> id = "2bcb6b3c-f2ad-4232-9aae-8e22fd8820b5"; :>> outcome = VerdictKind::proposed; :>> judgedAgainst = "9453faf5"; :>> judgedAt = "2026-09-19"; :>> judgedBy = "claudeFable5"; }
    verification keelCliIsThinDispatchStandupGate : Test { :>> id = "c7a63059-575e-46a4-82e2-a53dccc078fb"; :>> title = "Sprint 750 standup gate"; :>> createdAt = "2026-09-19"; :>> createdBy = "claudeFable5"; :>> method = VerificationMethod::inspect; :>> procedureText = "The transform is one script with one reconciliation line; every rewrite class is counted and the count is read back before --apply. Placement by reach, not by name: a verb's home is the lowest member whose dependency closure covers what the body calls, so the D0479 layering holds by construction and cargo tree is the check. The guard verbs landing in a locked directory is the lock meeting code it should always have covered; D0532 records that and is held for the human."; }
    // RAN: LADDER: guard=pass
    part keelCliIsThinDispatchStandupGateR1 : TestResult { :>> id = "c0654c65-ea79-49fc-870f-3b68520ac0c6"; :>> outcome = VerdictKind::proposed; :>> judgedAgainst = "9453faf5"; :>> judgedAt = "2026-09-19"; :>> judgedBy = "claudeFable5"; }
    verification keelCliIsThinDispatchImplementGate : Test { :>> id = "84444f88-86c3-4c4d-bce8-1dc447e709b0"; :>> title = "Sprint 750 implement gate"; :>> createdAt = "2026-09-19"; :>> createdBy = "claudeFable5"; :>> method = VerificationMethod::test; :>> procedureText = "cargo build --release exit 0; cargo clippy --workspace --all-targets -- -D warnings exit 0; cmp of keel --help before and after identical; verb_homes --check 3 items, 0 that only keel-cli can hold; wc -l keel-cli/src/main.rs 356, lib.rs 151; the slice check on the applied main.rs passes (3 slices); a touch of members/keel-suite/src/suite_verbs.rs recompiles keel-suite, keel-hooks, keel-process, keel-serve and keel-cli with 14 members Fresh, which is cargo tree -i keel-suite exactly; gate validate 867 files clean; gate check-engine clean; the full guard set passes with process-change authorised by the co-committed D0532; sync-claude --check matches."; }
    // RAN: LADDER: clippy=pass
    part keelCliIsThinDispatchImplementGateR1 : TestResult { :>> id = "ecbcbc0b-e860-4c70-b192-2af393cac9b3"; :>> outcome = VerdictKind::pass; :>> judgedAgainst = "9453faf5"; :>> judgedAt = "2026-09-19"; :>> judgedBy = "claudeFable5"; }
    verification keelCliIsThinDispatchReviewGate : Test { :>> id = "64b55637-21cc-477c-a1ed-91673252167e"; :>> title = "Sprint 750 review gate — three passes per D0172"; :>> createdAt = "2026-09-19"; :>> createdBy = "claudeFable5"; :>> method = VerificationMethod::inspect; :>> procedureText = "main.rs read back after the transform: the header, the pruned imports, one wrapped use keel_cli::verbs import of the dispatched names, cmd_show, main and the test module; no fn cmd_* remains. Each member verb file opens with the D0479 header naming its verbs and the allow of the three pub-visibility lints; no member file names a crate its manifest does not list directly. The reconciliation line reads 129 items = 126 moved + 3 stay, 4154 lines moved into 14 member files, 129 slice starts checked, and a second --apply refuses as already applied."; }
    // RAN: LADDER: probe=pass
    part keelCliIsThinDispatchReviewGateR1 : TestResult { :>> id = "04123e04-92e8-41b7-ae70-0d9b62a49585"; :>> outcome = VerdictKind::proposed; :>> judgedAgainst = "9453faf5"; :>> judgedAt = "2026-09-19"; :>> judgedBy = "claudeFable5"; }
    verification keelCliIsThinDispatchCloseOutGate : Test { :>> id = "439ca514-010d-42e2-be98-27865f6f98e6"; :>> title = "Sprint 750 closeOut gate (autonomous, D0049)"; :>> createdAt = "2026-09-19"; :>> createdBy = "claudeFable5"; :>> method = VerificationMethod::inspect; :>> procedureText = "The task's DoD result is recorded from the verifier's receipt; D0532 is proposed and held for the human's word; the stale registry row ceHookDispatch is repointed to members/keel-hooks/src/lib.rs in this commit and its control is tracked as dcCodeRegistryRowsFollowTheCode."; }
    // RAN: LADDER: touched=pass
    part keelCliIsThinDispatchCloseOutGateR1 : TestResult { :>> id = "9ece8610-ca7e-4d72-80f5-fa66921d0232"; :>> outcome = VerdictKind::proposed; :>> judgedAgainst = "9453faf5"; :>> judgedAt = "2026-09-19"; :>> judgedBy = "claudeFable5"; }
    verification keelCliIsThinDispatchRetroGate : Test { :>> id = "510af66e-159d-4bbc-93e4-bbe7d801028a"; :>> title = "Sprint 750 retro gate (autonomous, D0049)"; :>> createdAt = "2026-09-19"; :>> createdBy = "claudeFable5"; :>> method = VerificationMethod::analyze; :>> procedureText = "Four findings, avoidable issues scanned (issue011). Finding: verb_homes.strip blanked strings line by line, so a const whose string spans lines hid the word process and the transform imported std::process into a member that never calls it; the placement table it feeds was unaffected (byte-identical before and after) but the import pool was not. Control landed this sprint: strip is a character walk over strings, raw strings, byte strings, char literals and nested block comments, keeping format captures. Finding: a doc block stranded above a use line since sprint 740 (write_engine_file) would have moved into a member as a doc that documents nothing, and clippy found it, not the transform; control landed this sprint: the slice check refuses a slice whose tail is a doc line or attribute, with its own pair. Finding: the code registry named keel-cli/src/main.rs as cmd_hook's file for eleven sprints because no guard reads filePath and the file still existed; the row is fixed here and the control is tracked as dcCodeRegistryRowsFollowTheCode, added in this commit. Finding: seven source-scanning tests in four files (keel-write write_path_registry_tests x2, keel-guards hardening every_positional_read_is_flag_guarded and no_write_path_defaults_a_provenance_date, keel-cli capability_refusal_bites x3, no_op_writes_lose_nothing x1) read keel-cli/src/main.rs by name for fn sites, routers, positional reads, date defaults and surface writes; the move emptied that file of all of them, three went red and four passed over an empty scan - a control that names its subject's file goes silent when the subject moves, and the first verifier pass surfaced only the red one. Control landed this sprint: keel_fs::test_support::verb_sources lists the verb sources from the tree (main.rs plus every members/*/src/*_verbs.rs, each read recorded, D0481), source_holding finds the one holding a router, every re-aimed scan asserts a non-zero floor so it cannot pass over nothing, and a failure names file:line. Finding, already tracked: the second verifier receipt read DISCREPANCIES: NONE over its own LADDER line outcome=fail touched=fail failed=2 - issue490 recurring for the third time (sprints 676, 745, 750), resolver dcVerifierReceiptOutcomeIsRenderedNotTyped still open; the primary read the ladder rows, not the summary line. The guard verbs landing under the D0504 prefix is not a finding: it is the lock working, recorded as D0532."; }
    // RAN: LADDER: outcome=pass stopped_at=none
    part keelCliIsThinDispatchRetroGateR1 : TestResult { :>> id = "81efaadb-4e4a-4126-baf4-4dbad6da1400"; :>> outcome = VerdictKind::proposed; :>> judgedAgainst = "9453faf5"; :>> judgedAt = "2026-09-19"; :>> judgedBy = "claudeFable5"; }
}
