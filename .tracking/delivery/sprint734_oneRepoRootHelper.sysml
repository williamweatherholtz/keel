// ProjectDeliveryS734 — Sprint 734: one repository-root walk for every test - dcOneRepoRootHelper. keel_fs::test_support::repo_root (the first ancestor of the crate manifest holding .git) replaces the ten local fn repo_root copies in nine member files (github, cli_surface, activation, fingerprint, orient, queries, arch, view/mod, write twice), keel-cli/src's eight remaining cwd-relative test anchors (adherence, attestation, main, process_cmd twice, reports, serve, workspace) repoint to it, and the touched.rs scan no_member_test_anchors_on_a_cwd_relative_path widens from members/*/src to keel-cli/src as well, so the next D0479 move carries no anchor into its member and inherits no path fix. Resolves issue557. EXECUTE. 3 pts.
package ProjectDeliveryS734 {
    private import EngineElement::*;
    private import EngineWork::*;
    private import EngineVerification::*;
    private import EngineRelationships::*;

    #CharteredBy dependency from oneRepoRootHelperStory to d0479;

    part oneRepoRootHelperStory : Story {
        :>> id = "a0f31a4d-f1e6-4c09-bd9e-ff9be2549887";
        :>> title = "Sprint 734: one repository-root walk for every test - dcOneRepoRootHelper. keel_fs::test_support::repo_root (the first ancestor of the crate manifest holding .git) replaces the ten local fn repo_root copies in nine member files (github, cli_surface, activation, fingerprint, orient, queries, arch, view/mod, write twice), keel-cli/src's eight remaining cwd-relative test anchors (adherence, attestation, main, process_cmd twice, reports, serve, workspace) repoint to it, and the touched.rs scan no_member_test_anchors_on_a_cwd_relative_path widens from members/*/src to keel-cli/src as well, so the next D0479 move carries no anchor into its member and inherits no path fix. Resolves issue557 (3 pts)";
        :>> createdAt = "2026-09-17"; :>> createdBy = "claudeFable5"; :>> kind = WorkKind::code; :>> priority = WorkPriority::p0; :>> owner = "claudeFable5"; :>> estimatedPoints = 3;
    }

    action def DeliveryRunS734 {
        action storyOneRepoRootHelper;
        verification storyOneRepoRootHelperDoD : Test { :>> id = "2dc83708-31cc-411f-a715-0ad02a9069c9"; :>> method = VerificationMethod::test; :>> procedureText = "DELIVERED BACKLOG ITEMS: dcOneRepoRootHelper. DONE MEANS: members/keel-fs/src/test_support.rs holds the one pub fn repo_root (doc-hidden, must_use, expect allowed as a fixture), exported as keel_fs::test_support; grep -rn 'fn repo_root' keel-cli/src members/*/src names that one definition; every former local copy is a use keel_fs::test_support::repo_root line at the head of its test module (keel-github and keel-schema gain keel-fs as a dev-dependency, the shape keel-actor already carries); no keel-cli/src line matches the four anchor shapes (Path::new('..'), read_to_string('src/, CARGO_MANIFEST_DIR')).join('..'), read_to_string('../); the scan's population is test_bearing_sources minus keel-cli/tests and it asserts keel-cli/src/touched.rs is in it; python scripts/modgraph.py --check holds. Known-positive, chosen before the tree is read: the widened scan over this tree reports nothing and one fn repo_root is defined (pos734.py). Known-negative: a planted keel-cli/src/zz_probe734.rs carrying Path::new('..') makes the scan red naming that file and line, and is removed on every path (neg734.py). The DoD's site counts were authored at sprint 731: the tenth helper (view/mod.rs) came with sprint 732 and guards.rs's seven and hardening.rs's five anchors left for members/keel-guards under the member scan in sprint 733, leaving eight in keel-cli/src - the probe, not the count, is the contract."; }
        // RAN: passed=904 failed=0 seconds=791
        part storyOneRepoRootHelperDoDR1 : TestResult { :>> id = "df84b313-5afe-46af-bfe1-24443b1d9939"; :>> outcome = VerdictKind::pass; :>> judgedAgainst = "e3714e3"; :>> judgedAt = "2026-09-17"; :>> judgedBy = "claudeFable5"; }
    }

    verification oneRepoRootHelperRefineGate : Test { :>> id = "f96c2cab-ca8e-4777-88eb-63c1930c93a9"; :>> title = "Sprint 734 refine gate (DoR)"; :>> createdAt = "2026-09-17"; :>> createdBy = "claudeFable5"; :>> method = VerificationMethod::inspect; :>> procedureText = "DoR: dcOneRepoRootHelper is the first line of keel show whats-next at e3714e3, moved to the head of the D0479 cluster by sprint 733's retro (issue583: the recurrence it predicted was paid a second time). Chartered by D0479 (accepted) through its #CharteredBy edge; #DependsOn dcModelAndWriteAreMembers, done. Sized 3 - one new module in a leaf member, the committed script scripts/collapse_repo_root.py over nine files and two manifests, eight one-line repoints, one widened scan with its population assertion, and the D0388 pair as two scripts. Blocking dependencies: none."; }
    // RAN: outcome=pass stopped_at=none
    part oneRepoRootHelperRefineGateR1 : TestResult { :>> id = "98d363d3-d0f5-4378-9f21-81633627c77a"; :>> outcome = VerdictKind::proposed; :>> judgedAgainst = "e3714e3"; :>> judgedAt = "2026-09-17"; :>> judgedBy = "claudeFable5"; }
    verification oneRepoRootHelperStandupGate : Test { :>> id = "4c161347-be92-40d4-83f4-8c3e52947eb6"; :>> title = "Sprint 734 standup gate"; :>> createdAt = "2026-09-17"; :>> createdBy = "claudeFable5"; :>> method = VerificationMethod::inspect; :>> procedureText = "Owner claudeFable5. Blocker: none - brief 40 landed in e3714e3, no ladder or land is running. Order: (1) members/keel-fs/src/test_support.rs and its own test (the root holds .git, Cargo.toml and .engine, and this crate sits two levels under it). (2) scripts/collapse_repo_root.py: remove each fn repo_root with its own doc lines, insert the use line as the first line of the enclosing test module, add the two dev-dependencies, repoint the eight anchors; idempotent. (3) touched.rs: the scan reads test_bearing_sources filtered to source (not keel-cli/tests) and asserts touched.rs itself is in the population. (4) cargo test on keel-fs, the scan, and the five members; pos734/neg734; pair734.txt. (5) record the sprint with the retro filled; verifier with the pair file; recorder --owed 8 (six gates, the story DoD, the backlog DoD); land; CI conclusion."; }
    // RAN: outcome=pass stopped_at=none
    part oneRepoRootHelperStandupGateR1 : TestResult { :>> id = "07f827f8-5df4-4477-a033-d4169e4f5732"; :>> outcome = VerdictKind::proposed; :>> judgedAgainst = "e3714e3"; :>> judgedAt = "2026-09-17"; :>> judgedBy = "claudeFable5"; }
    verification oneRepoRootHelperImplementGate : Test { :>> id = "f4896604-db20-4308-ae1f-3e4445872a0e"; :>> title = "Sprint 734 implement gate"; :>> createdAt = "2026-09-17"; :>> createdBy = "claudeFable5"; :>> method = VerificationMethod::test; :>> procedureText = "The implement gate is the DoD's own probes plus the ladder: cargo test -p keel-fs --lib (2 passed); cargo test -p keel-cli --lib -- no_member_test_anchors_on_a_cwd_relative_path (1 passed, population > 40 files with touched.rs in it); cargo test --lib on keel-github, keel-schema, keel-model, keel-view, keel-write (12, 49, 16, 159, 62 passed); python pos734.py exit 0 (one definition, scan clean); python neg734.py exit 0 (rc 101, zz_probe734.rs:1 named, plant removed); python scripts/modgraph.py --check exit 0; keel verify . --probe-from pair734.txt (validate, guard, clippy, the pair, suite --touched) green."; }
    // RAN: outcome=pass stopped_at=none
    part oneRepoRootHelperImplementGateR1 : TestResult { :>> id = "5128bc29-42f0-4439-92f0-7dbf5a79a44d"; :>> outcome = VerdictKind::pass; :>> judgedAgainst = "e3714e3"; :>> judgedAt = "2026-09-17"; :>> judgedBy = "claudeFable5"; }
    verification oneRepoRootHelperReviewGate : Test { :>> id = "572ddcb1-5757-4846-8818-bdd8550d61c5"; :>> title = "Sprint 734 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every repointed test passes (the five members' lib runs and the ladder's touched set); the helper's walk from keel-fs's manifest lands on the same root as a walk from any caller's, asserted by its own test. Honesty: the scan's population is asserted to include keel-cli/src (touched.rs itself), so a widening that silently read only members would be red; the negative plants a file and expects the scan to name it. Scope: only test code and one test-support module changed; keel-cli/tests' three anchors are integration tests of the binary that stay beside it, named in the retro, not repointed."; }
    // RAN: outcome=pass stopped_at=none
    part oneRepoRootHelperReviewGateR1 : TestResult { :>> id = "a119517a-b1d1-41ab-bf24-0ff2d4b4dfed"; :>> outcome = VerdictKind::proposed; :>> judgedAgainst = "e3714e3"; :>> judgedAt = "2026-09-17"; :>> judgedBy = "claudeFable5"; }
    verification oneRepoRootHelperCloseOutGate : Test { :>> id = "31621907-d772-4db8-b86a-e6ed0c6eb74c"; :>> title = "Sprint 734 closeOut gate (autonomous, D0049)"; :>> createdAt = "2026-09-17"; :>> createdBy = "claudeFable5"; :>> method = VerificationMethod::inspect; :>> procedureText = "Landed when the verifier's receipt reads DISCREPANCIES: NONE and its probe rung row names pair734.txt, the recorder's report passes check_report.py --owed 8, git status -sb is clean after keel land and gh run list names the landing commit with conclusion success. The DoD result is recorded against dcOneRepoRootHelperDoD at that sha; issue557's resolution is computed from its #Resolves edge."; }
    // RAN: outcome=pass stopped_at=none
    part oneRepoRootHelperCloseOutGateR1 : TestResult { :>> id = "2630f408-4bdb-421e-a4e4-8ecd00316f27"; :>> outcome = VerdictKind::proposed; :>> judgedAgainst = "e3714e3"; :>> judgedAt = "2026-09-17"; :>> judgedBy = "claudeFable5"; }
    verification oneRepoRootHelperRetroGate : Test { :>> id = "8d536198-f614-4eba-959d-8e86868667d3"; :>> title = "Sprint 734 retro gate (autonomous, D0049)"; :>> createdAt = "2026-09-17"; :>> createdBy = "claudeFable5"; :>> method = VerificationMethod::analyze; :>> procedureText = "Written at close-out, before the verifier is dispatched; avoidable issues scanned (issue011), each finding a tracked item or the reason it is not. (1) Sprint 718's scripted insertion of fn repo_root placed the helper before the first #[test] of each module without checking for a doc comment above it, so five tests' doc comments (activation's issue149 paragraph, fingerprint, orient, queries, arch) were glued onto the helper and detached from the tests they described; the collapse removed the helper and its own two doc lines and the five docs reattach. No new item - the inserting script is retired and grep '/// The repository root, found from the crate manifest' over the tree is zero after the collapse. (2) The DoD's counts (nine helpers, sixteen anchors) were authored at sprint 731 and the tree moved twice before execution: ten helpers, eight anchors. No new item - the DoD's probes (one definition by grep; the scan clean; a planted anchor red) are the contract and each held; the result's evidence carries the actual counts. (3) keel-cli/tests holds three cwd-relative anchors outside the widened population. No new item - the class breaks when a CRATE moves two levels down, and keel-cli's integration tests move with keel-cli, whose parent stays the repository root; if keel-cli itself ever moves under members/ the scan's filter is the one line to drop. (4) pos734.py's first run was red on Windows path separators (glob returned backslashes, the comparison expected slashes) before the tree was judged - the D0388 discipline caught the probe, not the tree; fixed in the script. No new item - a scratchpad probe. (5) The scan keeps the name no_member_test_anchors_on_a_cwd_relative_path while its population is every crate: the doc line states the population, and five records plus facts.py cite the name. No new item - a rename would orphan the citations for a word."; }
    // RAN: outcome=pass stopped_at=none
    part oneRepoRootHelperRetroGateR1 : TestResult { :>> id = "b6981f28-dace-4db4-9561-1cce52f83fc4"; :>> outcome = VerdictKind::proposed; :>> judgedAgainst = "e3714e3"; :>> judgedAt = "2026-09-17"; :>> judgedBy = "claudeFable5"; }
}
