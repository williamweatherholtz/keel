// ProjectDeliveryS761 — Sprint 761: The human said on 2026-09-22 (st192): fix artifact permanently so the comment section is unique per tab; today it is shared and they cannot give feedback per ask. This sprint makes one note field per ask the brief contract (D0550): a clause in the brief checker with its self-test pair, the skill table row, and the runner-direction brief rebuilt and republished at its URL with seven per-ask notes whose digest lands each note beneath its own answer.. EXECUTE. 1 pts.
package ProjectDeliveryS761 {
    private import EngineElement::*;
    private import EngineWork::*;
    private import EngineVerification::*;
    private import EngineRelationships::*;

    #CharteredBy dependency from briefNoteIsPerAskStory to d0550;
    #Delivers dependency from briefNoteIsPerAskStory to dcBriefNoteIsPerAsk;

    part briefNoteIsPerAskStory : Story {
        :>> id = "e320a227-64c7-4e9f-891a-6123105a2b24";
        :>> title = "Sprint 761: The human said on 2026-09-22 (st192): fix artifact permanently so the comment section is unique per tab; today it is shared and they cannot give feedback per ask. This sprint makes one note field per ask the brief contract (D0550): a clause in the brief checker with its self-test pair, the skill table row, and the runner-direction brief rebuilt and republished at its URL with seven per-ask notes whose digest lands each note beneath its own answer. (1 pts)";
        :>> createdAt = "2026-09-22"; :>> createdBy = "claudeFable5"; :>> kind = WorkKind::code; :>> priority = WorkPriority::p0; :>> owner = "claudeFable5"; :>> estimatedPoints = 1;
    }

    action def DeliveryRunS761 {
        action storyBriefNoteIsPerAsk;
        verification storyBriefNoteIsPerAskDoD : Test { :>> id = "102799c7-d407-4c15-8f00-46163a2bb2ab"; :>> method = VerificationMethod::test; :>> procedureText = "scripts/check_templates.py --brief refuses a page whose note count differs from its panel count or whose note sits outside a panel, with two self-test cases; the asi-templates section table carries the Notes row in .engine/skills and the .claude mirror; the runner-direction brief is rebuilt with one keyed note per ask, its digest emits each beneath its answer, it passes the checker and is republished at its URL; keel sync-claude --check, keel gate validate, guard and check-engine are green on the committed tree."; }
        // RAN: python scripts/check_templates.py --self-test pass; --brief clean on the rebuilt page and 'notes and asks disagree' on brief58.html; the Notes row present in .engine/skills/asi-templates/SKILL.md and mirrored (keel sync-claude --check clean); the page republished at its URL with 7 keyed notes; validate, check-engine, guard green.
        part storyBriefNoteIsPerAskDoDR1 : TestResult { :>> id = "94e7695d-7c6e-4239-ae08-9027358dea30"; :>> outcome = VerdictKind::pass; :>> judgedAgainst = "b65a13e4894742f65340660584e599deb5404a73"; :>> judgedAt = "2026-09-22"; :>> judgedBy = "claudeFable5"; }
    }

    verification briefNoteIsPerAskRefineGate : Test { :>> id = "e0037239-b14f-4031-87c6-1c46eb236558"; :>> title = "Sprint 761 refine gate (DoR)"; :>> createdAt = "2026-09-22"; :>> createdBy = "claudeFable5"; :>> method = VerificationMethod::inspect; :>> procedureText = "A correction from the human's own use of the published page; the process is the asi-templates surface's contract check, which already gained clauses this way for tabs (D0404), durations (D0405) and named sets (D0406). One refinement: the clause counts notes inside panels rather than trusting a class name, so a note placed outside a tab is refused even if it is labelled as a note. Sized 1 point: one clause, two fixture cases, one table row, one rebuild."; }
    // RAN: st192 read verbatim from .tracking/intake/intake-2026-09-22.sysml; dcBriefNoteIsPerAsk authored with record task before the sprint was scaffolded; DoR: estimatedPoints 1, #CharteredBy d0550 and #Delivers dcBriefNoteIsPerAsk on the Story, DoD in the fill; the D0404/D0405/D0406 precedent read in .engine/skills/asi-templates/SKILL.md section 2.1.
    part briefNoteIsPerAskRefineGateR1 : TestResult { :>> id = "8657908a-884e-43f8-99a3-299518dbc7bc"; :>> outcome = VerdictKind::proposed; :>> judgedAgainst = "b65a13e4894742f65340660584e599deb5404a73"; :>> judgedAt = "2026-09-22"; :>> judgedBy = "claudeFable5"; }
    verification briefNoteIsPerAskStandupGate : Test { :>> id = "10c02255-3c66-4c9d-baa3-a419976aa0ed"; :>> title = "Sprint 761 standup gate"; :>> createdAt = "2026-09-22"; :>> createdBy = "claudeFable5"; :>> method = VerificationMethod::inspect; :>> procedureText = "Two choices. The clause reads the same panel regex the per-tab ceiling reads, so the two clauses agree on what a tab is. And the previous standing page (brief58.html, the 2026-09-20 publish) was run through the new checker to confirm it now fails the clause - the point of putting the fix in the checker rather than in one builder is that the next republish of the standing page must comply."; }
    // RAN: the new clause reuses the tabpanel regex the D0407 per-tab ceiling reads (scripts/check_templates.py, the block after 3b); python scripts/check_templates.py --brief on brief58.html (the 2026-09-20 standing page) -> notes and asks disagree: 1 note field(s), 0 inside a tab, 12 tabs, confirming the next standing republish must comply.
    part briefNoteIsPerAskStandupGateR1 : TestResult { :>> id = "4a0474b0-d158-4880-8420-b9365797a350"; :>> outcome = VerdictKind::proposed; :>> judgedAgainst = "b65a13e4894742f65340660584e599deb5404a73"; :>> judgedAt = "2026-09-22"; :>> judgedBy = "claudeFable5"; }
    verification briefNoteIsPerAskImplementGate : Test { :>> id = "21c9937a-f808-461d-8f58-268d7c15a577"; :>> title = "Sprint 761 implement gate"; :>> createdAt = "2026-09-22"; :>> createdBy = "claudeFable5"; :>> method = VerificationMethod::test; :>> procedureText = "RAN python scripts/check_templates.py --self-test (all cases ok including the two new ones); the brief rebuilt by build_panel_brief.py with seven data-d note fields each inside its panel and keyed by data-ask, the digest emitting Recorded with this answer under each ask's options and the draft store keeping notes per ask; check_templates.py --brief on the rebuilt page clean; the same check on brief58.html reports notes and asks disagree; the page republished at its URL; the row added to .engine/skills/asi-templates/SKILL.md and mirrored; keel sync-claude --check clean; D0550 recorded and accepted under standing consent."; }
    // RAN: python scripts/check_templates.py --self-test -> pass, including 'a shared note below two tabs refused' and 'one note inside each of two tabs passes'; build_panel_brief.py -> 7 tabs, 7 data-d note fields each inside its section with data-ask; python scripts/check_templates.py --brief runner_direction_verdict.html -> brief contract: clean; republished at https://claude.ai/artifact/3e35AtqqdYE7sVPK3fpfkP (version 2); Notes row added to .engine/skills/asi-templates/SKILL.md and .claude/skills/asi-templates/SKILL.md; keel sync-claude --check -> keel-owned subset matches this binary's generator; D0550 recorded and accepted under standing consent d0207.
    part briefNoteIsPerAskImplementGateR1 : TestResult { :>> id = "957a8b10-670e-4994-b36d-7e5b54bdeeb3"; :>> outcome = VerdictKind::pass; :>> judgedAgainst = "b65a13e4894742f65340660584e599deb5404a73"; :>> judgedAt = "2026-09-22"; :>> judgedBy = "claudeFable5"; }
    verification briefNoteIsPerAskReviewGate : Test { :>> id = "7988bf69-85b2-4ef3-821b-dd936bcc5a72"; :>> title = "Sprint 761 review gate — three passes per D0172"; :>> createdAt = "2026-09-22"; :>> createdBy = "claudeFable5"; :>> method = VerificationMethod::inspect; :>> procedureText = "Content: the clause names both counts and the reason in its refusal; the fixture pair exercises both directions. Structure: one clause, placed beside the tab clause it extends. Record: D0550 says NOT A FORK and NOT A PROCESS CHANGE with reasons; the DoD names its checks; the human's words are st192 verbatim."; }
    // RAN: the clause's refusal names both counts and D0550; the fixture gained a shared_note switch and the two cases run under --self-test which CI runs; keel gate validate . clean; keel gate check-engine . clean; keel gate guard --no-receipt ALL PASS; keel sync-claude --check clean.
    part briefNoteIsPerAskReviewGateR1 : TestResult { :>> id = "32590e0c-a7de-4c42-84cd-4b6ca3ff4fc8"; :>> outcome = VerdictKind::proposed; :>> judgedAgainst = "b65a13e4894742f65340660584e599deb5404a73"; :>> judgedAt = "2026-09-22"; :>> judgedBy = "claudeFable5"; }
    verification briefNoteIsPerAskCloseOutGate : Test { :>> id = "05382727-f295-42ee-8d2f-ceba6aae9666"; :>> title = "Sprint 761 closeOut gate (autonomous, D0049)"; :>> createdAt = "2026-09-22"; :>> createdBy = "claudeFable5"; :>> method = VerificationMethod::inspect; :>> procedureText = "Delivered: the checker clause and its self-test pair, the skill row in source and mirror, D0550, the rebuilt and republished brief, dcBriefNoteIsPerAsk. Not delivered on purpose: the standing decision page is not rebuilt here; its next republish must pass the new clause, which is the control the human asked for."; }
    // RAN: git status --short lists scripts/check_templates.py, the two SKILL.md files, 0550-briefNoteIsPerAsk.sysml, sprint761_briefNoteIsPerAsk.sysml, backlog.sysml, intake-2026-09-22.sysml, the four accepted decision files, .engine/decisions edits; validate, check-engine and guard exit 0. Delivered the clause, its self-test pair, the skill row, D0550, the republished brief, dcBriefNoteIsPerAsk; the standing page is not rebuilt here by design.
    part briefNoteIsPerAskCloseOutGateR1 : TestResult { :>> id = "3f379b8b-3dc5-463c-9cd5-5bd5886a526a"; :>> outcome = VerdictKind::proposed; :>> judgedAgainst = "b65a13e4894742f65340660584e599deb5404a73"; :>> judgedAt = "2026-09-22"; :>> judgedBy = "claudeFable5"; }
    verification briefNoteIsPerAskRetroGate : Test { :>> id = "08f02d79-2fc3-4069-807c-8e0576f8d354"; :>> title = "Sprint 761 retro gate (autonomous, D0049)"; :>> createdAt = "2026-09-22"; :>> createdBy = "claudeFable5"; :>> method = VerificationMethod::analyze; :>> procedureText = "Retro held; avoidable-issue scan over the sprint: one finding, no avoidable issue. The source template already carried a note per tab; the builders dropped it when the tabs came back and no clause held it, so a shape the template knew was lost by drift - the clause is the correction and no new item is needed beyond dcBriefNoteIsPerAsk, which this commit adds."; }
    // RAN: the retro text names dcBriefNoteIsPerAsk (added by this commit) and says no new item is needed; keel gate guard --no-receipt -> ALL PASS with retro-backlog among the passes.
    part briefNoteIsPerAskRetroGateR1 : TestResult { :>> id = "a76156c4-6f3e-4eba-8e0a-0f26ff0065be"; :>> outcome = VerdictKind::proposed; :>> judgedAgainst = "b65a13e4894742f65340660584e599deb5404a73"; :>> judgedAt = "2026-09-22"; :>> judgedBy = "claudeFable5"; }
}
