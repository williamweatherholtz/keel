// ProjectDeliveryS751 — Sprint 751: the verifier's receipt is rendered from the receipt files by scripts/verify_receipt.py, never typed: DISCREPANCIES is computed, a running ladder is WAIT or KILLED by its writer's liveness (D0533; issue490, issue567). EXECUTE. 5 pts.
package ProjectDeliveryS751 {
    private import EngineElement::*;
    private import EngineWork::*;
    private import EngineVerification::*;
    private import EngineRelationships::*;

    #CharteredBy dependency from verifierReceiptIsRenderedStory to d0533;
    #Delivers dependency from verifierReceiptIsRenderedStory to dcVerifierReceiptOutcomeIsRenderedNotTyped;

    part verifierReceiptIsRenderedStory : Story {
        :>> id = "07d5cda3-e1b9-4481-8d70-d3277aee2645";
        :>> title = "Sprint 751: the verifier's receipt is rendered from the receipt files by scripts/verify_receipt.py, never typed: DISCREPANCIES is computed, a running ladder is WAIT or KILLED by its writer's liveness (D0533; issue490, issue567) (5 pts)";
        :>> createdAt = "2026-09-19"; :>> createdBy = "claudeFable5"; :>> kind = WorkKind::code; :>> priority = WorkPriority::p0; :>> owner = "claudeFable5"; :>> estimatedPoints = 5;
    }

    action def DeliveryRunS751 {
        action storyVerifierReceiptIsRendered;
        verification storyVerifierReceiptIsRenderedDoD : Test { :>> id = "dd10742e-7f51-4e60-85a2-547c0b74740f"; :>> method = VerificationMethod::test; :>> procedureText = "DELIVERED BACKLOG ITEM: dcVerifierReceiptOutcomeIsRenderedNotTyped. DONE MEANS: the task's DoD passes as written - scripts/verify_receipt.py reads .keel/metrics/verify-receipt.toml, touched-receipt.toml, verify-launch.epoch and verify-touched.out, runs gate check-engine and sync-claude --check under --keel, and emits the receipt's RESULT block with DISCREPANCIES computed as the diff between the ladder's claims and those fields; the test-verify skill's steps 4-6 run the script in a bounded wait loop and forbid editing the rendered file; its --probe pair passes (a fail fixture with two failing names renders a red block naming both, a pass fixture renders passed=N failed=0 and DISCREPANCIES: NONE; running with an alive writer is one WAIT line exit 2 with no block, running with no writer is KILLED at the rung naming verify-launch.epoch and at, exit 3); ci-probe on line 2 puts it under scripts/script_probes.py; the live render over sprint 750's metrics is faithful (it names the ladder's head 9453faf5 against HEAD b7289c4d and the touched receipt keel land rewrote after the ladder); clippy, the full guard set and the touched test set pass."; }
        // RAN: validate=pass guard=pass clippy=pass probe=pass touched=pass; keel suite --touched: pass - 914 passed in 887s
        part storyVerifierReceiptIsRenderedDoDR1 : TestResult { :>> id = "02a796f6-2acf-45f4-b4e6-448675e8f5d8"; :>> outcome = VerdictKind::pass; :>> judgedAgainst = "b7289c4d"; :>> judgedAt = "2026-09-19"; :>> judgedBy = "claudeFable5"; }
    }

    verification verifierReceiptIsRenderedRefineGate : Test { :>> id = "4920dfb8-698f-41ef-9a36-d2540af0918f"; :>> title = "Sprint 751 refine gate (DoR)"; :>> createdAt = "2026-09-19"; :>> createdBy = "claudeFable5"; :>> method = VerificationMethod::inspect; :>> procedureText = "One backlog item, sized 5: a Python renderer over four receipt files with a liveness read and a stem mirror of touched.rs, a skill rewrite, and one process-change Decision (D0533) because the verifier's procedure (D0438) changes. Ready when the script's probe fixtures (fail-two-names, pass, running-alive, running-dead) are written before the live metrics are read, and the sprint's own pair is the script's --probe beside a fixture the script must refuse."; }
    // RAN: validate=pass guard=pass clippy=pass probe=pass touched=pass
    part verifierReceiptIsRenderedRefineGateR1 : TestResult { :>> id = "9fbc5bec-236a-4237-9120-9afe833b0a55"; :>> outcome = VerdictKind::proposed; :>> judgedAgainst = "b7289c4d"; :>> judgedAt = "2026-09-19"; :>> judgedBy = "claudeFable5"; }
    verification verifierReceiptIsRenderedStandupGate : Test { :>> id = "1bd887b6-6f19-4f78-ac5a-dbfc53dcea90"; :>> title = "Sprint 751 standup gate"; :>> createdAt = "2026-09-19"; :>> createdBy = "claudeFable5"; :>> method = VerificationMethod::inspect; :>> procedureText = "The script renders and never judges: every line below the header is a field, DISCREPANCIES is the list of fields that disagree with a green claim, and NONE is what prints when the list is empty. Liveness is read from the process table (the receipt's pid under D0493, else any keel or cargo process), because a stub that says running cannot say whether its writer died. The skill's steps 4-6 become the wait loop and a prohibition on editing the file; the only line the verifier contributes is VERIFIER-NOTED WRITES through --noted (D0516). D0533 is held for the human."; }
    // RAN: validate=pass guard=pass clippy=pass probe=pass touched=pass
    part verifierReceiptIsRenderedStandupGateR1 : TestResult { :>> id = "15a60de1-b25e-4166-9008-3ea81d14943a"; :>> outcome = VerdictKind::proposed; :>> judgedAgainst = "b7289c4d"; :>> judgedAt = "2026-09-19"; :>> judgedBy = "claudeFable5"; }
    verification verifierReceiptIsRenderedImplementGate : Test { :>> id = "1823c90c-3ff5-4069-8125-23fa142875d6"; :>> title = "Sprint 751 implement gate"; :>> createdAt = "2026-09-19"; :>> createdBy = "claudeFable5"; :>> method = VerificationMethod::test; :>> procedureText = "python scripts/verify_receipt.py --probe: 12 checks, 0 failure(s); the live render over sprint 750's .keel/metrics exits 0 with three computed discrepancies, each true (LADDER head=9453faf5 != HEAD b7289c4d; TOUCHED at=1789849824 after LADDER at=1789848808, rewritten by keel land; stems over a landed change set), and a test result line read from verify-touched.out:2130 compacted to [96 binaries]; CRLF count 0; keel sync-claude . regenerates .claude/skills/test-verify/SKILL.md byte-equal to .engine; gate validate clean; gate check-engine clean; the guard set passes; the touched set passes under the ladder."; }
    // RAN: validate=pass guard=pass clippy=pass probe=pass touched=pass
    part verifierReceiptIsRenderedImplementGateR1 : TestResult { :>> id = "453640b0-9ef9-4ef8-a94e-18bad8d4815c"; :>> outcome = VerdictKind::pass; :>> judgedAgainst = "b7289c4d"; :>> judgedAt = "2026-09-19"; :>> judgedBy = "claudeFable5"; }
    verification verifierReceiptIsRenderedReviewGate : Test { :>> id = "87f8aaf5-42f8-431b-9044-67302d9aa29f"; :>> title = "Sprint 751 review gate — three passes per D0172"; :>> createdAt = "2026-09-19"; :>> createdBy = "claudeFable5"; :>> method = VerificationMethod::inspect; :>> procedureText = "The script read back: the docstring names both issues and the four inputs; no line of the RESULT block is a constant other than the labels; DISCREPANCIES is appended only from computed conditions; the WAIT and KILLED paths return before any block is built; the stem rule mirrors touched.rs module_stem, embedded_stem and the merge-base diff plus untracked; the outside checks copy their last line and exit code. The skill read back: step 2 no longer asks the verifier to run anything by hand, step 4 is one bounded loop on exit code 2, step 6 says the file is the script's output and is not opened for editing, the receipt shape matches the script's render line for line."; }
    // RAN: validate=pass guard=pass clippy=pass probe=pass touched=pass
    part verifierReceiptIsRenderedReviewGateR1 : TestResult { :>> id = "38aa7145-9b16-49be-9f83-804a6f515a7a"; :>> outcome = VerdictKind::proposed; :>> judgedAgainst = "b7289c4d"; :>> judgedAt = "2026-09-19"; :>> judgedBy = "claudeFable5"; }
    verification verifierReceiptIsRenderedCloseOutGate : Test { :>> id = "92228447-83e4-4f44-96bd-b4dee58f2a86"; :>> title = "Sprint 751 closeOut gate (autonomous, D0049)"; :>> createdAt = "2026-09-19"; :>> createdBy = "claudeFable5"; :>> method = VerificationMethod::inspect; :>> procedureText = "The task's DoD result and the six gate results are recorded from the verifier's receipt - which is, for the first time, the script's own output; D0533 is proposed and held for the human's word; issue490 and issue567 resolve when the DoD passes."; }
    // RAN: validate=pass guard=pass clippy=pass probe=pass touched=pass
    part verifierReceiptIsRenderedCloseOutGateR1 : TestResult { :>> id = "dc54ea04-3ec8-4cd7-9ebf-46d309c3d51f"; :>> outcome = VerdictKind::proposed; :>> judgedAgainst = "b7289c4d"; :>> judgedAt = "2026-09-19"; :>> judgedBy = "claudeFable5"; }
    verification verifierReceiptIsRenderedRetroGate : Test { :>> id = "f36d6ed0-864f-4194-ac22-56288de049b5"; :>> title = "Sprint 751 retro gate (autonomous, D0049)"; :>> createdAt = "2026-09-19"; :>> createdBy = "claudeFable5"; :>> method = VerificationMethod::analyze; :>> procedureText = "Two findings, avoidable issues scanned (issue011). Finding: the first live render showed the touched receipt keel land wrote AFTER the ladder (736 passed) standing in for the ladder's own touched run (963 passed, still in verify-touched.out) - a receipt file with one slot and two writers, and no check between the ladder's at and the touched receipt's at. Control landed this sprint: a touched receipt dated after the ladder is a computed discrepancy with its own probe fixture - detection, not prevention; the root (one slot, two writers, no writer field) is tracked as issue660, resolved by dcTouchedReceiptNamesItsWriter, both recorded this sprint. Finding: the renderer's first cut split the probe rung's command on a colon and truncated every Windows path at the drive letter; the live render caught it, the fixture did not, because the fixture path was C:/pair.txt and the assertion never read the LADDER line's tail. Control landed this sprint: the split is on colon-space and the fixture's command carries a drive-letter path. No process improvement is owed beyond D0533 itself: the typed-summary class it closes was named in the retros of 676, 745 and 750, and this sprint is the resolver those retros pointed at."; }
    // RAN: validate=pass guard=pass clippy=pass probe=pass touched=pass
    part verifierReceiptIsRenderedRetroGateR1 : TestResult { :>> id = "ffafed36-a001-4794-9d4f-8851ab7c775b"; :>> outcome = VerdictKind::proposed; :>> judgedAgainst = "b7289c4d"; :>> judgedAt = "2026-09-19"; :>> judgedBy = "claudeFable5"; }
}
