// ProjectDeliveryS713 — Sprint 713: Resolve issue546 through dcEveryProseFlagReadsAFile. Sprint 711 gave record result and gate-result their --evidence-from / --notes-from file forms through one reader, prose_flag (D0224), and its retro asked which flag-shaped prose inputs still ride the shell argument path: override --reason (main.rs:2496), record story --i-want / --so-that / --triage-note (3431-3456), and the --note of accept (5042), reject (5148) and judge-set (5270), read again inside fold_words_into_note and fold_warnings_into_note. Each is AI-typed prose passed as a double-quoted shell argument - the shape in which a backtick becomes a command the shell runs into the record, caught five times under D0224. Chartered by D0224 (prose goes through a file). 2 pts.. EXECUTE. 2 pts.
package ProjectDeliveryS713 {
    private import EngineElement::*;
    private import EngineWork::*;
    private import EngineVerification::*;
    private import EngineRelationships::*;

    #CharteredBy dependency from everyProseFlagReadsAFileStory to d0224;

    part everyProseFlagReadsAFileStory : Story {
        :>> id = "3e6cc9ea-459d-4b7c-a287-f27037b64dd6";
        :>> title = "Sprint 713: Resolve issue546 through dcEveryProseFlagReadsAFile. Sprint 711 gave record result and gate-result their --evidence-from / --notes-from file forms through one reader, prose_flag (D0224), and its retro asked which flag-shaped prose inputs still ride the shell argument path: override --reason (main.rs:2496), record story --i-want / --so-that / --triage-note (3431-3456), and the --note of accept (5042), reject (5148) and judge-set (5270), read again inside fold_words_into_note and fold_warnings_into_note. Each is AI-typed prose passed as a double-quoted shell argument - the shape in which a backtick becomes a command the shell runs into the record, caught five times under D0224. Chartered by D0224 (prose goes through a file). 2 pts. (2 pts)";
        :>> createdAt = "2026-09-14"; :>> createdBy = "claudeFable5"; :>> kind = WorkKind::code; :>> priority = WorkPriority::p0; :>> owner = "claudeFable5"; :>> estimatedPoints = 2;
    }

    action def DeliveryRunS713 {
        action storyEveryProseFlagReadsAFile;
        verification storyEveryProseFlagReadsAFileDoD : Test { :>> id = "df9b47cb-c59f-4678-ac83-363d8ab96814"; :>> method = VerificationMethod::test; :>> procedureText = "Resolves issue546: one argument-level normaliser, prose_args, rewrites --X-from FILE into --X TEXT through prose_flag at each command's entry - override (reason), record story (i-want, so-that, triage-note), accept, reject and judge-set (note) - so every downstream reader, the two fold_* readers and the channel layer included, sees one form and none learns about files; both forms at once is refused by name with nothing written. --implication stays inline (an ImplicationKind member, not prose); accept --words stays a shell argument on purpose (a human's short quote, D0192) and its usage line says so. The usage lines, cli_facts.rs and commands.sysml name each file form; the four facts owned by claudeOpus5 are retired by #Supersede edges beside them, never re-authored under their ids (D0108, D0477). Known-positive: an integration test drives the built binary with a file carrying a backtick span and a parenthesised refusal into override --reason-from, story --i-want-from / --so-that-from / --triage-note-from and accept --note-from, each landing verbatim; known-negative: the inline forms land unchanged, both forms at once is refused naming both flags, and a grep of main.rs for flag(args, over the prose-shaped names finds every read inside one of the five commands after its prose_args call, or inside fold_words_into_note / fold_warnings_into_note / verdict_channel_refusal, whose only callers are those commands after that call - no read of a prose flag ever sees the raw argument list."; }
        // RAN: DoD for dcEveryProseFlagReadsAFile (issue546) at af5def6, 2026-09-14. prose_args(args, names, verb) -> Result<Vec<String>, i32> at main.rs 2901 rewrites --X-from FILE into --X TEXT through prose_flag and refuses both by name (prose_flag's error); called first in cmd_override (reason), cmd_record_story (i-want, so-that, triage-note), cmd_accept, cmd_reject, cmd_judge_set (note). --implication stays inline; accept --words stays a shell argument and the usage line says so (D0192). Usage lines, cli_facts.rs and commands.sysml name each file form; cliAccept/cliReject/cliJudgeSet/cliOverride retired by #Supersede edges beside them, re-declared as cliAccept2/cliReject2/cliJudgeSet2/cliOverride2 under minted ids. // RAN: cargo test --release -p keel-cli --test prose_flags_read_a_file -> 3 passed; 0 failed (known-positive: the span 'run `keel gate validate .` first (refused otherwise)' lands verbatim in .keel/override.json, in the story's iWant, and in the accepted decision's note; known-negative: inline forms land, both forms refused naming both flags with nothing written, asserted per command) // RAN: grep -n 'flag(args, '/(reason/|i-want/|so-that/|triage-note/|note/)')' keel-cli/src/main.rs -> 11 reads at 2500 (cmd_override), 3479/3504/3505 (cmd_record_story), 4925 (fold_warnings_into_note), 4980/4989 (verdict_channel_refusal), 5054 (fold_words_into_note), 5097 (cmd_accept), 5207 (cmd_reject), 5333 (cmd_judge_set); the helpers' only callers are cmd_accept/cmd_reject/cmd_judge_set after their prose_args call (grep -n on the helper names) // RAN: keel gate guard --no-receipt . -> cli-surface-declared PASS 86 scanned; ownership PASS; no violations
        part storyEveryProseFlagReadsAFileDoDR1 : TestResult { :>> id = "f2a41644-9029-4856-90d2-cba9970fe78e"; :>> outcome = VerdictKind::pass; :>> judgedAgainst = "af5def6"; :>> judgedAt = "2026-09-14"; :>> judgedBy = "claudeFable5"; }
    }

    verification everyProseFlagReadsAFileRefineGate : Test { :>> id = "ee54468d-f7a6-4cd1-947f-5a1a18ea6ab3"; :>> title = "Sprint 713 refine gate (DoR)"; :>> createdAt = "2026-09-14"; :>> createdBy = "claudeFable5"; :>> method = VerificationMethod::inspect; :>> procedureText = "Chartered by D0224 (accepted). NOT A PROCESS CHANGE: no gate, hook or workflow step changes; five commands gain a file form for prose they already take, through the reader sprint 711 landed. NOT A FORK: the DoD names one shape - normalise the argument list at the entry - and the alternative, teaching each of seven reads about files, is the duplication D0224 refused. Two points: one function, five call sites, five usage lines, five facts superseded, one integration test. DoR: dcEveryProseFlagReadsAFile ranks first on keel show whats-next at af5def6, its #DependsOn to dcCliFactSupersessionIsHonoured discharged by that landing."; }
    // RAN: DoR at af5def6 (2026-09-14). Charter: #CharteredBy everyProseFlagReadsAFileStory -> d0224 (proseGoesThroughAFile, accepted). Frontier: dcEveryProseFlagReadsAFile was the first ready item after af5def6 landed dcCliFactSupersessionIsHonoured, its #DependsOn (backlog.sysml, dependency from dcEveryProseFlagReadsAFile to dcCliFactSupersessionIsHonoured) discharged. estimatedPoints = 2 (one function, five entries, five usage lines, five facts, one integration test). NOT A PROCESS CHANGE: no locked path touched (main.rs, cli_facts.rs, commands.sysml, tests/, .tracking). Sites confirmed by reading main.rs before the edit: cmd_override 2496 (reason), cmd_record_story 3431/3455/3456 (i-want, so-that, triage-note), cmd_accept 5042, cmd_reject 5148, cmd_judge_set 5270 (note), plus the downstream readers fold_warnings_into_note 4876, fold_words_into_note 5005, verdict_channel_refusal 4931/4940; record issue has no --note field (it reads --description-from), so issue546's seventh site does not exist - recorded in the retro.
    part everyProseFlagReadsAFileRefineGateR1 : TestResult { :>> id = "ba43b992-1eed-4837-ac42-b6fae0565d0e"; :>> outcome = VerdictKind::proposed; :>> judgedAgainst = "af5def6"; :>> judgedAt = "2026-09-14"; :>> judgedBy = "claudeFable5"; }
    verification everyProseFlagReadsAFileStandupGate : Test { :>> id = "7dc19141-52fe-4df2-b3a2-659ffffbb2d1"; :>> title = "Sprint 713 standup gate"; :>> createdAt = "2026-09-14"; :>> createdBy = "claudeFable5"; :>> method = VerificationMethod::inspect; :>> procedureText = "Order: this record; prose_args beside prose_flag; the five entries; usage lines; cli_facts.rs invocations; commands.sysml - private import EngineRelationships, five new facts with minted v4 ids and #Supersede edges to the four claudeOpus5 facts plus cliRecordVerbs (mine, edited in place); integration test prose_flags_read_a_file over an init scaffold; cargo build --release, copy, the test, clippy -D warnings, gate guard --no-receipt with cli-surface-declared PASS; then keel verify . and the land."; }
    // RAN: Standup at af5def6 (2026-09-14). Order followed as written: sprint record scaffolded (keel record sprint 713 everyProseFlagReadsAFile --charter d0224 --points 2 --fill); prose_args authored beside prose_flag (main.rs 2901); the five entries call it first (main.rs 2492 override, 3467 record story, 5073 accept, 5188 reject, 5312 judge-set); usage lines updated; cli_facts.rs invocations for accept/reject/judge-set/override and the record story segment; commands.sysml: private import EngineRelationships::*, cliAccept2/cliReject2/cliJudgeSet2/cliOverride2 with minted ids (keel record mint) and #Supersede edges to the four claudeOpus5 facts, cliRecordVerbs (mine) edited in place; keel-cli/tests/prose_flags_read_a_file.rs written. cargo build --release 3m24s, copied to keel-serve.exe.
    part everyProseFlagReadsAFileStandupGateR1 : TestResult { :>> id = "af018061-5f06-4b38-be46-7f197102056a"; :>> outcome = VerdictKind::proposed; :>> judgedAgainst = "af5def6"; :>> judgedAt = "2026-09-14"; :>> judgedBy = "claudeFable5"; }
    verification everyProseFlagReadsAFileImplementGate : Test { :>> id = "d1ed4ca3-719c-40ed-952b-dca7871500e1"; :>> title = "Sprint 713 implement gate"; :>> createdAt = "2026-09-14"; :>> createdBy = "claudeFable5"; :>> method = VerificationMethod::test; :>> procedureText = "The implement gate holds when: cargo test --release -p keel-cli --test prose_flags_read_a_file passes; cargo clippy --release --all-targets -- -D warnings exits 0; keel gate guard --no-receipt . reports cli-surface-declared PASS with the superseded facts not in force and ownership PASS; keel --help renders each file form; sync-claude --check clean. Evidence quotes those commands' lines through --evidence-from."; }
    // RAN: Implement gate at af5def6, run 2026-09-14 from ./target/release/keel-serve.exe (copied after cargo build --release). // RAN: cargo test --release -p keel-cli --test prose_flags_read_a_file -> running 3 tests; test story_prose_reads_files_field_by_field ... ok; test override_reason_reads_a_file_and_the_inline_form_still_lands ... ok; test accept_and_reject_notes_read_a_file_before_the_channel_layer_reads_them ... ok; test result: ok. 3 passed; 0 failed; finished in 5.51s // RAN: cargo clippy --release --all-targets -- -D warnings -> Finished `release` profile [optimized] target(s) in 15.55s; exit 0 (one manual_contains lint fixed first: out.contains(&from_key)) // RAN: keel gate guard --no-receipt . -> [guard:cli-surface-declared] PASS - 86 scanned, 0 warning(s), 0 violation(s); [guard:ownership] PASS - 86 scanned (read: working tree), 0 warning(s), 0 violation(s); [guard:working-tree-eol] PASS - 1871 scanned; [guard:retro-backlog] PASS - 1 scanned; no guard reported a violation // RAN: keel --help -> 6 lines carry -from FILE; accept <decision> (--words TEXT | --note-from FILE | --note TEXT) ...; reject likewise; judge-set <.tracking file> (--words TEXT | --note-from FILE | --note TEXT) ...; override <path> (--reason-from FILE | --reason TEXT) // RAN: keel sync-claude --check . -> claude-surface: keel-owned subset matches this binary's generator (47 registry skill(s)) // RAN: keel gate validate . -> 818 tracking file(s) validated clean. // RAN: keel gate check-engine . -> .engine instance files validated clean (kernel-free; D0112 phase 2).
    part everyProseFlagReadsAFileImplementGateR1 : TestResult { :>> id = "9619bcaa-fffe-4027-84f3-81b01e2fbc64"; :>> outcome = VerdictKind::pass; :>> judgedAgainst = "af5def6"; :>> judgedAt = "2026-09-14"; :>> judgedBy = "claudeFable5"; }
    verification everyProseFlagReadsAFileReviewGate : Test { :>> id = "38876516-9b6a-414a-b848-dd1d869416c5"; :>> title = "Sprint 713 review gate — three passes per D0172"; :>> createdAt = "2026-09-14"; :>> createdBy = "claudeFable5"; :>> method = VerificationMethod::inspect; :>> procedureText = "Three passes (D0172). Correctness: the normaliser runs before fold_words_into_note, so a --note-from framing folds with --words exactly as an inline --note does, and the channel layer's quote receipt reads the same text. Honesty: the retired facts are retired by edge, not re-authored - the first use of the D0477 reader on the real tree, and the guard's PASS is the evidence it works; --words is left inline deliberately and the usage line states why. Scope: --implication is an enum member and stays inline; record issue --note named in issue546 is read only in the usage line, not as a field - stated in the retro, not silently dropped."; }
    // RAN: Review at af5def6 (2026-09-14), three passes (D0172). Correctness: prose_args is the first statement of cmd_accept (main.rs 5073), before fold_words_into_note (5077) and accept_channel_refusal/fold_warnings_into_note (5079-5080); the test accept_and_reject_notes_read_a_file_before_the_channel_layer_reads_them proves a --note-from framing folds with --words (framing and quote both in the accepted decision) and that a --note-from quote satisfies the channel layer's QUOTE check on reject. Honesty: the four claudeOpus5 facts are retired by #Supersede edges in commands.sysml lines 16/20/24/28 and their parts remain in the file under their original ids; cli-surface-declared PASS at 86 scanned is the first real-tree use of the D0477 reader. --words stays a shell argument on purpose and the accept usage line says why (D0192). Scope: --implication stays inline (ImplicationKind member); issue546's record issue --note site does not exist (that verb reads --description-from), stated in the retro; the DoD's known-negative was corrected before this gate from 'only reads inside prose_flag' (false by design) to the caller map every prose read actually satisfies: eleven flag(args, '<prose>') reads, each inside one of the five commands after its prose_args call or inside fold_words_into_note / fold_warnings_into_note / verdict_channel_refusal, whose only callers are those commands after that call (grep -n on main.rs, 2026-09-14).
    part everyProseFlagReadsAFileReviewGateR1 : TestResult { :>> id = "783ed259-1489-4541-8ee7-bac609c7888c"; :>> outcome = VerdictKind::proposed; :>> judgedAgainst = "af5def6"; :>> judgedAt = "2026-09-14"; :>> judgedBy = "claudeFable5"; }
    verification everyProseFlagReadsAFileCloseOutGate : Test { :>> id = "f114e229-c157-4e60-b858-d37fd4dd345d"; :>> title = "Sprint 713 closeOut gate (autonomous, D0049)"; :>> createdAt = "2026-09-14"; :>> createdBy = "claudeFable5"; :>> method = VerificationMethod::inspect; :>> procedureText = "Closes at the commit that lands the normaliser, the five entries, the facts and the test with this record: keel-land runs the touched set; gate validate / check-engine / guard --no-receipt green; dcEveryProseFlagReadsAFileDoD carries a pass through --evidence-from; git status -sb level with origin and the CI conclusion for that commit read from gh run list --json conclusion."; }
    // RAN: Sprint 713 closed at 4604637 (2026-09-14): the commit landing prose_args, the five entries, the superseded CLI facts, the sprint record and the integration test. // RAN: git status -sb -> ## main...origin/main (level with origin after the post-commit land) // RAN: keel-land touched set (.keel/metrics/touched-receipt.toml) -> head = '4604637', outcome = 'pass', passed = 661, failed = 0, runner = 'cargo-nextest 0.9.144', 51 binaries skipped as observed green at this content (D0474) // RAN: gh run list --limit 1 --json conclusion,status,headSha,name -> conclusion 'success', status 'completed', headSha 46046376195a77c8990c4d886dbfd707cf5ba90d, name 'ci' // RAN: keel verify . before the commit -> pass in 339 s (validate, guard, clippy, probe pair, suite --touched all green); dcEveryProseFlagReadsAFileDoDR1 pass at af5def6
    part everyProseFlagReadsAFileCloseOutGateR1 : TestResult { :>> id = "aceb894b-a07c-4144-9090-c91c41d17642"; :>> outcome = VerdictKind::proposed; :>> judgedAgainst = "4604637"; :>> judgedAt = "2026-09-14"; :>> judgedBy = "claudeFable5"; }
    verification everyProseFlagReadsAFileRetroGate : Test { :>> id = "98baae34-5dbc-4a30-8050-28731cf018db"; :>> title = "Sprint 713 retro gate (autonomous, D0049)"; :>> createdAt = "2026-09-14"; :>> createdBy = "claudeFable5"; :>> method = VerificationMethod::analyze; :>> procedureText = "Avoidable issues scanned; findings are tracked items, not prose. The class here is a fix landed at one site when the defect had seven: sprint 711's reader reached the two flags its issue named and the retro found the rest by one grep - the grep is now the DoD's known-negative and can be re-run. issue546 named record issue --note as a site; the grep shows that verb has no --note field (main.rs reads --description-from), so the count is six, not seven. No new item: the finding is a miscount in the text of issue546, whose resolver dcEveryProseFlagReadsAFile this sprint delivers with the corrected set; a miscount is not a recurrable defect and gets no control (D0047), and the DoD's grep is the check anyone re-runs."; }
    // RAN: Retro for sprint 713 at 4604637 (2026-09-14). Avoidable issues scanned. Finding: issue546 counted seven prose-flag sites; the grep in the DoD finds six - record issue has no --note field (it reads --description-from). No new item: a miscount in an issue's text is not a recurrable defect (D0047); the DoD's caller-map grep is the check anyone re-runs, already tracked through dcEveryProseFlagReadsAFile, which this sprint delivered. Second observation: the DoD's known-negative was rewritten before the review gate from 'only reads inside prose_flag' to the caller map, because the normaliser design makes the first wording false by construction; the review evidence states the correction. No further item: the corrected wording is in the tree and the review gate carries it. // RAN: grep -n 'flag(args, '/(reason/|i-want/|so-that/|triage-note/|note/)')' keel-cli/src/main.rs -> 11 reads, each downstream of a prose_args call
    part everyProseFlagReadsAFileRetroGateR1 : TestResult { :>> id = "e7a373a2-cc11-4e8a-8ce1-2c1d01905286"; :>> outcome = VerdictKind::proposed; :>> judgedAgainst = "4604637"; :>> judgedAt = "2026-09-14"; :>> judgedBy = "claudeFable5"; }
}
