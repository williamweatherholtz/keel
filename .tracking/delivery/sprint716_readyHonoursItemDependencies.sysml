// ProjectDeliveryS716 — Sprint 716: The ready frontier honours every edge the model authors to mean WAITING: an item that #DependsOn another undone item, and an item #CharteredBy a Decision the human has not accepted (dcReadyHonoursItemDependencies, issue549, issue552, D0052). EXECUTE. 2 pts.
package ProjectDeliveryS716 {
    private import EngineElement::*;
    private import EngineWork::*;
    private import EngineVerification::*;
    private import EngineRelationships::*;

    #CharteredBy dependency from readyHonoursItemDependenciesStory to d0052;

    part readyHonoursItemDependenciesStory : Story {
        :>> id = "bac632fa-a82f-49f5-a018-2df2b3e7f3fc";
        :>> title = "Sprint 716: The ready frontier honours every edge the model authors to mean WAITING: an item that #DependsOn another undone item, and an item #CharteredBy a Decision the human has not accepted (dcReadyHonoursItemDependencies, issue549, issue552, D0052) (2 pts)";
        :>> createdAt = "2026-09-14"; :>> createdBy = "claudeFable5"; :>> kind = WorkKind::code; :>> priority = WorkPriority::p0; :>> owner = "claudeFable5"; :>> estimatedPoints = 2;
    }

    action def DeliveryRunS716 {
        action storyReadyHonoursItemDependencies;
        verification storyReadyHonoursItemDependenciesDoD : Test { :>> id = "0271b7c5-dc77-4840-a777-59a8f6988517"; :>> method = VerificationMethod::test; :>> procedureText = "DELIVERED: view/mod.rs blocked_by reads charteredby beside dependson and dependency; a new blocked_on_items (pure core blocked_by_items) reads every item-to-item dependson edge against the frontier's own done-set and names a superseded target as such; orient.rs narrowing_filters takes the tasks and done-set, adds the blocked-on-item filter fail-closed like its two siblings, and Output carries `blocked` (item, waitsOn, why) ranked in declaration order, always emitted. VERIFY: the fixture pair (scripts/probes/ready_honours_item_dependencies.py pos, neg) - pos fails against the pre-fix binary (three items ready, no blocked key) and holds against the built one; neg holds; keel-cli/tests/ready_honours_item_dependencies.rs walks the same fixture end to end (predecessor passes, charter accepted, each frees its dependant with no other edit); against the real tree the frontier at bd5076a lost exactly the nine items whose predecessor is undone (twelve edges of the backlog's nineteen dc-to-dc DependsOn edges), gained none, kept its order and its counts; unit tests in view/mod.rs cover the charter case and the superseded-target case."; }
        // RAN: // RAN: DoD for dcReadyHonoursItemDependencies (issue549, issue552) at bd5076a (2026-09-14). keel verify . --probe 'python scripts/probes/ready_honours_item_dependencies.py pos,python scripts/probes/ready_honours_item_dependencies.py neg' from target/release/keel-verify.exe: validate pass 0 s, guard pass 2 s, clippy pass 16 s, probe pass 3 s (pos holds: ready=[dcFirst] blocked=[{dcSecond waitsOn dcFirst, not done}]; neg holds: ready=[dcSecond, storyChartered] blocked=[]), touched pass 182 s (keel suite --touched: 674 passed, 0 failed, changed modules [orient, view], set includes ready_honours_item_dependencies and the lib unit tests); every rung green in 206 s; receipt .keel/metrics/verify-receipt.toml. Known-positive fails without the fix: the same pos case against target/release/keel-land.exe (built before the change) exited 1 with ready=[dcFirst, dcSecond, storyChartered] blocked=None. Known-negative on the real tree: keel show orient at the working tree vs the orient JSON captured before the change - ready 77 to 68, the nine removed items are exactly the twelve blocked rows' items (removed == blocked items: True), added: [], declaration order preserved, counts equal, answerStatus COMPUTED; the DoD's named example moved because its predecessor passed at 396f13f (dcWorkspaceHoldsTheLeafMembers done, so dcGuardsViewOrientCycleIsBroken is ready, as the clause requires). issue552: the stopgap #DependsOn from dcWorkspaceLayeringIsGuarded to d0483 was removed in this commit and the #CharteredBy edge alone keeps the story off the ready list (68 ready before and after). Unit tests view::tests a_story_chartered_by_a_proposed_decision_is_blocked_until_it_is_accepted and an_item_depending_on_an_undone_item_is_blocked_and_says_what_it_waits_on pass inside the lib run.
        part storyReadyHonoursItemDependenciesDoDR1 : TestResult { :>> id = "2b029e53-65dd-486f-9ad2-e98d56f45db0"; :>> outcome = VerdictKind::pass; :>> judgedAgainst = "bd5076a"; :>> judgedAt = "2026-09-14"; :>> judgedBy = "claudeFable5"; }
    }

    verification readyHonoursItemDependenciesRefineGate : Test { :>> id = "73be8b62-e71f-44e4-8b5c-4a8f54e9937b"; :>> title = "Sprint 716 refine gate (DoR)"; :>> createdAt = "2026-09-14"; :>> createdBy = "claudeFable5"; :>> method = VerificationMethod::inspect; :>> procedureText = "READY. Ranked first on the frontier by declaration order. Sized 2: two predicates in view, one filter in orient, a JSON field, a fixture test and a kept probe. Chartered by D0052: declaration order IS priority and the frontier is auto-followed, so a ranked item the model itself says is waiting is the defect the Decision exists to prevent."; }
    // RAN: Refine gate: DoR held - estimatedPoints 2 set, #CharteredBy to d0052 authored at scaffold, scope is two issues (549, 552) each with a fixture line, no blocking dependency (keel-cli/src is unlocked), DoD authored on the backlog item before implement.
    part readyHonoursItemDependenciesRefineGateR1 : TestResult { :>> id = "87810c43-3180-4a7f-adaf-a662c1e47157"; :>> outcome = VerdictKind::proposed; :>> judgedAgainst = "bd5076a"; :>> judgedAt = "2026-09-14"; :>> judgedBy = "claudeFable5"; }
    verification readyHonoursItemDependenciesStandupGate : Test { :>> id = "7fb6e271-1e9f-4939-8267-130b9e788760"; :>> title = "Sprint 716 standup gate"; :>> createdAt = "2026-09-14"; :>> createdBy = "claudeFable5"; :>> method = VerificationMethod::inspect; :>> procedureText = "Blockers: none. keel-cli/src is not a locked surface and no schema, process or enforcement file moves (NOT A PROCESS CHANGE: a computed view reads two edge kinds it already stored; the process that authors them is unchanged). The one line of CLAUDE.md that names the orient lens gains the word blocked in the same commit."; }
    // RAN: Standup gate: blockers none; NOT A PROCESS CHANGE - a computed view reads two edge kinds it already stored; no schema, process or enforcement file moved; the orient line of CLAUDE.md gains the word blocked in the same commit.
    part readyHonoursItemDependenciesStandupGateR1 : TestResult { :>> id = "ce871abf-2167-4881-82d5-bb90e6093a4a"; :>> outcome = VerdictKind::proposed; :>> judgedAgainst = "bd5076a"; :>> judgedAt = "2026-09-14"; :>> judgedBy = "claudeFable5"; }
    verification readyHonoursItemDependenciesImplementGate : Test { :>> id = "86ea95ad-312e-4765-9e6d-ebdfdf38c37e"; :>> title = "Sprint 716 implement gate"; :>> createdAt = "2026-09-14"; :>> createdBy = "claudeFable5"; :>> method = VerificationMethod::test; :>> procedureText = "view/mod.rs: blocked_by filters dependson, dependency and charteredby to a proposed Decision; blocked_on_items / blocked_by_items read dependson edges whose both ends are work items and return (item, waitsOn, why) with why in {not done, superseded}. orient.rs: BlockedItem type; narrowing_filters(repo, tasks, done_map) adds the filter fail-closed; frontier excludes the waiting items from ready and carries blocked, ranked by the item's declaration order; to_json emits 'blocked' after 'ready'; the two hand-built Output tests gain the field. scripts/probes/ready_honours_item_dependencies.py is the kept D0388 pair; keel-cli/tests/ready_honours_item_dependencies.rs the end-to-end fixture."; }
    // RAN: // RAN: DoD for dcReadyHonoursItemDependencies (issue549, issue552) at bd5076a (2026-09-14). keel verify . --probe 'python scripts/probes/ready_honours_item_dependencies.py pos,python scripts/probes/ready_honours_item_dependencies.py neg' from target/release/keel-verify.exe: validate pass 0 s, guard pass 2 s, clippy pass 16 s, probe pass 3 s (pos holds: ready=[dcFirst] blocked=[{dcSecond waitsOn dcFirst, not done}]; neg holds: ready=[dcSecond, storyChartered] blocked=[]), touched pass 182 s (keel suite --touched: 674 passed, 0 failed, changed modules [orient, view], set includes ready_honours_item_dependencies and the lib unit tests); every rung green in 206 s; receipt .keel/metrics/verify-receipt.toml. Known-positive fails without the fix: the same pos case against target/release/keel-land.exe (built before the change) exited 1 with ready=[dcFirst, dcSecond, storyChartered] blocked=None. Known-negative on the real tree: keel show orient at the working tree vs the orient JSON captured before the change - ready 77 to 68, the nine removed items are exactly the twelve blocked rows' items (removed == blocked items: True), added: [], declaration order preserved, counts equal, answerStatus COMPUTED; the DoD's named example moved because its predecessor passed at 396f13f (dcWorkspaceHoldsTheLeafMembers done, so dcGuardsViewOrientCycleIsBroken is ready, as the clause requires). issue552: the stopgap #DependsOn from dcWorkspaceLayeringIsGuarded to d0483 was removed in this commit and the #CharteredBy edge alone keeps the story off the ready list (68 ready before and after). Unit tests view::tests a_story_chartered_by_a_proposed_decision_is_blocked_until_it_is_accepted and an_item_depending_on_an_undone_item_is_blocked_and_says_what_it_waits_on pass inside the lib run.
    part readyHonoursItemDependenciesImplementGateR1 : TestResult { :>> id = "a308bbb7-42a9-48ea-9113-98f0e1607821"; :>> outcome = VerdictKind::pass; :>> judgedAgainst = "bd5076a"; :>> judgedAt = "2026-09-14"; :>> judgedBy = "claudeFable5"; }
    verification readyHonoursItemDependenciesReviewGate : Test { :>> id = "117d145e-cff4-4321-af0e-5e8e782365f2"; :>> title = "Sprint 716 review gate — three passes per D0172"; :>> createdAt = "2026-09-14"; :>> createdBy = "claudeFable5"; :>> method = VerificationMethod::inspect; :>> procedureText = "Pass 1 (intent): both issues' clauses are in the DoD and each has a fixture line that fails without the fix - pos was run against target/release/keel-land.exe (the pre-fix build) and exited 1 with all three items ready. Pass 2 (defects): the blocked list is filtered by done_map and superseded so a done or retired dependant never appears as waiting; an edge whose target is a requirement or Decision is not this filter's (is_item = tasks.contains_key). Pass 3 (residual): the filter reads direct edges only - a chain is honoured because each link blocks its own successor, but a dependant of a superseded item is blocked forever until a Decision re-points it, and the view says superseded so a reader sees why; the succession chain (first A then B) and the typed edge remain two ways to say the same thing."; }
    // RAN: Review gate, three passes (D0172). Intent: both issues' clauses are in the DoD and the pos fixture exited 1 against the pre-fix binary target/release/keel-land.exe (three items ready, no blocked key). Defects: blocked rows are filtered by done_map and superseded so a done or retired dependant never shows as waiting; a target that is a requirement or Decision is outside is_item = tasks.contains_key. Residual: direct edges only - a chain is honoured link by link; a dependant of a superseded item stays blocked with why=superseded until a Decision re-points it; succession and the typed edge remain two ways to say the same thing.
    part readyHonoursItemDependenciesReviewGateR1 : TestResult { :>> id = "1a7f22ba-e711-4801-9aed-fddf6a891162"; :>> outcome = VerdictKind::proposed; :>> judgedAgainst = "bd5076a"; :>> judgedAt = "2026-09-14"; :>> judgedBy = "claudeFable5"; }
    verification readyHonoursItemDependenciesCloseOutGate : Test { :>> id = "ae3ce11d-d773-4345-a20a-72f28d3df7c2"; :>> title = "Sprint 716 closeOut gate (autonomous, D0049)"; :>> createdAt = "2026-09-14"; :>> createdBy = "claudeFable5"; :>> method = VerificationMethod::inspect; :>> procedureText = "The frontier now reads every WAITING edge the model authors. Nine items left the ready list and the layering chain reads one member at a time, as its Decision intended."; }
    // RAN: CloseOut: the frontier reads every WAITING edge the model authors; nine items left ready (77 to 68), the twelve blocked rows name what each waits on, the issue552 stopgap edge is gone and the charter edge alone holds its story. Items are dcReadyHonoursItemDependencies (DoD result at bd5076a) and the retro's issue554 with resolver dcEveryEdgeKindHasAReader.
    part readyHonoursItemDependenciesCloseOutGateR1 : TestResult { :>> id = "956a63ec-daca-4567-867e-9ad1de535661"; :>> outcome = VerdictKind::proposed; :>> judgedAgainst = "bd5076a"; :>> judgedAt = "2026-09-14"; :>> judgedBy = "claudeFable5"; }
    verification readyHonoursItemDependenciesRetroGate : Test { :>> id = "6d901538-070e-4fba-89a5-e5790b9aec0f"; :>> title = "Sprint 716 retro gate (autonomous, D0049)"; :>> createdAt = "2026-09-14"; :>> createdBy = "claudeFable5"; :>> method = VerificationMethod::analyze; :>> procedureText = "Retro held; avoidable-issue scan: the class is a stored edge no view read (issue549 and issue552 are one defect seen from two edge kinds). The D0479 pass authored nineteen edges before any view consumed them and the whats-next list contradicted the backlog for a day. Control already tracked: none names this class - an authored edge kind with no reader. Finding: a guard or census that lists every edge kind the model stores against the views that read it, so a kind nothing reads is a violation the moment it is authored; recorded as an Issue with a resolver rather than a reminder (D0047)."; }
    // RAN: Retro: avoidable-issue scan - one class, a stored edge kind no view read (issue549 and issue552 are one defect from two edge kinds; nineteen edges were authored before any view consumed them). No tracked control names that class. Finding became issue554 (Medium) with resolver dcEveryEdgeKindHasAReader: a guard edge-kind-readers that lists every stored edge kind against its Rust readers and fails on a kind with none (D0047, D0131).
    part readyHonoursItemDependenciesRetroGateR1 : TestResult { :>> id = "f338e2d6-fcee-40d0-8561-e6201fceb565"; :>> outcome = VerdictKind::proposed; :>> judgedAgainst = "bd5076a"; :>> judgedAt = "2026-09-14"; :>> judgedBy = "claudeFable5"; }
}
