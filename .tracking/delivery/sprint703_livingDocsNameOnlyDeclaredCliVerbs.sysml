// ProjectDeliveryS703 — Sprint 703: Resolve issue528 (High) through dcLivingDocsNameOnlyDeclaredCliVerbs: guard cli-reference holds every keel verb the living doc surface names to a command this binary dispatches (and after a router or show, a declared sub-verb or lens), and the eight retired spellings the survey found in test-verify and knowledge-graph-memory read their current form, so a delegated agent following a skill verbatim runs the gate it names instead of a usage dump (D0471).. EXECUTE. 3 pts.
package ProjectDeliveryS703 {
    private import EngineElement::*;
    private import EngineWork::*;
    private import EngineVerification::*;
    private import EngineRelationships::*;

    #CharteredBy dependency from livingDocsNameOnlyDeclaredCliVerbsStory to d0471;

    part livingDocsNameOnlyDeclaredCliVerbsStory : Story {
        :>> id = "666ced34-4024-4af1-908d-d0d746570fab";
        :>> title = "Sprint 703: Resolve issue528 (High) through dcLivingDocsNameOnlyDeclaredCliVerbs: guard cli-reference holds every keel verb the living doc surface names to a command this binary dispatches (and after a router or show, a declared sub-verb or lens), and the eight retired spellings the survey found in test-verify and knowledge-graph-memory read their current form, so a delegated agent following a skill verbatim runs the gate it names instead of a usage dump (D0471). (3 pts)";
        :>> createdAt = "2026-09-13"; :>> createdBy = "claudeFable5"; :>> kind = WorkKind::code; :>> priority = WorkPriority::p0; :>> owner = "claudeFable5"; :>> estimatedPoints = 3;
    }

    action def DeliveryRunS703 {
        action storyLivingDocsNameOnlyDeclaredCliVerbs;
        verification storyLivingDocsNameOnlyDeclaredCliVerbsDoD : Test { :>> id = "b6928bae-a80b-4b7b-9b23-f551e48a2358"; :>> method = VerificationMethod::test; :>> procedureText = "DELIVERED: (a) keel-cli/src/guards.rs cli_reference beside tool_reference, sharing living_doc_files; GUARD_NAMES 74; dispatch arm; three unit tests carrying the D0388 pair - known-positive a doc line naming keel guard . fails naming .engine/skills/s.md:1 and today it is keel gate guard, known-negative keel gate guard . and keel show why pass - plus the code/prose rule, the router sub-verb and lens checks, a copy of the binary, and the sentence-final period. (b) .engine/docs/guards.md row, .engine/rules/guard-constraints.sysml cliReference guard 74, control-map gCliReference bound to ehz5. (c) test-verify SKILL.md lines 83-85 and 140-142 read KEEL gate validate / gate check-engine / gate guard --no-receipt; knowledge-graph-memory 98 keel show why, 101 keel show knowledge question-coverage; delegated-ceremony recorder brief a sub-verb of keel record; .claude regenerated by sync-claude. VERIFIED BY: the guard on the tree before the corrections FAILED naming all eight survey sites (plus three in its own catalogue row quoting the defect, and two wordings it is right to refuse); after, PASS 438 scanned 0 violations; gate validate, check-engine, guard --no-receipt green; sync-claude --check clean. The DoD's ten sites overcounted by two: the two keel workspace mentions are prose about the cargo workspace, not commands, and stay."; }
        // RAN: PROBE PAIR: cli-reference unit tests -> positive a_retired_verb_in_code_fails_naming_its_line_and_the_current_spelling_passes: PASS; negative (keel show why): PASS [guard:cli-reference] PASS — 438 scanned, 0 warning(s), 0 violation(s) TOUCHED RECEIPT: outcome=pass passed=801 failed=0 seconds=766
        part storyLivingDocsNameOnlyDeclaredCliVerbsDoDR1 : TestResult { :>> id = "b2dd5cd8-22b4-47d9-8a5b-ac937a02c72d"; :>> outcome = VerdictKind::pass; :>> judgedAgainst = "32d9424"; :>> judgedAt = "2026-09-13"; :>> judgedBy = "claudeFable5"; }
    }

    verification livingDocsNameOnlyDeclaredCliVerbsRefineGate : Test { :>> id = "3d085551-31b6-4790-9f08-7342b3b261e7"; :>> title = "Sprint 703 refine gate (DoR)"; :>> createdAt = "2026-09-13"; :>> createdBy = "claudeFable5"; :>> method = VerificationMethod::inspect; :>> procedureText = "DoR: estimatedPoints 3 (a guard with a tokenizer over two file kinds, tests, three doc surfaces, eight corrections, a rebuild); scope the eight sites the survey named and the guard; chartered by d0471; unblocked (issue528 has no open dependency)."; }
    // RAN: KEEL gate validate . -> 806 tracking file(s) validated clean.; exit=0 KEEL gate check-engine . -> .engine instance files validated clean (kernel-free; D0112 phase 2).; exit=0 KEEL gate guard --no-receipt . -> [guard] ALL PASS
    part livingDocsNameOnlyDeclaredCliVerbsRefineGateR1 : TestResult { :>> id = "d9cfd42a-cfc8-4eb7-b356-e9ddf6e201c4"; :>> outcome = VerdictKind::proposed; :>> judgedAgainst = "32d9424"; :>> judgedAt = "2026-09-13"; :>> judgedBy = "claudeFable5"; }
    verification livingDocsNameOnlyDeclaredCliVerbsStandupGate : Test { :>> id = "91332b2c-a46e-4870-90c0-1227fa6e18a6"; :>> title = "Sprint 703 standup gate"; :>> createdAt = "2026-09-13"; :>> createdBy = "claudeFable5"; :>> method = VerificationMethod::inspect; :>> procedureText = "In progress: the guard, its tests, the doc rows, the eight corrections; blocked on nothing; the D0388 pair chosen before the real tree was read."; }
    // RAN: KEEL gate validate . -> 806 tracking file(s) validated clean.; exit=0 KEEL gate check-engine . -> .engine instance files validated clean (kernel-free; D0112 phase 2).; exit=0 KEEL gate guard --no-receipt . -> [guard] ALL PASS
    part livingDocsNameOnlyDeclaredCliVerbsStandupGateR1 : TestResult { :>> id = "421e1a9e-2bc8-4e3d-944f-f9eb0f21c914"; :>> outcome = VerdictKind::proposed; :>> judgedAgainst = "32d9424"; :>> judgedAt = "2026-09-13"; :>> judgedBy = "claudeFable5"; }
    verification livingDocsNameOnlyDeclaredCliVerbsImplementGate : Test { :>> id = "b9e39157-10e4-4ff2-ab8f-4aff7a66d5ab"; :>> title = "Sprint 703 implement gate"; :>> createdAt = "2026-09-13"; :>> createdBy = "claudeFable5"; :>> method = VerificationMethod::test; :>> procedureText = "Implemented as the DoD states; the guard ran on the tree before and after the corrections."; }
    // RAN: PROBE PAIR: cli-reference unit tests -> positive a_retired_verb_in_code_fails_naming_its_line_and_the_current_spelling_passes: PASS; negative (keel show why): PASS [guard:cli-reference] PASS — 438 scanned, 0 warning(s), 0 violation(s) TOUCHED RECEIPT: outcome=pass passed=801 failed=0 seconds=766
    part livingDocsNameOnlyDeclaredCliVerbsImplementGateR1 : TestResult { :>> id = "2c225202-1c53-4f29-8fd3-7c1e2ebaac66"; :>> outcome = VerdictKind::pass; :>> judgedAgainst = "32d9424"; :>> judgedAt = "2026-09-13"; :>> judgedBy = "claudeFable5"; }
    verification livingDocsNameOnlyDeclaredCliVerbsReviewGate : Test { :>> id = "58879223-6acd-4dca-9a0b-5df081360438"; :>> title = "Sprint 703 review gate — three passes per D0172"; :>> createdAt = "2026-09-13"; :>> createdBy = "claudeFable5"; :>> method = VerificationMethod::inspect; :>> procedureText = "Three passes per D0172: the scanner's code/prose rule against the 442 hits the first run examined (one scanner defect found and fixed: a sentence-final period read as a root argument, keel itself.); the suggestion text against cli_facts (a retired verb that is a sub-verb of one router names that router, a lens names show); the scope against tool-reference's (Decisions and .tracking excluded as history)."; }
    // RAN: KEEL gate validate . -> 806 tracking file(s) validated clean.; exit=0 KEEL gate check-engine . -> .engine instance files validated clean (kernel-free; D0112 phase 2).; exit=0 KEEL gate guard --no-receipt . -> [guard] ALL PASS
    part livingDocsNameOnlyDeclaredCliVerbsReviewGateR1 : TestResult { :>> id = "06427ef5-cfa9-4c57-99df-b3571f755ae3"; :>> outcome = VerdictKind::proposed; :>> judgedAgainst = "32d9424"; :>> judgedAt = "2026-09-13"; :>> judgedBy = "claudeFable5"; }
    verification livingDocsNameOnlyDeclaredCliVerbsCloseOutGate : Test { :>> id = "3e1eac8e-3f5d-413e-9db8-c0bda7f0d481"; :>> title = "Sprint 703 closeOut gate (autonomous, D0049)"; :>> createdAt = "2026-09-13"; :>> createdBy = "claudeFable5"; :>> method = VerificationMethod::inspect; :>> procedureText = "Autonomous per D0049; the sprint file is the record."; }
    // RAN: KEEL gate validate . -> 806 tracking file(s) validated clean.; exit=0 KEEL gate check-engine . -> .engine instance files validated clean (kernel-free; D0112 phase 2).; exit=0 KEEL gate guard --no-receipt . -> [guard] ALL PASS
    part livingDocsNameOnlyDeclaredCliVerbsCloseOutGateR1 : TestResult { :>> id = "a19137cb-12b3-4796-a3dc-f316266a6e88"; :>> outcome = VerdictKind::proposed; :>> judgedAgainst = "32d9424"; :>> judgedAt = "2026-09-13"; :>> judgedBy = "claudeFable5"; }
    verification livingDocsNameOnlyDeclaredCliVerbsRetroGate : Test { :>> id = "3cc7b5e5-bff2-47a2-aad5-d7e1abc2df95"; :>> title = "Sprint 703 retro gate (autonomous, D0049)"; :>> createdAt = "2026-09-13"; :>> createdBy = "claudeFable5"; :>> method = VerificationMethod::analyze; :>> procedureText = "Avoidable issues scanned: findings become Issues, not prose. Tracked: issue531 (the survey that sized issue528 was a scratchpad script and overcounted by two; the guard's examined set is not listable) with resolver dcCliReferencesAreAListableLens, added in this commit; issue532 (the RECORDER wrote outside keel record - textpatch on this file - and re-recorded the red retro gate three times, and check_report.py passed the report because it reads only markers and the last line) with resolver dcRecorderReportRefusesNonRecordWrites, added in this commit. Closed in-sprint, no item needed: the guard's first run on the real tree was the scanner's real test - the unit pair passed while keel itself. was still a false positive, so a text-scanning guard's D0388 pair should carry a prose corpus line; and the recorder brief's own wording was the guard's second true positive outside the survey, so a brief dispatched verbatim is a living doc even when written as a fence."; }
    // RAN: KEEL gate validate . -> 806 tracking file(s) validated clean.; exit=0 KEEL gate check-engine . -> .engine instance files validated clean (kernel-free; D0112 phase 2).; exit=0 KEEL gate guard --no-receipt . -> [guard] ALL PASS
    part livingDocsNameOnlyDeclaredCliVerbsRetroGateR4 : TestResult { :>> id = "f6f7f943-3b87-4853-91fc-a75e0fb247f1"; :>> outcome = VerdictKind::proposed; :>> judgedAgainst = "32d9424"; :>> judgedAt = "2026-09-13"; :>> judgedBy = "claudeFable5"; }
}
