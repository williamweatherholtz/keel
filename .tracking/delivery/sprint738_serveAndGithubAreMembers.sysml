// ProjectDeliveryS738 — Sprint 738: the console is a member - dcServeAndGithubAreMembers, the eighth D0479 extraction, chartered by D0479. serve.rs, deck.rs, launcher.rs, console_registry.rs, reports.rs and attestation.rs leave keel-cli/src for members/keel-serve/src with the console page they embed; ci_runs.rs joins members/keel-github (which gains keel-json, keel-git and keel-model); verification.rs joins members/keel-view; and the orient computation (OrientReport, compute_orient_state, orient_root, whats_next_root) is sliced out of keel-cli's lib.rs into members/keel-model/src/readiness.rs so the console reads the frontier from the read model, not the binary. keel-cli's lib.rs re-exports every moved module and the four orient names at their old paths, so no caller in main.rs or the tests moved; keel-cli's manifest drops tokio, axum, async-stream, tokio-stream and the tower dev-dep. Three locked files change only a path string that follows its source: hardening.rs's api_surface lens and route test, and the obligation-review process and skill-registry sentences that cite deck.rs. D0509 (marked process-change, HELD, #DependsOn d0479) records the layering.. EXECUTE. 8 pts.
package ProjectDeliveryS738 {
    private import EngineElement::*;
    private import EngineWork::*;
    private import EngineVerification::*;
    private import EngineRelationships::*;

    #CharteredBy dependency from serveAndGithubAreMembersStory to d0479;

    part serveAndGithubAreMembersStory : Story {
        :>> id = "9be0cb2c-4b96-4415-9e56-8bc78d7e474d";
        :>> title = "Sprint 738: the console is a member - dcServeAndGithubAreMembers, the eighth D0479 extraction, chartered by D0479. serve.rs, deck.rs, launcher.rs, console_registry.rs, reports.rs and attestation.rs leave keel-cli/src for members/keel-serve/src with the console page they embed; ci_runs.rs joins members/keel-github (which gains keel-json, keel-git and keel-model); verification.rs joins members/keel-view; and the orient computation (OrientReport, compute_orient_state, orient_root, whats_next_root) is sliced out of keel-cli's lib.rs into members/keel-model/src/readiness.rs so the console reads the frontier from the read model, not the binary. keel-cli's lib.rs re-exports every moved module and the four orient names at their old paths, so no caller in main.rs or the tests moved; keel-cli's manifest drops tokio, axum, async-stream, tokio-stream and the tower dev-dep. Three locked files change only a path string that follows its source: hardening.rs's api_surface lens and route test, and the obligation-review process and skill-registry sentences that cite deck.rs. D0509 (marked process-change, HELD, #DependsOn d0479) records the layering. (8 pts)";
        :>> createdAt = "2026-09-17"; :>> createdBy = "claudeFable5"; :>> kind = WorkKind::code; :>> priority = WorkPriority::p0; :>> owner = "claudeFable5"; :>> estimatedPoints = 8;
    }

    action def DeliveryRunS738 {
        action storyServeAndGithubAreMembers;
        verification storyServeAndGithubAreMembersDoD : Test { :>> id = "2d079d92-1550-42d1-9339-499f2b87f1e7"; :>> method = VerificationMethod::test; :>> procedureText = "DELIVERED BACKLOG ITEMS: dcServeAndGithubAreMembers. DONE MEANS: members/keel-serve holds serve.rs, deck.rs, launcher.rs, console_registry.rs, reports.rs, attestation.rs and assets/console.html under the member lint preamble, with a Cargo.toml naming eleven members, serde, serde_json, toml, tokio, axum, async-stream and tokio-stream and dev-deps keel-fs and tower; members/keel-github/src holds ci_runs.rs and its manifest names keel-json, keel-git, keel-model and serde_json; members/keel-view/src holds verification.rs; members/keel-model/src/readiness.rs holds the orient computation; keel-cli/src holds none of the eight files and no console.html, and its lib.rs re-exports each at its old path; the root manifest lists members/keel-serve before keel-cli and keel-cli's manifest depends on it without tokio, axum, async-stream, tokio-stream or tower; hardening.rs reads members/keel-serve/src/serve.rs and members/keel-serve/assets/console.html; the deliverable manifest's serveItemActions and rustS7QueryAlign rows and the code registry's ceServeJudgment and ceLauncher elements name the new paths; scripts/extract_serve.py is the idempotent transform (dry-run default; 8 files moved with 294 crate:: references each kept or rewritten, 2 include paths re-anchored, 1 asset moved, 1 slice of 6327 chars conserved, 28 anchored edits in 12 staying files, 3 files written; re-run says already applied); cargo clippy --release --workspace --all-targets -D warnings clean; keel --help byte-identical to the pre-move render (cmp help_before738.txt help_after738.txt, 15089 bytes) and keel version's guard line unchanged (75: 66 hard-blocking, 9 warning-only); python scripts/modgraph.py --check and python scripts/module_home.py --probe hold. Known-positive, chosen before the tree is read (the DoD's own words): cargo tree -p keel-serve names no keel-cli and cargo tree -p keel-github names no keel-view, keel-guards, keel-process, keel-suite or keel-serve; touching members/keel-serve/src/serve.rs recompiles keel-serve and keel-cli under cargo build --release --verbose with all fifteen other members Fresh; device_bound_taps (1), gesture_citation_is_the_commands (2), launcher_controls_actually_fire (3) and the keel-serve (39) and keel-github (17) unit tests pass; keel --help equals the pre-move capture (pos738.py). Known-negative: a pub use keel_view::view planted in members/keel-github/src/lib.rs fails cargo check -p keel-github naming the undeclared crate keel_view, lib.rs restored bytes and mtime on every path (neg738.py). The DoD's prose and the tree do not both hold at two points, and the probe is the contract (sprints 734-737): (1) 'keel-serve holds ... claude_surface' - claude_surface has been keel-write's since sprint 733 (the launcher and sync read it through keel_write::claude_surface) and does not move; (2) reports.rs and attestation.rs, which the prose does not name, ride with serve because each reads across the whole stack (guards' readiness, the view layer, reverify, the actor) and no lower member can hold them without depending upward - D0509 records the ruling."; }
        // RAN: keel-serve verify . --probe-from pair738.txt -> outcome=pass stopped_at=none seconds=637 at=1789675650 (validate=pass guard=pass clippy=pass probe=pass touched=pass); PROBE PAIR pos738.py pass, neg738.py pass; TOUCHED RECEIPT outcome=pass passed=745 failed=0 seconds=121 stems=[attestation, ci_runs, console_registry, deck, hardening, init, launcher, readiness, reports, serve, verification]; keel-serve gate check-engine . exit=0; keel-serve sync-claude --check . exit=0 (47 skills) - the verifier's receipt, DISCREPANCIES: NONE
        part storyServeAndGithubAreMembersDoDR1 : TestResult { :>> id = "94eef9a2-f24f-467a-b142-d6610c91b656"; :>> outcome = VerdictKind::pass; :>> judgedAgainst = "904ff24c"; :>> judgedAt = "2026-09-17"; :>> judgedBy = "claudeFable5"; }
    }

    verification serveAndGithubAreMembersRefineGate : Test { :>> id = "ccd430c3-12c0-4348-bac4-8d87376fc028"; :>> title = "Sprint 738 refine gate (DoR)"; :>> createdAt = "2026-09-17"; :>> createdBy = "claudeFable5"; :>> method = VerificationMethod::inspect; :>> procedureText = "DoR: dcServeAndGithubAreMembers is the first line of keel show whats-next at 904ff24c (brief 43 landed, CI conclusion success). Chartered by D0479 (accepted) through its #CharteredBy edge; #DependsOn dcKeelIssuesIsAMember and dcProcessIsAMember, both done. Sized 8 - eight files moved with a codemod across three destination crates, one slice out of keel-cli's lib.rs into a new keel-model module, one asset moved with its include, one new member manifest and two manifests gaining dependencies, three locked-path string edits, two manifest rows and two registry elements, the D0388 pair as two scripts, and a marked Decision. Not split: sprint-planning permits 8 and a split would land a console whose reports render from a crate above it. Three locked-path edits (members/keel-guards/src/hardening.rs, .engine/processes/obligation-review.sysml, .engine/skills/obligation-review/registry.sysml - each a path string following the file it names) require the marked Decision D0509, HELD for the human; the sprint is not blocked on it - the guard reads the same file at its new home and the brief carries the question. Blocking dependencies: none."; }
    // RAN: LADDER: keel-serve verify . --probe-from pair738.txt -> outcome=pass stopped_at=none
    part serveAndGithubAreMembersRefineGateR1 : TestResult { :>> id = "be027330-cbdb-4350-99c2-ebad10d11423"; :>> outcome = VerdictKind::proposed; :>> judgedAgainst = "904ff24c"; :>> judgedAt = "2026-09-17"; :>> judgedBy = "claudeFable5"; }
    verification serveAndGithubAreMembersStandupGate : Test { :>> id = "191f8db0-aec7-4171-922b-a56126698ffd"; :>> title = "Sprint 738 standup gate"; :>> createdAt = "2026-09-17"; :>> createdBy = "claudeFable5"; :>> method = VerificationMethod::inspect; :>> procedureText = "Owner claudeFable5. Blocker: none - 904ff24c landed with CI success, no ladder or land is running; the human's serve runs from the pin cache, so the release image rebuilds freely. Order: (1) scripts/extract_serve.py: git mv the eight files and the asset, rewrite crate:: paths per destination map (serve, github, view), slice the orient block into readiness.rs, write the member's Cargo.toml and lib.rs, edit the manifests, keel-cli's lib.rs re-exports and dead imports, hardening.rs, the deliverable manifest, the code registry and the two process sentences; dry-run reconciled, then --apply. (2) cargo build --release, clippy --workspace --all-targets, keel --help against help_before738.txt, keel version, cargo test on keel-serve, keel-github, keel-view verification, keel-guards hardening, the three serve integration tests, cli_bdd and orient_bdd. (3) pos738/neg738; pair738.txt; modgraph --check; module_home --probe. (4) doc-sync (the two obligation-review sentences are the only living prose naming a moved path), sync-claude --check. (5) D0509 (marker process-change, HELD), the two retro Issues with resolvers, the sprint with the retro filled, brief 44 through decision-surfacing (pending set changes); verifier with the pair file; recorder --owed 7; land; CI conclusion."; }
    // RAN: LADDER: keel-serve verify . --probe-from pair738.txt -> outcome=pass stopped_at=none
    part serveAndGithubAreMembersStandupGateR1 : TestResult { :>> id = "8a94b44e-5860-4089-b5ee-8d650370b3fe"; :>> outcome = VerdictKind::proposed; :>> judgedAgainst = "904ff24c"; :>> judgedAt = "2026-09-17"; :>> judgedBy = "claudeFable5"; }
    verification serveAndGithubAreMembersImplementGate : Test { :>> id = "bc222508-1ab3-4cea-b57f-dcec6bcd1f4f"; :>> title = "Sprint 738 implement gate"; :>> createdAt = "2026-09-17"; :>> createdBy = "claudeFable5"; :>> method = VerificationMethod::test; :>> procedureText = "The implement gate is the DoD's own probes plus the ladder: python scripts/extract_serve.py dry run reconciled (8 files, 294 refs, 2 include paths, 1 asset, 1 slice, 28 edits in 12 files, 3 written), --apply, cargo build --release Finished clean on the first build; cargo clippy --release --workspace --all-targets -- -D warnings Finished clean; cmp help_before738.txt help_after738.txt byte-identical (15089 bytes); keel version guards line 75 (66 hard-blocking, 9 warning-only); python scripts/modgraph.py --check exit 0 (71 modules); python scripts/module_home.py --probe 0 failures; cargo test --release -p keel-serve 39 passed, -p keel-github 17 passed, -p keel-view --lib verification 5 passed, -p keel-guards --lib hardening 12 passed, -p keel-cli --test device_bound_taps 1, --test gesture_citation_is_the_commands 2, --test launcher_controls_actually_fire 3 passed, --test cli_bdd 6 scenarios 21 steps, --test orient_bdd 8 scenarios 40 steps passed; python pos738.py PASS; python neg738.py PASS (cargo check rc 101 naming keel_view, lib.rs restored); keel gate validate 853 clean with D0509, issue593, issue594 and the two resolver items in the tree; keel gate check-engine clean; keel sync-claude --check matches (47 skills)."; }
    // RAN: LADDER: keel-serve verify . --probe-from pair738.txt -> outcome=pass stopped_at=none
    part serveAndGithubAreMembersImplementGateR1 : TestResult { :>> id = "284c1509-8985-4760-865a-9c3f99e1650f"; :>> outcome = VerdictKind::pass; :>> judgedAgainst = "904ff24c"; :>> judgedAt = "2026-09-17"; :>> judgedBy = "claudeFable5"; }
    verification serveAndGithubAreMembersReviewGate : Test { :>> id = "50482933-ed87-4747-80c5-8394f9ee10bb"; :>> title = "Sprint 738 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every moved test passes in its new crate (39 in keel-serve, 17 in keel-github, 5 verification tests in keel-view), every caller of the moved names resolves through a re-export (main.rs, the tests - zero caller edits), the hardening lens reads the console source at its new path and its route test passes, and the binary's help and guard count are the pre-move ones. Honesty: the negative plants in keel-github's lib.rs and asserts the compiler names the crate the member must not know, not merely that the build fails; the positive touches the console's own file and reads Fresh for all fifteen other members from cargo's verbose lines, checks both dependency trees by cargo tree rather than by reading manifests, and compares help to a capture taken before the move. Scope: three locked-path files are in the diff (hardening.rs, the obligation-review process, its skill registry - each a path string following the file it names), so D0509 carries the process-change marker and is co-committed HELD (D0209 cl.2); the process-change guard reads it. No hook, CI yml or rule edit."; }
    // RAN: LADDER: keel-serve verify . --probe-from pair738.txt -> outcome=pass stopped_at=none
    part serveAndGithubAreMembersReviewGateR1 : TestResult { :>> id = "14d75bb8-4537-4914-b0f7-096d3e132312"; :>> outcome = VerdictKind::proposed; :>> judgedAgainst = "904ff24c"; :>> judgedAt = "2026-09-17"; :>> judgedBy = "claudeFable5"; }
    verification serveAndGithubAreMembersCloseOutGate : Test { :>> id = "fb674958-210e-4b72-9411-938b3253733c"; :>> title = "Sprint 738 closeOut gate (autonomous, D0049)"; :>> createdAt = "2026-09-17"; :>> createdBy = "claudeFable5"; :>> method = VerificationMethod::inspect; :>> procedureText = "Landed when the verifier's receipt reads DISCREPANCIES: NONE and its probe rung row names pair738.txt, the recorder's report passes check_report.py --owed 7, git status -sb is clean after keel land and gh run list names the landing commit with conclusion success. The DoD result is recorded against dcServeAndGithubAreMembersDoD at that sha; D0509 is proposed and HELD (marker process-change: the three locked path strings), so the authority queue's pending set changes and brief 44 is published once through decision-surfacing. dcKeelCliIsThinDispatch's #DependsOn edge to this item is satisfied when the DoD result lands; it is the last extraction."; }
    // RAN: LADDER: keel-serve verify . --probe-from pair738.txt -> outcome=pass stopped_at=none
    part serveAndGithubAreMembersCloseOutGateR1 : TestResult { :>> id = "03e5f084-0371-43cd-a06c-292e005e7498"; :>> outcome = VerdictKind::proposed; :>> judgedAgainst = "904ff24c"; :>> judgedAt = "2026-09-17"; :>> judgedBy = "claudeFable5"; }
    verification serveAndGithubAreMembersRetroGate : Test { :>> id = "bb1cf0de-9dd1-486e-a1fe-68f0e04d5130"; :>> title = "Sprint 738 retro gate (autonomous, D0049)"; :>> createdAt = "2026-09-17"; :>> createdBy = "claudeFable5"; :>> method = VerificationMethod::analyze; :>> procedureText = "Written at close-out, before the verifier is dispatched; avoidable issues scanned (issue011), each finding a tracked item or the reason it is not. (1) The code registry's filePath values: eleven of twenty-five name files earlier extractions moved (nine distinct under keel-cli/src) and nothing reads them; this sprint's codemod corrected the two elements that are claudeFable5's and left claudeOpus5's nine (D0108). Tracked: issue593, resolver dcCodeRegistryPathsResolve (added this sprint) - a check that reads every filePath against the tree, plus the corrections. (2) Six leaf members (keel-actor, keel-git, keel-github, keel-json, keel-perf, keel-schema) carry no lint preamble while the codemod wrote one into keel-serve from a constant - two lint regimes in one workspace and the settle build cannot tell. Tracked: issue594, resolver dcMembersCarryTheLintPreamble (added this sprint). (3) The DoD's prose named claude_surface for keel-serve; it has been keel-write's since sprint 733 and did not move - the fifth sprint running (734-738) to read the probe as the contract over the prose. Not tracked beyond what 737's retro already said: the next member DoD (dcKeelCliIsThinDispatch) is the last and its prose names only the probe. (4) reports.rs and attestation.rs were not in the DoD's list and had no lower home; they ride with serve. NOT A FORK: each reads across the stack and any lower home depends upward; D0509 records it. (5) D0508's file carried no #DependsOn edge although brief 43's page comment said it did (checked by git grep at 904ff24c: only the #SupersedeClause line) - the edge was described and not authored, the dual-truth class. Fixed in this commit: the two edges (d0479, d0506) added to 0508's file, and D0509's edge to d0479 authored with it. Not tracked as an Issue: record decision has no --depends-on flag, so the edge is a hand line after the write; a --depends-on flag that authors the edge with the Decision (D0352's shape) is the control if the miss recurs - one instance is not a pattern, but it is the trigger. (6) The codemod applied clean on the first build with no fix-up pass - the first extraction of eight to do so; the design inventory (every crate:: path per file counted before the script was written) is what changed. Non-finding. (7) Three locked files change a path string only; the marked Decision is HELD while the code is on main - the fourth HELD extraction Decision (D0506, D0508 precedents). Not tracked: D0209 cl.2 is the control and it fired as designed. (8) readiness.rs carries no unit tests: the orient slice had none in lib.rs (its scenarios are orient_bdd's 8, which pass through the re-export). Not tracked: the coverage is where it was; a test that the re-export resolves is orient_bdd itself. (9) Added after the first verifier run: its touched rung spanned a 97-minute host standby (Kernel-Power 506 at 11:59:01, 507 at 13:36:04; 18 in-flight tests at 5930-6040 s) and two clock-sensitive tests read red that pass in isolation in under six seconds - the receipt named the reds and not the standby, and the cause was read from the Windows event log by hand. Third instance of issue481/issue534's class in the form no fixture margin absorbs. Tracked: issue595, resolver dcSuiteReceiptNamesTheStandbyItSpanned (added this sprint) - the runner measures suspended time into the receipt and re-runs a red once in isolation when the run spanned a standby. The ladder was re-run for this sprint's receipt."; }
    // RAN: LADDER: keel-serve verify . --probe-from pair738.txt -> outcome=pass stopped_at=none
    part serveAndGithubAreMembersRetroGateR1 : TestResult { :>> id = "01760941-a8f5-4933-890a-2ee69ba5883e"; :>> outcome = VerdictKind::proposed; :>> judgedAgainst = "904ff24c"; :>> judgedAt = "2026-09-17"; :>> judgedBy = "claudeFable5"; }
}
