// ProjectDeliveryS722 — Sprint 722: dcVerifyReceiptSaysRunning, the correction for issue565 - the verify receipt held the previous run's fail while the sprint 721 ladder ran, and the D0425 verifier read it as its own. The receipt now says running from before the first rung, and a census test holds every receipt writer to the same form.. EXECUTE. 1 pts.
package ProjectDeliveryS722 {
    private import EngineElement::*;
    private import EngineWork::*;
    private import EngineVerification::*;
    private import EngineRelationships::*;

    #CharteredBy dependency from verifyReceiptSaysRunningStory to d0387;

    part verifyReceiptSaysRunningStory : Story {
        :>> id = "cfe3d2e8-c113-42cf-ace8-eccb864da42f";
        :>> title = "Sprint 722: dcVerifyReceiptSaysRunning, the correction for issue565 - the verify receipt held the previous run's fail while the sprint 721 ladder ran, and the D0425 verifier read it as its own. The receipt now says running from before the first rung, and a census test holds every receipt writer to the same form. (1 pts)";
        :>> createdAt = "2026-09-15"; :>> createdBy = "claudeFable5"; :>> kind = WorkKind::code; :>> priority = WorkPriority::p0; :>> owner = "claudeFable5"; :>> estimatedPoints = 1;
    }

    action def DeliveryRunS722 {
        action storyVerifyReceiptSaysRunning;
        verification storyVerifyReceiptSaysRunningDoD : Test { :>> id = "c9479f87-6ae4-466c-b9b1-2511c4479e33"; :>> method = VerificationMethod::test; :>> procedureText = "DELIVERED BACKLOG ITEMS: dcVerifyReceiptSaysRunning. DONE MEANS: keel verify rewrites .keel/metrics/verify-receipt.toml BEFORE every rung with outcome = 'running', the rung in flight under `running`, this run's head, an `at` of the write (the launch for the first stub) and only the [[rung]] blocks finished so far; the final write carries the verdict and stopped_at with running = 'none'; a receipt from before the form (no `running` key) parses as finished. Resolves issue565. The control (D0047, the issue322 pattern): a unit test in verify.rs reads every module in the crate holding a `.keel/metrics/*` RECEIPT constant that renders an `outcome` and fails for one that never renders 'running' - today suite.rs, touched.rs, verify.rs, and a fourth cannot ship without joining the list AND the form; the census predicate is itself probed on a fabricated writer without the word (named) and one with it (passed). VERIFIED BY: cargo test --release --lib verify:: green (9 tests: the D0388 pair a_receipt_mid_run_says_running_and_a_finished_one_says_its_verdict, the census pair); cargo clippy --all-targets clean; a live keel verify read at launch+8 s says outcome = 'running', running = 'validate', at = the launch epoch, 0 rungs; read during clippy it says running = 'clippy' with validate and guard passed; the ladder run from keel-serve.exe green with the D0388 pair."; }
        // RAN: LADDER: outcome=pass stopped_at=none seconds=7
        part storyVerifyReceiptSaysRunningDoDR1 : TestResult { :>> id = "b0a123fd-0375-4682-9eb2-ce1384cfc7fa"; :>> outcome = VerdictKind::pass; :>> judgedAgainst = "222a8d8"; :>> judgedAt = "2026-09-15"; :>> judgedBy = "claudeFable5"; }
    }

    verification verifyReceiptSaysRunningRefineGate : Test { :>> id = "5d0fd0a9-a6a0-41e9-aac9-bf74c6db9c16"; :>> title = "Sprint 722 refine gate (DoR)"; :>> createdAt = "2026-09-15"; :>> createdBy = "claudeFable5"; :>> method = VerificationMethod::inspect; :>> procedureText = "DoR: chartered by d0387 (the running-stub Decision this extends to the third receipt); 1 point - one module, one struct field, one callback, three tests, no schema; the head of the frontier at 222a8d8; blocking dependency none; the DoD Test is in this file."; }
    // RAN: DoR: chartered by d0387; head 222a8d8 frontier verified
    part verifyReceiptSaysRunningRefineGateR1 : TestResult { :>> id = "79256e3f-dca3-4ae8-90ee-78274c728aa1"; :>> outcome = VerdictKind::proposed; :>> judgedAgainst = "222a8d8"; :>> judgedAt = "2026-09-15"; :>> judgedBy = "claudeFable5"; }
    verification verifyReceiptSaysRunningStandupGate : Test { :>> id = "1d78d879-a952-471d-ad31-9ed5df154e90"; :>> title = "Sprint 722 standup gate"; :>> createdAt = "2026-09-15"; :>> createdBy = "claudeFable5"; :>> method = VerificationMethod::inspect; :>> procedureText = "Frontier at 222a8d8: dcVerifyReceiptSaysRunning first, dcRetroScanIsCheckedAtTheWrite second (both from sprint 721's own ceremony), then the Delivery items the new requirements govern (dcViewIsAMember, dcSuiteIsAMember). Blockers: none."; }
    // RAN: Frontier: 222a8d8; blockers none; verify LADDER outcome=pass
    part verifyReceiptSaysRunningStandupGateR1 : TestResult { :>> id = "8d033fff-ff81-4369-8221-571c190a2b8b"; :>> outcome = VerdictKind::proposed; :>> judgedAgainst = "222a8d8"; :>> judgedAt = "2026-09-15"; :>> judgedBy = "claudeFable5"; }
    verification verifyReceiptSaysRunningImplementGate : Test { :>> id = "91d1eac3-c491-407f-b93b-28d23940e1c7"; :>> title = "Sprint 722 implement gate"; :>> createdAt = "2026-09-15"; :>> createdBy = "claudeFable5"; :>> method = VerificationMethod::test; :>> procedureText = "Ladder gains in_flight and outcome(); climb takes a progress callback fired before each rung with the steps so far; cmd rewrites the receipt through it and once more at the end; render emits `running = <rung|none>`, parse reads it with `none` as the legacy default; help names the form. Tests: the running/finished/legacy triple, the census over the crate, the census predicate probed both ways. Order followed as written in the DoD."; }
    // RAN: LADDER passed: validate=pass guard=pass clippy=pass probe=pass touched=pass
    part verifyReceiptSaysRunningImplementGateR1 : TestResult { :>> id = "1934b7a3-637e-4d13-9840-008e2830014c"; :>> outcome = VerdictKind::pass; :>> judgedAgainst = "222a8d8"; :>> judgedAt = "2026-09-15"; :>> judgedBy = "claudeFable5"; }
    verification verifyReceiptSaysRunningReviewGate : Test { :>> id = "7603921d-e2a0-40cc-b811-8dcb9c453c86"; :>> title = "Sprint 722 review gate — three passes per D0172"; :>> createdAt = "2026-09-15"; :>> createdBy = "claudeFable5"; :>> method = VerificationMethod::inspect; :>> procedureText = "Three passes (D0172): the running stub is written by the same render as the verdict, so a reader parses one shape; a receipt with the previous run's verdict cannot survive the first progress call, which fires before rung one; the census predicate matches the word as a literal or inside a format string and is probed on a fabricated fourth writer before it is trusted on the crate. Residual: the census is a source-text read, not a type-level obligation - a writer that renders the word some other way needs the list edited, which is the point."; }
    // RAN: clippy=pass; PROBE PAIR: positive artefact.py: pass; negative module_home.py: pass
    part verifyReceiptSaysRunningReviewGateR1 : TestResult { :>> id = "f8ffece8-b9ea-48dd-b68e-4c5ef638f335"; :>> outcome = VerdictKind::proposed; :>> judgedAgainst = "222a8d8"; :>> judgedAt = "2026-09-15"; :>> judgedBy = "claudeFable5"; }
    verification verifyReceiptSaysRunningCloseOutGate : Test { :>> id = "1510d517-37a5-41b0-af2f-1cd8068329b9"; :>> title = "Sprint 722 closeOut gate (autonomous, D0049)"; :>> createdAt = "2026-09-15"; :>> createdBy = "claudeFable5"; :>> method = VerificationMethod::inspect; :>> procedureText = "Code, tests and help in verify.rs; the DoD result and six gates recorded from the verifier's receipt by the recorder; issue565 resolves when the resolver is done (computed). The test-verify skill already told the verifier a running stub exists (line 136); the code now keeps that promise."; }
    // RAN: keel gate check-engine: .engine instance files validated clean; LADDER outcome=pass
    part verifyReceiptSaysRunningCloseOutGateR1 : TestResult { :>> id = "676da40c-5780-44f3-ae67-fa4e22fcca7d"; :>> outcome = VerdictKind::proposed; :>> judgedAgainst = "222a8d8"; :>> judgedAt = "2026-09-15"; :>> judgedBy = "claudeFable5"; }
    verification verifyReceiptSaysRunningRetroGate : Test { :>> id = "bf66311d-cacf-4637-9dd2-0a5830aec86a"; :>> title = "Sprint 722 retro gate (autonomous, D0049)"; :>> createdAt = "2026-09-15"; :>> createdBy = "claudeFable5"; :>> method = VerificationMethod::analyze; :>> procedureText = "Finding: this is the third receipt to gain the running form separately (issue399 suite, issue468 touched, issue565 verify) - each fix was scoped to the file that fired, and the file left out was the one that fired next. The census test is the cross-file control; the pattern (issue322: a control applied per file) is already tracked. Avoidable issues scanned (issue011): none new in this sprint - the ladder ran twice because the sprint record was authored after the first launch, a sequencing slip with no record consequence (the second run is the one recorded). No process improvement beyond the census."; }
    // RAN: DISCREPANCIES: NONE; third receipt form adoption complete; census control active
    part verifyReceiptSaysRunningRetroGateR1 : TestResult { :>> id = "cfce8ef3-ddff-4a61-9f3b-c55df84534b5"; :>> outcome = VerdictKind::proposed; :>> judgedAgainst = "222a8d8"; :>> judgedAt = "2026-09-15"; :>> judgedBy = "claudeFable5"; }
}
