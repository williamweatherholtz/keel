// ProjectDeliveryS707 — Sprint 707: Implement D0475 through dcNextestIsTheTouchedRunner: the touched set runs under cargo-nextest - binaries in parallel, one process per test - and the receipt carries every test's duration, so the run's long pole is named by measurement. The pain: 12-21 minute lands whose per-binary sum was known but whose critical path was not (issue536); the panel in perf-options-panel-2026-09-13 ranked the runner second. Also resolves issue539 through dcTouchedRunScrubsPerfFromTheChildEnv: the cargo child no longer inherits the operator's KEEL_PERF. Chartered by D0475 (process-change, accepted by the human 2026-09-14). 5 pts.. EXECUTE. 5 pts.
package ProjectDeliveryS707 {
    private import EngineElement::*;
    private import EngineWork::*;
    private import EngineVerification::*;
    private import EngineRelationships::*;

    #CharteredBy dependency from nextestIsTheTouchedRunnerStory to d0475;

    part nextestIsTheTouchedRunnerStory : Story {
        :>> id = "e6f66a17-2865-44c7-bf5d-1eba36d0f467";
        :>> title = "Sprint 707: Implement D0475 through dcNextestIsTheTouchedRunner: the touched set runs under cargo-nextest - binaries in parallel, one process per test - and the receipt carries every test's duration, so the run's long pole is named by measurement. The pain: 12-21 minute lands whose per-binary sum was known but whose critical path was not (issue536); the panel in perf-options-panel-2026-09-13 ranked the runner second. Also resolves issue539 through dcTouchedRunScrubsPerfFromTheChildEnv: the cargo child no longer inherits the operator's KEEL_PERF. Chartered by D0475 (process-change, accepted by the human 2026-09-14). 5 pts. (5 pts)";
        :>> createdAt = "2026-09-14"; :>> createdBy = "claudeFable5"; :>> kind = WorkKind::code; :>> priority = WorkPriority::p0; :>> owner = "claudeFable5"; :>> estimatedPoints = 5;
    }

    action def DeliveryRunS707 {
        action storyNextestIsTheTouchedRunner;
        verification storyNextestIsTheTouchedRunnerDoD : Test { :>> id = "cb3831cb-bcea-409b-ac2f-035cd9861e50"; :>> method = VerificationMethod::test; :>> procedureText = "DELIVERED: keel-cli/src/touched.rs - TestTiming and parse_nextest (rows by counter, LEAK is a pass, a retry is judged by its last word, the Summary re-list is not a second red), custom_harness_tests over the manifest (the three cucumber binaries run under cargo test in a second invocation), Runner with a cargo-test fallback when nextest is absent (NEXTEST_INSTALL names the pin), scrub_perf on every cargo child, --no-tests pass (a lib with no unit tests is not a red), run() partitions the set and merges both invocations into one log, the receipt gains runner and [[timing]] rows slowest first, the summary names the slowest test; suite.rs --help names the runner; guards.rs shallow-checkout and gate-environment-parity read `cargo nextest` as a test step; ci.yml and release.yml install nextest 0.9.144 from get.nexte.st and run the libtest binaries under it with the cucumber trio under cargo test, GH_TOKEN kept on the step; test-verify skill, guards.md and CLAUDE.md sect.4 name the runner and the receipt's new rows; the integration test asserts the runner and the timing row's verdict. VERIFY: lib touched:: tests 17 passed, 0 failed (the nextest parser pair, the manifest reader pair, the KEEL_PERF scrub pair); cargo test --release --test touched_tests_run_before_land -> 5 passed (fixture lands now run under nextest); clippy -D warnings clean; gate validate / check-engine / sync-claude --check clean, guard --no-receipt: process-change red until this record is co-committed (D0465), every other guard PASS; the real-tree run under the new runner: `keel suite --touched . --no-receipt` from keel-serve.exe, detached, head d64d319, at 1789373804: outcome pass, 823 passed, 0 failed, runner cargo-nextest 0.9.144, 68 binaries (the set grew to 823 tests because guards, init and suite are among the changed modules), 995 s wall in the receipt of which 265 s was the release build of every test target, 641 s the nextest Summary (823 tests, 50 slow), 60 s a rebuild before the cargo test invocation and the rest orient_bdd; 823 [[timing]] rows, the first four: lib view::tests::report_produces_cards_and_rejects_unknown 600394 ms, batched_governance_agrees the_batched_path_gives_the_same_answer_as_the_per_item_path 508229 ms, federation f1_a_scaffolded_project_can_make_its_first_commit_at_any_path_shape 407825 ms, land_gate land_refuses_to_push_a_workspace_carrying_a_broken_project 364905 ms. Against the D0474 receipt's cargo test run of the same day (63 binaries, 1246 s wall including its build) that is 1.25x on the receipt's own seconds. MEASURED, before vs after, same 63-binary set of 2026-09-14: cargo test 1246 s wall (per-binary sum 913 s); nextest 723 s at 20 threads, 653 s at 8, 701 s at 4 (test phase alone, 62 binaries); this run's receipt 995 s wall over 68 binaries with 265 s of build in it. The gain is 1.91x at best - UNDER the 2x of D0475's own consequence clause - and the receipt's first timing row says why: view::tests::report_produces_cards_and_rejects_unknown, 347-690 s under contention for a lib whose serial run is 145 s (issue540). The keep-or-supersede judgment on D0475 is deferred to the remeasure after issue540's resolver lands; this record does not make it."; }
        // RAN: Delivered as the DoD names: cargo test --release --lib -- touched:: -> 17 passed, 0 failed; cargo test --release --test touched_tests_run_before_land -> 5 passed; cargo clippy --release --all-targets -- -D warnings -> exit 0; KEEL suite --touched . --no-receipt (keel-serve.exe, detached, head d64d319, at 1789373804) -> outcome pass, 823 passed, 0 failed, runner cargo-nextest 0.9.144, 68 binaries, 995 s wall, 823 [[timing]] rows, slowest lib view::tests::report_produces_cards_and_rejects_unknown 600394 ms; gate validate 811 clean, check-engine clean, guard --no-receipt ALL PASS, sync-claude --check clean. Gain 1.91x at best, under D0475's 2x clause; the judgment on D0475 is deferred to the remeasure after issue540's resolver, not made by this result
        part storyNextestIsTheTouchedRunnerDoDR1 : TestResult { :>> id = "0ab7f1f5-f84e-439a-8327-1dea5ae9b45b"; :>> outcome = VerdictKind::pass; :>> judgedAgainst = "d64d319"; :>> judgedAt = "2026-09-14"; :>> judgedBy = "claudeFable5"; }
    }

    verification nextestIsTheTouchedRunnerRefineGate : Test { :>> id = "3fa2ce10-5bfe-49ad-9908-6b41b15ce506"; :>> title = "Sprint 707 refine gate (DoR)"; :>> createdAt = "2026-09-14"; :>> createdBy = "claudeFable5"; :>> method = VerificationMethod::inspect; :>> procedureText = "Chartered by D0475, accepted by the human 2026-09-14 with the process-change marker (CI workflows and guard source change; the receipt's meaning changes). Five points: a rewritten runner, a parser with its pair, two CI workflows, a guard needle, doc-sync and a real-tree measurement; the sprint-planning table puts a subsystem with tests at 5. DoR: dcNextestIsTheTouchedRunner ranks first on keel show whats-next at d64d319 after D0474 closed (declaration order is priority, D0052); the pair is the DoD's own; issue477 binds - no keel-cli/src or .engine edit while cargo or keel-land runs; nextest 0.9.144 installed on the host from get.nexte.st before the sprint (the measurement of 2026-09-14 used it)."; }
    // RAN: KEEL show whats-next . at d64d319 -> dcNextestIsTheTouchedRunner first, then dcVerifyLadderStopsAtTheFirstRed, dcReportTestBuildsTheModelOnce, dcBuildScriptDoesNotWatchTheGitIndex; d0475 accepted by wweatherholtz 2026-09-14 with the process-change marker (its acceptance is in the authority-queue's answered set); 5 points by the sprint-planning table (subsystem with tests); cargo nextest --version -> cargo-nextest 0.9.144 on the host
    part nextestIsTheTouchedRunnerRefineGateR1 : TestResult { :>> id = "6a46d79a-5741-4540-b51f-0a2bc4b2b327"; :>> outcome = VerdictKind::proposed; :>> judgedAgainst = "d64d319"; :>> judgedAt = "2026-09-14"; :>> judgedBy = "claudeFable5"; }
    verification nextestIsTheTouchedRunnerStandupGate : Test { :>> id = "7aba19cd-24cf-4052-8b03-4fb58cd25f1e"; :>> title = "Sprint 707 standup gate"; :>> createdAt = "2026-09-14"; :>> createdBy = "claudeFable5"; :>> method = VerificationMethod::inspect; :>> procedureText = "Order: measure first (three nextest runs at 20/8/4 threads against the cargo test wall already in the D0474 receipt) so the code is written against a known critical path; parser and manifest reader with their pairs; run() partition; the scrub; receipt and summary; suite help, guard needles, ci.yml and release.yml; doc-sync; rebuild, the integration test, the gates; the real-tree run detached from keel-serve.exe with --no-receipt; issue540 and its resolver ranked next; the sprint record; one CR: commit; keel-land; git status -sb and the CI conclusion read back."; }
    // RAN: Order followed as the standup names it: measured first (three nextest runs j20/j8/j4 in scratch s706, 797 passed each), then parser + manifest reader + pairs, run() partition, scrub, receipt/summary, suite help, guard needles, ci.yml + release.yml, doc-sync (test-verify SKILL.md, guards.md, CLAUDE.md sect.4), rebuild + keel sync-claude, integration test, gates, real-tree run detached, records, commit; issue477 held - no keel-cli/src or .engine edit while cargo or the touched run was live
    part nextestIsTheTouchedRunnerStandupGateR1 : TestResult { :>> id = "8233cb45-575f-407d-98ef-64ea2204c484"; :>> outcome = VerdictKind::proposed; :>> judgedAgainst = "d64d319"; :>> judgedAt = "2026-09-14"; :>> judgedBy = "claudeFable5"; }
    verification nextestIsTheTouchedRunnerImplementGate : Test { :>> id = "8a8c7768-8ca4-48d6-bd83-f3684e72328a"; :>> title = "Sprint 707 implement gate"; :>> createdAt = "2026-09-14"; :>> createdBy = "claudeFable5"; :>> method = VerificationMethod::test; :>> procedureText = "RAN: cargo nextest run over the 62 listable binaries plus the lib, three times (scratch s706/nextest_full.log j20 722.8 s, nextest_j8.log 653 s, nextest_j4.log 701 s; 797 passed each time, 49 slow at j20); cargo test --release --lib -- touched:: -> 17 passed, 0 failed (the nextest parser pair, the manifest reader pair, the KEEL_PERF scrub pair); cargo test --release --test touched_tests_run_before_land -> 5 passed after two corrections; cargo clippy --release --all-targets -- -D warnings -> clean after two fixes (a doc comment split by the patch anchor; match on an Option became map_or_else). Corrections in-sprint: nextest exits `error: no tests to run` on a selected binary with no tests - the fixture lib - and the fallback would have named every binary failing, so the command carries --no-tests pass; the integration test's `the red loses its row` assertion read the whole receipt and the new [[timing]] row for the red test tripped it - it now reads the observation table alone and asserts the timing row's fail verdict besides. device_bound_taps.rs reviewed for its fixed port: one test in the workspace binds one (7900 + pid % 80, device_bound_taps.rs:115) and nextest's one-process-per-test gives it a pid of its own; it passed in all three measured runs."; }
    // RAN: cargo test --release --lib -- touched:: -> 17 passed, 0 failed (nextest_rows_are_read_once_each_with_their_durations, custom_harness_targets_are_read_from_the_manifest, the_cargo_child_never_inherits_the_operators_perf_variable among them); cargo test --release --test touched_tests_run_before_land -> 5 passed, 53 s, after two in-sprint corrections (--no-tests pass; the receipt assertion reads the observation table alone); cargo clippy --release --all-targets -- -D warnings -> exit 0 after two fixes; KEEL sync-claude --check . -> keel-owned subset matches this binary's generator (47 registry skill(s))
    part nextestIsTheTouchedRunnerImplementGateR1 : TestResult { :>> id = "be22ccd1-7274-48eb-b412-b13a078e60da"; :>> outcome = VerdictKind::pass; :>> judgedAgainst = "d64d319"; :>> judgedAt = "2026-09-14"; :>> judgedBy = "claudeFable5"; }
    verification nextestIsTheTouchedRunnerReviewGate : Test { :>> id = "2ed8c661-d264-4e19-889a-2008cf74d931"; :>> title = "Sprint 707 review gate — three passes per D0172"; :>> createdAt = "2026-09-14"; :>> createdBy = "claudeFable5"; :>> method = VerificationMethod::inspect; :>> procedureText = "Three passes (D0172). Correctness: a row is a row only with the (n/N) counter, so the SLOW notice and the post-Summary re-list are not counted (the parser's pair); never_ran applies to each invocation alone, so a nextest list failure names every binary it was given and a cucumber failure names its own; failing is sorted and deduplicated across both. Honesty: the receipt says which runner ran; the cargo-test fallback is labelled and carries no timings rather than invented ones; the measured gain is quoted under D0475's own threshold instead of being rounded to it, and the judgment is deferred to a named remeasure, not made here. Scope: full `keel suite` (no --touched) still runs cargo test - out of D0475's clause, unchanged; `keel land` shares touched::run so it runs under nextest by construction; the count of `cargo test` needles in CI keeps gate-environment-parity's comparison on both workflows."; }
    // RAN: KEEL gate validate . -> 811 tracking file(s) validated clean.; KEEL gate check-engine . -> .engine instance files validated clean (kernel-free; D0112 phase 2).; KEEL gate guard --no-receipt . -> [guard] ALL PASS - 353 actionable warning(s) across 9 guard(s); exit=0 (process-change red before the sprint record existed, discharged by it under D0465). Three passes per D0172 read against touched.rs: parse_nextest_row requires the (n/N) counter so SLOW and the post-Summary re-list are not rows; never_ran is applied per invocation; failing sorted + deduped; the fallback runner is labelled and carries no timings; full keel suite unchanged (out of D0475's clause); device_bound_taps.rs:115 pid-derived port reviewed, one binder in the workspace
    part nextestIsTheTouchedRunnerReviewGateR1 : TestResult { :>> id = "a59d737f-a5c9-4a1f-b393-afbc970cd878"; :>> outcome = VerdictKind::proposed; :>> judgedAgainst = "d64d319"; :>> judgedAt = "2026-09-14"; :>> judgedBy = "claudeFable5"; }
    verification nextestIsTheTouchedRunnerCloseOutGate : Test { :>> id = "62ba69e3-cc54-48aa-a9c7-7215264793b9"; :>> title = "Sprint 707 closeOut gate (autonomous, D0049)"; :>> createdAt = "2026-09-14"; :>> createdBy = "claudeFable5"; :>> method = VerificationMethod::inspect; :>> procedureText = "Closes at the CR: commit that lands touched.rs, suite.rs, guards.rs, both workflows, the integration test, the doc-sync, the regenerated .claude surface, issue539's corrected text, issue540 with its resolver and this record together: keel-land runs the touched set from that commit under nextest (the code key moved with the commit, so every binary reruns); gate validate / check-engine / guard --no-receipt green over that tree; dcNextestIsTheTouchedRunnerDoD and dcTouchedRunScrubsPerfFromTheChildEnvDoD carry a pass each with the RAN receipts; issue536 and issue539 resolve by those passes; the CI conclusion for the landing commit - the first under nextest on ubuntu - is read back as success; git status -sb shows main level with origin."; }
    // RAN: TOUCHED RECEIPT: KEEL suite --touched . --no-receipt from keel-serve.exe detached -> outcome=pass passed=823 failed=0 seconds=995 runner=cargo-nextest 0.9.144 head=d64d319 at=1789373804 code_key=d03793a642caf4fb tree_key=6d6092bf058a2662, 68 binaries, 823 [[timing]] rows; log touched-1789372807.log: release build 4m25s, nextest Summary 641.047s 823 tests run 823 passed (50 slow), a 59.55s rebuild before the cargo test invocation (issue541), orient_bdd under cargo test. Slowest: lib view::tests::report_produces_cards_and_rejects_unknown 600394 ms; batched_governance_agrees 508229 ms; federation f1 407825 ms; land_gate 364905 ms. The CR: commit and the land are the closing acts; their CI conclusion is read back after this record
    part nextestIsTheTouchedRunnerCloseOutGateR1 : TestResult { :>> id = "733a3023-63d9-4fdc-afbd-29b9a47fb979"; :>> outcome = VerdictKind::proposed; :>> judgedAgainst = "d64d319"; :>> judgedAt = "2026-09-14"; :>> judgedBy = "claudeFable5"; }
    verification nextestIsTheTouchedRunnerRetroGate : Test { :>> id = "baed291d-bdbb-4c83-aa13-1eac8bdd11e4"; :>> title = "Sprint 707 retro gate (autonomous, D0049)"; :>> createdAt = "2026-09-14"; :>> createdBy = "claudeFable5"; :>> method = VerificationMethod::analyze; :>> procedureText = "Avoidable issues scanned; findings are tracked items, not prose. Finding one: the number D0475 is judged by is not about the runner - one unit test builds the model eight times over the real tree and is the last test standing in every configuration; issue540, resolver dcReportTestBuildsTheModelOnce, ranked next in the backlog, and the D0475 keep/supersede judgment waits on its remeasure. Finding two: issue539's record and its resolver's DoD said the perf report was on stdout; main.rs already wrote it to stderr and the tests read both streams as one - the records were corrected in this sprint under owner edit, and the lesson is the contract's own: a defect claim names the file:line read. Finding three: the harness = false binaries cannot run under nextest, so the runner is two invocations, and CI mirrors the split by hand (-E 'not (binary(...))'); a workflow that drifts from the manifest would go unnoticed - not tracked as an Issue because custom_harness_tests reads the manifest and its test pins the real trio, so a fourth cucumber binary fails that test before it can drift. Finding four: the cargo test invocation for the cucumber trio recompiled keel-cli for 60 s after nextest had just built it (log lines 1 and 978) - build.rs:47-51 watches ../.git/index, which git status, git ls-files and every self-reading test rewrite, so the provenance script reruns and the crate recompiles after nearly every run; issue541, resolver dcBuildScriptDoesNotWatchTheGitIndex, ranked behind issue540's. Closed in-sprint: the fixture lib's `no tests to run`."; }
    // RAN: Avoidable issues scanned: issue540 (the lib's long pole is one unit test building the model eight times; 600394 ms this run, 690/606/347 s in the j20/j8/j4 measurements, lib serial 145 s) resolver dcReportTestBuildsTheModelOnce, ranked after dcVerifyLadderStopsAtTheFirstRed; issue541 (build.rs:47-51 watches .git/index, so every cargo invocation after a test run recompiles keel-cli, 59.55 s in this run's log) resolver dcBuildScriptDoesNotWatchTheGitIndex, ranked next; issue539's record and its DoD corrected under owner edit (main.rs:5667 already writes the perf report to stderr; the tests read both streams as one) - the correction is the D0151 lesson, a defect claim names its file:line; the D0475 keep/supersede judgment (1.91x at best, under its 2x clause) is deferred to the remeasure after issue540's resolver and named so in the DoD result, not made here
    part nextestIsTheTouchedRunnerRetroGateR1 : TestResult { :>> id = "aeefb7f5-e600-4b47-9586-c8c45590dd36"; :>> outcome = VerdictKind::proposed; :>> judgedAgainst = "d64d319"; :>> judgedAt = "2026-09-14"; :>> judgedBy = "claudeFable5"; }
}
