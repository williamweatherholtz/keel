// ProjectDeliveryS695 — Sprint 695: Resolve issue432 and issue456: the routing rig scores a sample that spent its whole turn budget after a declared prefix as `budget`, apart from `none`, so a check that ran out is not read as a route that failed (D0381). Then re-run the release case at 6 turns and record what the samples establish. EXECUTE; 2 pts; dcPrefixLeavesRoomForTheRoute.. EXECUTE. 2 pts.
package ProjectDeliveryS695 {
    private import EngineElement::*;
    private import EngineWork::*;
    private import EngineVerification::*;
    private import EngineRelationships::*;

    #CharteredBy dependency from budgetVerdictTellsExhaustedFromNoneStory to d0381;

    part budgetVerdictTellsExhaustedFromNoneStory : Story {
        :>> id = "cb91dd58-2c66-4f1c-83a7-98e76544fce4";
        :>> title = "Sprint 695: Resolve issue432 and issue456: the routing rig scores a sample that spent its whole turn budget after a declared prefix as `budget`, apart from `none`, so a check that ran out is not read as a route that failed (D0381). Then re-run the release case at 6 turns and record what the samples establish. EXECUTE; 2 pts; dcPrefixLeavesRoomForTheRoute. (2 pts)";
        :>> createdAt = "2026-09-13"; :>> createdBy = "claudeFable5"; :>> kind = WorkKind::code; :>> priority = WorkPriority::p0; :>> owner = "claudeFable5"; :>> estimatedPoints = 2;
    }

    action def DeliveryRunS695 {
        action storyBudgetVerdictTellsExhaustedFromNone;
        verification storyBudgetVerdictTellsExhaustedFromNoneDoD : Test { :>> id = "1c54e52d-186f-45de-b4ca-153babe34925"; :>> method = VerificationMethod::test; :>> procedureText = "DELIVERED: routing_probe.py `score(skills, accept, turns_used, turns)` returns `budget` when a declared prefix was invoked, nothing accepted or wrong followed, and turns_used >= turns; `none` stays for a turn with no Skill call at all whatever it spent, and for a prefix-only turn that stopped short. run_one counts assistant messages as turns and takes the result event's num_turns when present; a budget sample's note prints `used/budget turns`. `--probe` carries the five budget cases (the two the DoD names plus the edges: no Skill call at the budget = none, route at the budget = routed, wrong at the budget = wrong). finding() reads a unanimous `budget` as a finding against the CHECK - `BUDGET ... the CHECK ran out, not the route (issue432): re-run with a larger --turns` - never as NOT ROUTING. The header's verdict table names it. Re-run at 6 turns: ROUTED release 3/3, prefix intake in every sample, $3.95 over 3 runs, 87s wall; the receipt on dcPrefixLeavesRoomForTheRouteDoD quotes the finding line and the spend. No rate or standing number introduced (D0378 C)."; }
        // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
        part storyBudgetVerdictTellsExhaustedFromNoneDoDR1 : TestResult { :>> id = "735b3d9f-4011-4e8e-9681-06b064fecd00"; :>> outcome = VerdictKind::pass; :>> judgedAgainst = "c8df10d"; :>> judgedAt = "2026-09-13"; :>> judgedBy = "claudeFable5"; }
    }

    verification budgetVerdictTellsExhaustedFromNoneRefineGate : Test { :>> id = "9230989b-30b0-4569-bc85-4e18cb9ef78b"; :>> title = "Sprint 695 refine gate (DoR)"; :>> createdAt = "2026-09-13"; :>> createdBy = "claudeFable5"; :>> method = VerificationMethod::inspect; :>> procedureText = "Chartered by D0381 (a check that disagrees with itself is a measurement defect to critique; issue456 was recorded under it). Two points: one pure function gains two inputs, five probe cases, one paid re-run of three samples. DoR: dcPrefixLeavesRoomForTheRouteDoD names the verdict, the probe cases and the re-run; the rig's --dry-run quoted the estimate ($3.78, ~2 min) before the run. Not a fork: the DoD fixed the design."; }
    // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
    part budgetVerdictTellsExhaustedFromNoneRefineGateR1 : TestResult { :>> id = "3db0b767-11a7-4eb7-80a5-68472e07e417"; :>> outcome = VerdictKind::proposed; :>> judgedAgainst = "c8df10d"; :>> judgedAt = "2026-09-13"; :>> judgedBy = "claudeFable5"; }
    verification budgetVerdictTellsExhaustedFromNoneStandupGate : Test { :>> id = "9ab95bdb-d2ce-41f8-9430-4cf96e9d78c3"; :>> title = "Sprint 695 standup gate"; :>> createdAt = "2026-09-13"; :>> createdBy = "claudeFable5"; :>> method = VerificationMethod::inspect; :>> procedureText = "Order (D0388: the probe before any model is paid for): patch score/probe/run_one/finding/mark from one scripted edit with asserted anchors; `--probe` must hold all 12 cases; `--dry-run` for the estimate; `--investigate release --samples 3 --turns 6`; read the finding line and the per-sample transcripts from .keel/metrics/routing-investigation.json; record the receipt on the DoD; sprint record; gates."; }
    // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
    part budgetVerdictTellsExhaustedFromNoneStandupGateR1 : TestResult { :>> id = "0b4e0083-2e15-45f0-9b02-f66cbebba749"; :>> outcome = VerdictKind::proposed; :>> judgedAgainst = "c8df10d"; :>> judgedAt = "2026-09-13"; :>> judgedBy = "claudeFable5"; }
    verification budgetVerdictTellsExhaustedFromNoneImplementGate : Test { :>> id = "e1b86b91-3bb8-4fc8-a64c-ff75f30eff7c"; :>> title = "Sprint 695 implement gate"; :>> createdAt = "2026-09-13"; :>> createdBy = "claudeFable5"; :>> method = VerificationMethod::test; :>> procedureText = "RAN: python .engine/tools/routing_probe.py --probe -> all 12 cases hold (the seven of sprint 638 plus: intake then two non-Skill turns to a 3-turn budget = budget; intake alone with one turn left = none; no Skill call at all to the budget = none; intake then release at the budget = routed; intake then stpa at the budget = wrong) and all 8 rubric cases hold. python .engine/tools/routing_probe.py --investigate release --samples 3 --turns 6 --dry-run -> estimated cost ~$3.78, ~2 min wall (per run $1.26, 38s, measured 2026-09-10). python .engine/tools/routing_probe.py --investigate release --samples 3 --turns 6 -> 1/3 ROUTED release #3 52.6s $1.136 prefix intake; 2/3 ROUTED release #1 60.8s $1.219 prefix intake; 3/3 ROUTED release #2 87.1s $1.595 prefix intake; ROUTED release: 3/3 samples agree; spend this investigation: $3.95 over 3 run(s), 87s wall (measured per run: $1.3165, 66.8s). Transcripts: every sample Skill(intake) then ToolSearch (one or two) then Skill(release) - the searches are the agent looking for intake's instrument after the sandbox disallowed Bash (issue456's cause), and at 6 turns the route is reached after them. Tree c8df10d."; }
    // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
    part budgetVerdictTellsExhaustedFromNoneImplementGateR1 : TestResult { :>> id = "50502860-9c87-4e0f-b950-78366bda792b"; :>> outcome = VerdictKind::pass; :>> judgedAgainst = "c8df10d"; :>> judgedAt = "2026-09-13"; :>> judgedBy = "claudeFable5"; }
    verification budgetVerdictTellsExhaustedFromNoneReviewGate : Test { :>> id = "874e29c8-bc8a-4df8-8b2b-4a23b6e1f7b2"; :>> title = "Sprint 695 review gate — three passes per D0172"; :>> createdAt = "2026-09-13"; :>> createdBy = "claudeFable5"; :>> method = VerificationMethod::inspect; :>> procedureText = "Three passes (D0172). Correctness: the verdict is decided by two facts the run records (the prefix, turns used against the budget) and never by the tools list, so a `budget` cannot be produced by a turn that made no Skill call - the third probe case holds that edge; a route or a wrong call at the last turn still wins over `budget` because score returns before the budget test - the fourth and fifth cases hold those. The five cases were chosen before the run and the run was paid for only after they held. Honesty: the finding is ROUTED 3/3 at 6 turns and is recorded as an investigation's finding on the item that motivated it, not as a rate and not as a TestResult of the release skill; the 3-turn `none` of 2026-09-09 and 2026-09-10 is not rewritten - the receipts of sprints 638 and 656 stand, and this receipt says what they were reading. Scope: routing_probe.py only; the DoD on dcPrefixLeavesRoomForTheRoute (created by claudeOpus5) is not edited (D0108/D0307) - the disallowed-Bash cause issue456 asked the DoD to name is carried in the receipt instead. Residual: the `budget` verdict reads the turn count, not why the turns were spent; a prefix that spends six turns searching would score `budget` again, and that would be the next Issue against the check, not a route finding."; }
    // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
    part budgetVerdictTellsExhaustedFromNoneReviewGateR1 : TestResult { :>> id = "766d2a5d-55d9-464e-8768-1f6644b8fea3"; :>> outcome = VerdictKind::proposed; :>> judgedAgainst = "c8df10d"; :>> judgedAt = "2026-09-13"; :>> judgedBy = "claudeFable5"; }
    verification budgetVerdictTellsExhaustedFromNoneCloseOutGate : Test { :>> id = "0d8a7a09-e787-4e89-b90b-39951c430adb"; :>> title = "Sprint 695 closeOut gate (autonomous, D0049)"; :>> createdAt = "2026-09-13"; :>> createdBy = "claudeFable5"; :>> method = VerificationMethod::inspect; :>> procedureText = "Closes on gate validate, gate check-engine and gate guard --no-receipt ALL PASS over the tree holding this sprint and the receipt; dcPrefixLeavesRoomForTheRouteDoD carries a pass with the RAN receipt; issue432 and issue456 resolve through it (computed)."; }
    // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
    part budgetVerdictTellsExhaustedFromNoneCloseOutGateR1 : TestResult { :>> id = "1b284f45-1a24-40ae-b864-9b7a336e1a81"; :>> outcome = VerdictKind::proposed; :>> judgedAgainst = "c8df10d"; :>> judgedAt = "2026-09-13"; :>> judgedBy = "claudeFable5"; }
    verification budgetVerdictTellsExhaustedFromNoneRetroGate : Test { :>> id = "420f53ad-6b9a-4e74-a548-f42c5ef6b0ed"; :>> title = "Sprint 695 retro gate (autonomous, D0049)"; :>> createdAt = "2026-09-13"; :>> createdBy = "claudeFable5"; :>> method = VerificationMethod::analyze; :>> procedureText = "AVOIDABLE-ISSUE SCAN (D0131): the samples show one empirical thing beyond the DoD - every sample spent one or two ToolSearch turns hunting for the instrument the intake prefix's procedure names, because the rig disallows Bash (issue456's cause). At 6 turns the route survives that; at 3 it did not. That cost is the sandbox's, not the skill's, and it is paid on every run of every case whose prefix is intake. Tracked as issue519 (Medium): the rig's sandbox removes the instrument the declared prefix's procedure runs, so every intake-prefixed sample spends turns on a search the real agent never makes; resolver dcRigSandboxKeepsThePrefixInstrument - a stub or allowed read-only `keel record statement --dry-run` path so the prefix completes in one turn, probed before and after with the same release case. Not a Decision: it is a one-off defect of the check with a measured basis, an Issue first."; }
    // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
    part budgetVerdictTellsExhaustedFromNoneRetroGateR1 : TestResult { :>> id = "bb9a36a0-a0a8-4034-8ffc-e92174010ff6"; :>> outcome = VerdictKind::proposed; :>> judgedAgainst = "c8df10d"; :>> judgedAt = "2026-09-13"; :>> judgedBy = "claudeFable5"; }
}
