// ProjectDeliveryS698 — Sprint 698: Resolve issue520: guard decision-scaffolding (keel-cli/src/guards.rs) re-read every line of every .tracking and .engine file once per candidate Decision, with two string allocations per line, and was the stop hook's critical path on 13 of its last 14 guard-running fires (4645-12463 ms). It now collects the corpus's inbound-edge targets ONCE into a set and answers each of the 151 candidates with one lookup; its verdicts are byte-identical. EXECUTE; 2 pts; dcDecisionScaffoldingIndexesItsEdgesOnce.. EXECUTE. 2 pts.
package ProjectDeliveryS698 {
    private import EngineElement::*;
    private import EngineWork::*;
    private import EngineVerification::*;
    private import EngineRelationships::*;

    #CharteredBy dependency from decisionScaffoldingIndexesItsEdgesOnceStory to d0414;

    part decisionScaffoldingIndexesItsEdgesOnceStory : Story {
        :>> id = "e913f6c0-2d03-4981-bf6b-2787067f8e60";
        :>> title = "Sprint 698: Resolve issue520: guard decision-scaffolding (keel-cli/src/guards.rs) re-read every line of every .tracking and .engine file once per candidate Decision, with two string allocations per line, and was the stop hook's critical path on 13 of its last 14 guard-running fires (4645-12463 ms). It now collects the corpus's inbound-edge targets ONCE into a set and answers each of the 151 candidates with one lookup; its verdicts are byte-identical. EXECUTE; 2 pts; dcDecisionScaffoldingIndexesItsEdgesOnce. (2 pts)";
        :>> createdAt = "2026-09-13"; :>> createdBy = "claudeFable5"; :>> kind = WorkKind::code; :>> priority = WorkPriority::p0; :>> owner = "claudeFable5"; :>> estimatedPoints = 2;
    }

    action def DeliveryRunS698 {
        action storyDecisionScaffoldingIndexesItsEdgesOnce;
        verification storyDecisionScaffoldingIndexesItsEdgesOnceDoD : Test { :>> id = "683e2a24-499e-45f1-ad02-46814c868991"; :>> method = VerificationMethod::test; :>> procedureText = "DELIVERED: inbound_edge_targets(texts) reads the X of every #CharteredBy / #DerivedFrom / #Resolves dependency from ... to X; line and of every satisfy X by line in one pass into a HashSet; unreached(candidates, targets) is the pre-grace filter; decision_scaffolding calls them where the per-candidate reachable closure was. The D0388 pair is pinned twice: on the pure core (four edge shapes read, a prose quotation / an untyped dependency / a chartered Decision not counted; the bare Decision named beside a chartered one) and through the public guard on a temp root (two bare accepted Decisions beside a chartered one: the OLDER is named, the newest exempt under the landing-sprint grace; one bare Decision, the newest violator, names nothing). The guard's warnings and violations on this tree are byte-identical before and after (9078 bytes each, diff exit 0). KEEL_PERF=2 timing quoted. The hookLatencyIndicator's ten-fire read-back is recorded when ten stop fires on the new binary exist, not before."; }
        // RAN: RAN: the story's DELIVERED clauses are the sprint 698 Implement gate's own receipt (line 28 of this file): cargo test --release --lib guards::inbound_edge_tests -> 2 passed 0 failed; clippy -D warnings exit 0; keel gate guard decision-scaffolding before vs after 9078 bytes each, diff exit 0; KEEL_PERF=2 phase guard:decision-scaffolding 4296/7905/4208 ms before, 2350/2111/2863 ms after. Landed as b9754c5; gh run list --json conclusion -> success for headSha b9754c5 (read back 2026-09-13). The ten-fire read-back is NOT this result: the story's own text records it later, and it is owed by dcDecisionScaffoldingIndexesItsEdgesOnceDoD and this sprint's CloseOut, both still open - .keel/metrics/hooks.jsonl holds 0 stop fires under build b9754c5 at this write.
        part storyDecisionScaffoldingIndexesItsEdgesOnceDoDR1 : TestResult { :>> id = "c03f8b2f-13b0-427a-af4a-addd1d61515a"; :>> outcome = VerdictKind::pass; :>> judgedAgainst = "b9754c5"; :>> judgedAt = "2026-09-13"; :>> judgedBy = "claudeFable5"; }
    }

    verification decisionScaffoldingIndexesItsEdgesOnceRefineGate : Test { :>> id = "2284a410-44cf-4248-a615-84e8091e196b"; :>> title = "Sprint 698 refine gate (DoR)"; :>> createdAt = "2026-09-13"; :>> createdBy = "claudeFable5"; :>> method = VerificationMethod::inspect; :>> procedureText = "Chartered by D0414 (slowHookFireExplainsItself, human-accepted, process-change marker): the fire ledger's phases field is what named decision-scaffolding as the critical path, and cutting the phase it names is the lineage sprints 644, 645 and 653 already ran under. keel-cli/src/guards.rs is keystone-locked; the D0465 path - a co-committed sprint record chartered by a marked Decision the human accepted - is the authority for this edit, so no new held Decision is added to the human's queue for a refactor whose verdicts are unchanged. Two points: one pure function, one filter, one call site, two tests, one timing pair. DoR: the DoD fixes the read-once shape, the byte-identical check, the fixture pair and the numbers to quote. One reading the DoD did not foresee, stated here rather than worked around: through the public guard a fixture with exactly one bare Decision can never warn - the landing-sprint grace pops the newest violator, and a lone violator is the newest - so the DoD's known positive is pinned on the pre-grace stage (unreached) and the public-guard positive uses two bare Decisions."; }
    // RAN: keel gate validate . -> tracking files validated clean; keel gate check-engine . -> .engine instance files validated clean; keel gate guard --no-receipt . -> ALL PASS, 0 violations, on the tree holding the guards.rs edit and sprint 698 chartered by d0414 (the process-change lock is satisfied on the D0465 path: a co-committed sprint record chartered by a marked Decision the human accepted; before the record existed the guard read FAIL naming keel-cli/src/guards.rs)
    part decisionScaffoldingIndexesItsEdgesOnceRefineGateR1 : TestResult { :>> id = "982bb8b5-06b0-48fd-a7b9-89ae15b0d361"; :>> outcome = VerdictKind::proposed; :>> judgedAgainst = "c071d43"; :>> judgedAt = "2026-09-13"; :>> judgedBy = "claudeFable5"; }
    verification decisionScaffoldingIndexesItsEdgesOnceStandupGate : Test { :>> id = "23460063-cd43-4b84-9ef5-19028994b660"; :>> title = "Sprint 698 standup gate"; :>> createdAt = "2026-09-13"; :>> createdBy = "claudeFable5"; :>> method = VerificationMethod::inspect; :>> procedureText = "Order: capture the before-verdicts and the before-timing from a copy of the current binary (keel-before.exe) while keel land ran, so no keel-cli edit raced the touched set (issue477); patch guards.rs from one scripted edit with asserted anchors after land exited; cargo test the pair, clippy -D warnings, release build, copy to the serve image; diff the after-verdicts; three alternating KEEL_PERF=2 pairs; sprint record chartered by d0414; gates; commit detached."; }
    // RAN: keel gate validate . -> tracking files validated clean; keel gate check-engine . -> .engine instance files validated clean; keel gate guard --no-receipt . -> ALL PASS, 0 violations, on the tree holding the guards.rs edit and sprint 698 chartered by d0414 (the process-change lock is satisfied on the D0465 path: a co-committed sprint record chartered by a marked Decision the human accepted; before the record existed the guard read FAIL naming keel-cli/src/guards.rs)
    part decisionScaffoldingIndexesItsEdgesOnceStandupGateR1 : TestResult { :>> id = "e2e5612f-816e-44a6-8e3e-62c7a34ca918"; :>> outcome = VerdictKind::proposed; :>> judgedAgainst = "c071d43"; :>> judgedAt = "2026-09-13"; :>> judgedBy = "claudeFable5"; }
    verification decisionScaffoldingIndexesItsEdgesOnceImplementGate : Test { :>> id = "45385cf0-922b-4c7c-8ba1-895bfc551948"; :>> title = "Sprint 698 implement gate"; :>> createdAt = "2026-09-13"; :>> createdBy = "claudeFable5"; :>> method = VerificationMethod::test; :>> procedureText = "RAN: cargo test --release --lib guards::inbound_edge_tests -> 2 passed 0 failed, first run (one fixture assertion was corrected on reading the code BEFORE the run: a `to d0905 ;` head lands the bytes 'd0905 ' in the set, harmless and the same thing the per-candidate ends_with saw, so the test asserts d0905 is unreached rather than that the bytes are absent). cargo clippy --release -p keel-cli --all-targets -- -D warnings -> exit 0. cargo build --release -> exit 0, copied to keel-serve.exe; .keel/bin/keel.exe (the hooks' binary) carries the same sha256 c77ddf43. keel gate guard decision-scaffolding . before (keel-before.exe) and after (keel-serve.exe): 9078 bytes each, diff exit 0 - 151 scanned, 31 warnings, 1 counted-history line, 0 violations, byte-identical. KEEL_PERF=2 keel gate guard --no-receipt . three alternating pairs, host 0F3DGVX25193H7: phase guard:decision-scaffolding before 4296 / 7905 / 4208 ms (the run's critical path at 5907 ms in the first capture), after 2350 / 2111 / 2863 ms, beside the ledger's 4645-12463 ms; the critical path after is acceptance-binds-to-text 3460 ms or priority-inversion 3839 / 4418 ms - decision-scaffolding is off it. hookLatencyIndicator live p90 at the change: 11812 ms over the last 25 stop fires, trigger above 10000 crossed, beside the declared 14125; the ten-fire read-back is owed and is recorded when it exists."; }
    // RAN: cargo test --release --lib guards::inbound_edge_tests -> 2 passed 0 failed; cargo clippy --release -p keel-cli --all-targets -- -D warnings -> exit 0; cargo build --release -> exit 0, copied to keel-serve.exe, .keel/bin/keel.exe same sha256 c77ddf43; keel gate guard decision-scaffolding . before (keel-before.exe) vs after: 9078 bytes each, diff exit 0, 151 scanned / 31 warnings / 0 violations byte-identical; KEEL_PERF=2 keel gate guard --no-receipt . three alternating pairs on host 0F3DGVX25193H7: phase guard:decision-scaffolding before 4296 / 7905 / 4208 ms, after 2350 / 2111 / 2863 ms, beside the ledger's 4645-12463 ms; critical path after = acceptance-binds-to-text 3460 or priority-inversion 3839 / 4418 ms
    part decisionScaffoldingIndexesItsEdgesOnceImplementGateR1 : TestResult { :>> id = "78a6933a-15ce-430f-9ecd-10e1fd6209ec"; :>> outcome = VerdictKind::pass; :>> judgedAgainst = "c071d43"; :>> judgedAt = "2026-09-13"; :>> judgedBy = "claudeFable5"; }
    verification decisionScaffoldingIndexesItsEdgesOnceReviewGate : Test { :>> id = "4832c012-9e24-4c99-bdfe-b8757115a715"; :>> title = "Sprint 698 review gate — three passes per D0172"; :>> createdAt = "2026-09-13"; :>> createdBy = "claudeFable5"; :>> method = VerificationMethod::inspect; :>> procedureText = "Three passes (D0172). Correctness: the set holds exactly what the per-candidate test matched - `to X` is the text after the LAST ' to ' of the line trimmed of whitespace and `;`, which equals X iff the trimmed line ends with ' to X' (names carry no space), and the satisfy subject is the text before the FIRST ' by ', which equals X iff the line starts with 'satisfy X by ' - so contains(d) and the old ends_with / starts_with agree on every line; the empirical check is the byte-identical diff over 151 live candidates. Honesty: the grace-versus-lone-violator reading is stated in the sprint's refine, not patched around by editing the DoD (D0307's class); the ten-fire indicator figure is not quoted because it does not exist yet. Scope: no verdict text, no schema, no hook or CI change; the D0469 clause and compound_decisions are untouched; what remains of the guard's 2.1-2.9 s is the corpus read and the other passes, which is a different item if the ledger names it."; }
    // RAN: keel gate validate . -> tracking files validated clean; keel gate check-engine . -> .engine instance files validated clean; keel gate guard --no-receipt . -> ALL PASS, 0 violations, on the tree holding the guards.rs edit and sprint 698 chartered by d0414 (the process-change lock is satisfied on the D0465 path: a co-committed sprint record chartered by a marked Decision the human accepted; before the record existed the guard read FAIL naming keel-cli/src/guards.rs)
    part decisionScaffoldingIndexesItsEdgesOnceReviewGateR1 : TestResult { :>> id = "5fa0eacd-9761-4264-88c9-38ff1fbfe564"; :>> outcome = VerdictKind::proposed; :>> judgedAgainst = "c071d43"; :>> judgedAt = "2026-09-13"; :>> judgedBy = "claudeFable5"; }
    verification decisionScaffoldingIndexesItsEdgesOnceCloseOutGate : Test { :>> id = "30acd4e9-ddfb-4be7-a061-0d4e5e3d1c2d"; :>> title = "Sprint 698 closeOut gate (autonomous, D0049)"; :>> createdAt = "2026-09-13"; :>> createdBy = "claudeFable5"; :>> method = VerificationMethod::inspect; :>> procedureText = "Closes when ten stop fires on the new binary exist and the hookLatencyIndicator's live p90 is read back beside 14125 (keel show indicators), gate validate / check-engine / guard --no-receipt are green over the tree holding the edit and this record, and dcDecisionScaffoldingIndexesItsEdgesOnceDoD carries a pass with the RAN receipt. Not closed at the commit that lands the code."; }
    verification decisionScaffoldingIndexesItsEdgesOnceRetroGate : Test { :>> id = "a797fc59-1cb4-4fb4-8f7d-e2ca596696b2"; :>> title = "Sprint 698 retro gate (autonomous, D0049)"; :>> createdAt = "2026-09-13"; :>> createdBy = "claudeFable5"; :>> method = VerificationMethod::analyze; :>> procedureText = "Recorded at closeOut from the ten-fire read-back; until then no finding and no new item - already tracked: the one open obligation is that read-back, owed to issue520 through its resolver dcDecisionScaffoldingIndexesItsEdgesOnce, and the D0131 avoidable-issue scan is written here when the read exists."; }
}
