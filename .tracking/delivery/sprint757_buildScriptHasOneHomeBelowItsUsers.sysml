// ProjectDeliveryS757 — Sprint 757: The build-provenance stamp lives at build/provenance.rs, a workspace path no crate owns, every crate that bakes KEEL_BUILD_COMMIT names it by build =, and scripts/modgraph.py reads build = as a dependency edge so a crate built from a script a crate above it owns is a layering red (D0479; issue585). EXECUTE. 2 pts.
package ProjectDeliveryS757 {
    private import EngineElement::*;
    private import EngineWork::*;
    private import EngineVerification::*;
    private import EngineRelationships::*;

    #CharteredBy dependency from buildScriptHasOneHomeBelowItsUsersStory to d0479;
    #Delivers dependency from buildScriptHasOneHomeBelowItsUsersStory to dcBuildScriptHasOneHomeBelowItsUsers;

    part buildScriptHasOneHomeBelowItsUsersStory : Story {
        :>> id = "f44d8f73-a517-4ded-b277-dea7c329a1fe";
        :>> title = "Sprint 757: The build-provenance stamp lives at build/provenance.rs, a workspace path no crate owns, every crate that bakes KEEL_BUILD_COMMIT names it by build =, and scripts/modgraph.py reads build = as a dependency edge so a crate built from a script a crate above it owns is a layering red (D0479; issue585) (2 pts)";
        :>> createdAt = "2026-09-20"; :>> createdBy = "claudeFable5"; :>> kind = WorkKind::code; :>> priority = WorkPriority::p0; :>> owner = "claudeFable5"; :>> estimatedPoints = 2;
    }

    action def DeliveryRunS757 {
        action storyBuildScriptHasOneHomeBelowItsUsers;
        verification storyBuildScriptHasOneHomeBelowItsUsersDoD : Test { :>> id = "c46fade1-d300-4a10-ab15-d4722e99ddcf"; :>> method = VerificationMethod::test; :>> procedureText = "DELIVERED BACKLOG ITEM: dcBuildScriptHasOneHomeBelowItsUsers. DONE MEANS: the task's DoD passes as written - keel-cli/build.rs is moved (git mv, history kept) to build/provenance.rs, a directory the root manifest does not list as a member so the owner-of-a-path lookup returns none; keel-cli/Cargo.toml names build = ../build/provenance.rs and the five members that bake the stamp (keel-guards, keel-hooks, keel-process, keel-serve, keel-write - the DoD counted two at 2026-09-17, three more reached up in sprints 736 and 750) name build = ../../build/provenance.rs; the three codemods that carry the manifest line as a template (scripts/extract_hooks.py, extract_process.py, extract_verbs.py add_build_script) land the new home on a re-run; scripts/modgraph.py gains crates(), path_deps(), build_edges(), check_build_edges() and --build-edges, and --check exits 1 on an UPWARD row naming the crate, the script, its owner and the manifest line; --probe runs the D0388 pair on two temp workspaces (positive: members/low built from ../../top/build.rs is one upward row at members/low/Cargo.toml:5; negative: members/low built from ../../build/provenance.rs has owner none and top's own build.rs has owner top) and then --check on the landed tree, and the # ci-probe: --probe header puts that pair in scripts/script_probes.py (ten probes, from nine) - the CI step and the pre-commit hook on staged scripts. Measured at e35fb846+dirty: python scripts/modgraph.py --check exit 0 printing 74 modules, 0 edges, 7 build scripts; --probe 0 failure(s); --build-edges lists six crates built from build/provenance.rs with owner (no crate) and keel-parser from its own build.rs; cargo build --release from the root Finished in 1m 44s recompiling the six stamped crates plus keel-view and keel-issues; keel version prints build commit e35fb846+dirty and git rev-parse --short HEAD prints e35fb846; cargo clippy --release --workspace --all-targets -- -D warnings Finished clean. Known-positive, chosen before the tree was read: the --probe positive fixture (an upward build.rs) is red under check_build_edges. Known-negative: python scripts/modgraph.py --check on the landed tree exits 0."; }
        // RAN: verify ladder passed: validate=pass guard=pass clippy=pass probe=pass touched=pass
        part storyBuildScriptHasOneHomeBelowItsUsersDoDR1 : TestResult { :>> id = "cc28446d-6ac6-4d21-ac33-b2e7a95bdb9c"; :>> outcome = VerdictKind::pass; :>> judgedAgainst = "e35fb846"; :>> judgedAt = "2026-09-20"; :>> judgedBy = "claudeFable5"; }
    }

    verification buildScriptHasOneHomeBelowItsUsersRefineGate : Test { :>> id = "5710c59f-8a71-4897-bca8-0db0d5a7655e"; :>> title = "Sprint 757 refine gate (DoR)"; :>> createdAt = "2026-09-20"; :>> createdBy = "claudeFable5"; :>> method = VerificationMethod::inspect; :>> procedureText = "One backlog item, sized 2: one file move under git, six manifest lines, three template lines in codemods, one new function group in an existing sensor script with its own probe, and the doc-sync of snModGraph, fbModGraph and two undone DoDs that cited the old path. DoR: estimatedPoints 2; charter d0479 (the layering Decision the item sits under, as sprints 740, 742 and 752); DoD authored 2026-09-17 with its D0388 pair named; first ready line of keel show whats-next at e35fb846. Not a process change: modgraph.py is the Sensor snModGraph, no guard, hook or CI yml is edited; the # ci-probe marker is read by the runner CI already carries (D0394, D0496)."; }
    // RAN: keel suite --touched: pass - 496 passed in 215s over [8 binaries]; 0 failed
    part buildScriptHasOneHomeBelowItsUsersRefineGateR1 : TestResult { :>> id = "5c16bc97-45e2-42a8-8cbb-a6ceb555f8e8"; :>> outcome = VerdictKind::proposed; :>> judgedAgainst = "e35fb846"; :>> judgedAt = "2026-09-20"; :>> judgedBy = "claudeFable5"; }
    verification buildScriptHasOneHomeBelowItsUsersStandupGate : Test { :>> id = "6174130d-4cbe-4091-b5e4-22b6aafd2c22"; :>> title = "Sprint 757 standup gate"; :>> createdAt = "2026-09-20"; :>> createdBy = "claudeFable5"; :>> method = VerificationMethod::inspect; :>> procedureText = "Layout chosen: a workspace-level build/ directory rather than members/keel-fs/build.rs. A build.rs on keel-fs would run git on every keel-fs build and cascade a rebuild through every dependent when HEAD moves; a script owned by no crate runs only for the crates that name it. Two consequences checked before the move: build/ is not gitignored (git check-ignore build/provenance.rs exits 1), and keel-suite's touched set: wsgraph::candidates (wsgraph.rs:148-161) makes every member a candidate for a changed CODE path no member owns, and SetKeys::read (touched.rs:328) folds unowned code into every member's key - but contentkey::is_code (contentkey.rs:110) listed no build/ arm, so the moved script would have been neither code nor owned: invisible to the set. Found from the first green ladder's receipt (ran = the eight lib rows the six changed manifests reach, stems=[] changed=[]) and read back in source; fixed in this sprint with one predicate arm and its test line before the ladder ran again. The upward definition: a script's owner is neither the crate itself nor in its transitive PATH-dependency closure ([dependencies] plus [build-dependencies]); registry deps are outside the closure by construction."; }
    // RAN: keel suite --touched: pass - 496 passed in 215s over [8 binaries]; 0 failed
    part buildScriptHasOneHomeBelowItsUsersStandupGateR1 : TestResult { :>> id = "9a923ebe-b2aa-4fdc-a9ab-f7dfaa9948d8"; :>> outcome = VerdictKind::proposed; :>> judgedAgainst = "e35fb846"; :>> judgedAt = "2026-09-20"; :>> judgedBy = "claudeFable5"; }
    verification buildScriptHasOneHomeBelowItsUsersImplementGate : Test { :>> id = "b6162910-1df6-4497-9afd-dfc94bbc08a6"; :>> title = "Sprint 757 implement gate"; :>> createdAt = "2026-09-20"; :>> createdBy = "claudeFable5"; :>> method = VerificationMethod::test; :>> procedureText = "git mv keel-cli/build.rs build/provenance.rs (65 lines before and after; the in-file comment at 45-49 names its new home); keel-cli/Cargo.toml:15 build = ../build/provenance.rs; members/{keel-guards,keel-hooks,keel-process,keel-serve,keel-write}/Cargo.toml build = ../../build/provenance.rs with the sprint-733/736/750 comments rewritten to name one home; scripts/extract_hooks.py:116, extract_process.py:104 template line and extract_verbs.py add_build_script relpath to REPO/build/provenance.rs; scripts/modgraph.py: header # ci-probe: --probe, imports tempfile and tomllib, _rel, crates (from [workspace].members), path_deps, build_edges (rows crate, script, owner or None, manifest line, upward), check_build_edges (FORBIDDEN build script: X -> Y (script) - Y is not a dependency of X), _fixture, probe, and --check reporting forbidden edges and upward scripts in one verdict line. Measured: modgraph --check exit 0 (74 modules, 0 edges, 7 build scripts); --probe 0 failures; script_probes.py 10 passed; cargo build --release Finished 1m 44s; keel version e35fb846+dirty equals git rev-parse --short HEAD e35fb846; clippy -D warnings clean; keel gate validate 874 clean. members/keel-suite/src/contentkey.rs:116 is_code gains an arm for paths under build/ with the doc comment and the test code_is_what_the_binaries_are_built_from_or_run_against asserting build/provenance.rs is code; wsgraph.rs:145 names build/ among the unowned code paths; the test passes (1 passed, 63 filtered out) and clippy -D warnings is clean after the change."; }
    // RAN: keel suite --touched: pass - 496 passed in 215s over [8 binaries]; 0 failed
    part buildScriptHasOneHomeBelowItsUsersImplementGateR1 : TestResult { :>> id = "d631695b-7666-485a-9c08-65b5b2161e0a"; :>> outcome = VerdictKind::pass; :>> judgedAgainst = "e35fb846"; :>> judgedAt = "2026-09-20"; :>> judgedBy = "claudeFable5"; }
    verification buildScriptHasOneHomeBelowItsUsersReviewGate : Test { :>> id = "8ba5006f-8a33-4dd1-a610-d2420cb29d61"; :>> title = "Sprint 757 review gate — three passes per D0172"; :>> createdAt = "2026-09-20"; :>> createdBy = "claudeFable5"; :>> method = VerificationMethod::inspect; :>> procedureText = "Three passes per D0172. Code read back: crates() reads the root manifest's [workspace].members only, as module_home does, so a nested workspace is unseen (the same failure mode the instrument record names); build = true and an absent key resolve to the crate's own build.rs, which is never upward; the owner lookup is longest-prefix over member directories, so a script under a member's subdirectory is owned by that member. Before the move, --build-edges on the unmoved tree listed five UPWARD rows (guards, hooks, process, serve, write -> keel-cli) and --check went red naming each with its manifest line - the DoD's two had become five, which the sensor now counts rather than a retro. Doc-sync: snModGraph.measures and fbModGraph.title extend to build-script edges; the KNOWN FAILURE MODES and PUBLISHED TO comments name the owner rule, the path-only closure and the ci-probe step; dcBuildScriptDoesNotWatchTheGitIndex's DoD (issue541) now cites build/provenance.rs:53-58 and provenance.rs:37 for the git status call, and dcBuildStampsAFixedWidthCommit's DoD (issue643) cites provenance.rs:32 - both undone items I own. Historical text in Decisions, sprint records and intake keeps keel-cli/build.rs as it was when written."; }
    // RAN: keel suite --touched: pass - 496 passed in 215s over [8 binaries]; 0 failed
    part buildScriptHasOneHomeBelowItsUsersReviewGateR1 : TestResult { :>> id = "23f3eb98-5152-40d4-b753-f68706782b83"; :>> outcome = VerdictKind::proposed; :>> judgedAgainst = "e35fb846"; :>> judgedAt = "2026-09-20"; :>> judgedBy = "claudeFable5"; }
    verification buildScriptHasOneHomeBelowItsUsersCloseOutGate : Test { :>> id = "9284eca7-d49f-4257-b275-785a5a43324c"; :>> title = "Sprint 757 closeOut gate (autonomous, D0049)"; :>> createdAt = "2026-09-20"; :>> createdBy = "claudeFable5"; :>> method = VerificationMethod::inspect; :>> procedureText = "The task's DoD result and the six gate results are recorded from the verifier's rendered receipt, itself passed by check_receipt.py before the recorder was dispatched; issue585 resolves when the DoD passes. Doc-sync rode the change. The touched set for this commit: the six changed manifests seed their owners closed over dependents, and the changed members/keel-suite source seeds keel-suite and its dependents; build/provenance.rs seeds every member once the is_code arm is in the binary that computes the set. The ladder runs suite --touched on it. Not a CR commit: no Decision is authored, the charter is D0479 as landed."; }
    // RAN: keel suite --touched: pass - 496 passed in 215s over [8 binaries]; 0 failed
    part buildScriptHasOneHomeBelowItsUsersCloseOutGateR1 : TestResult { :>> id = "04a56b95-0304-49ea-99d3-d44e81470383"; :>> outcome = VerdictKind::proposed; :>> judgedAgainst = "e35fb846"; :>> judgedAt = "2026-09-20"; :>> judgedBy = "claudeFable5"; }
    verification buildScriptHasOneHomeBelowItsUsersRetroGate : Test { :>> id = "8fb704f8-48ac-4238-8775-88e6620e126c"; :>> title = "Sprint 757 retro gate (autonomous, D0049)"; :>> createdAt = "2026-09-20"; :>> createdBy = "claudeFable5"; :>> method = VerificationMethod::analyze; :>> procedureText = "Four findings, avoidable issues scanned (issue585, issue541, issue643). Finding one: the DoD said two members reached up; five did by the time the item was worked, because sprints 736 and 750 copied the build = line from the members before them and nothing counted the reach. The control is this sprint's: modgraph --check is red on the next one, in CI through the probe marker. No new item. Finding two: keel-cli/build.rs was code owned by keel-cli, so a change to it keyed and seeded keel-cli's rows only, never the members baking the stamp; the move would have made it worse - build/ was not a contentkey::is_code path, so the script would have seeded nothing and keyed nothing. The standup text asserted the opposite from touched.rs:328 alone, without reading is_code; the first green ladder's receipt (eight lib rows from the manifests, stems=[] changed=[]) contradicted it and the source confirmed the gap. Fixed in the sprint (contentkey.rs:116 and its test). The class - a claim about a computed set made from one function without its predicate - is D0151's: state the check, or label the suspicion; no automated control fits a sentence in a gate's prose, so no item. Finding three: two undone DoDs cited the old path at fixed lines and were stale before this sprint started (issue541's cited build.rs:47-51 for a block that sits at 53-58 in a file of the same length - the lines were wrong when written, not moved). A line citation in a DoD is a fact about a file at a commit, and the model records no check on it; dcFactsAboutARangeReadTheRange (next on the frontier) is the same class for facts.py, so the finding attaches there rather than opening a second item. Finding four: the # ci-probe header on a Sensor script puts the D0479 layering in CI before dcWorkspaceLayeringIsGuarded lands it as a guard - the two overlap, and the item's DoD should say whether the guard replaces the probe rung or joins it; noted on the retro, resolved when that item is refined."; }
    // RAN: keel suite --touched: pass - 496 passed in 215s over [8 binaries]; 0 failed
    part buildScriptHasOneHomeBelowItsUsersRetroGateR1 : TestResult { :>> id = "4d6b35f0-12ce-48c1-bbfd-c2a6661c65ad"; :>> outcome = VerdictKind::proposed; :>> judgedAgainst = "e35fb846"; :>> judgedAt = "2026-09-20"; :>> judgedBy = "claudeFable5"; }
}
