// ProjectDeliveryS710 — Sprint 710: Resolve issue544 through dcCeremonyOrderCountsAFailedGateAsRecorded: the ceremony guard's order reader counts pass and proposed only, so sprint 708's honestly FAILED closeOut (CI red on issue542) read as unrecorded and its Retro as out of turn - keel gate guard went red on the one record that told the truth. D0437 already decided the clause - the guard checks sequence, not done-ness - and stopped at proposed because issue470 was the case in hand; this completes it for every written verdict. Chartered by D0437 (process-change, accepted). Same commit as sprint 709 because sprint-closure would otherwise hold 709 unstamped the moment 710 exists, and because 709 cannot commit while the tree is red on this. 1 pt.. EXECUTE. 1 pts.
package ProjectDeliveryS710 {
    private import EngineElement::*;
    private import EngineWork::*;
    private import EngineVerification::*;
    private import EngineRelationships::*;

    #CharteredBy dependency from ceremonyOrderCountsAFailedGateAsRecordedStory to d0437;

    part ceremonyOrderCountsAFailedGateAsRecordedStory : Story {
        :>> id = "c182a203-94e9-45c1-8c8d-7de5c92d3c1c";
        :>> title = "Sprint 710: Resolve issue544 through dcCeremonyOrderCountsAFailedGateAsRecorded: the ceremony guard's order reader counts pass and proposed only, so sprint 708's honestly FAILED closeOut (CI red on issue542) read as unrecorded and its Retro as out of turn - keel gate guard went red on the one record that told the truth. D0437 already decided the clause - the guard checks sequence, not done-ness - and stopped at proposed because issue470 was the case in hand; this completes it for every written verdict. Chartered by D0437 (process-change, accepted). Same commit as sprint 709 because sprint-closure would otherwise hold 709 unstamped the moment 710 exists, and because 709 cannot commit while the tree is red on this. 1 pt. (1 pts)";
        :>> createdAt = "2026-09-14"; :>> createdBy = "claudeFable5"; :>> kind = WorkKind::code; :>> priority = WorkPriority::p0; :>> owner = "claudeFable5"; :>> estimatedPoints = 1;
    }

    action def DeliveryRunS710 {
        action storyCeremonyOrderCountsAFailedGateAsRecorded;
        verification storyCeremonyOrderCountsAFailedGateAsRecordedDoD : Test { :>> id = "5adecc8d-6dc3-4e67-8c39-0aac26041b53"; :>> method = VerificationMethod::test; :>> procedureText = "Resolves issue544 (D0437's clause, completed): the ceremony guard's ORDER reader counts a gate as recorded when ANY TestResult is written for it - pass, proposed, fail, inconclusive or error - because sequence asks whether the record was written in its turn, not what it says; done-ness stays gate_passed's (orient, advance, the suspect algebra) and the flow view's retro reader (which asks where a sprint FINISHED, and refuses fail on purpose) is unchanged. Known-positive, chosen before the tree is read: a CloseOut recorded fail followed by a Retro recorded pass raises no ordering violation, while gate_passed still reads that CloseOut as not passed; known-negative: a CloseOut with no result at all followed by a Retro is still an ordering violation, and the real tree with sprint708's failed closeOut passes guard ceremony. The guard's doc comment and guards.md row say fail counts for order."; }
        // RAN: KNOWN-POSITIVE (unit, chosen before the tree was read): ceremony_order_counts_a_failed_gate_as_recorded - CloseOut fail then Retro pass -> gates_recorded 2, ordering_violations empty, gate_passed(CloseOut) false, gate_recorded(CloseOut) false; KNOWN-NEGATIVE: CloseOut with no result then Retro pass -> ordering_violations [(Retro, CloseOut)]; cargo test --release --lib -- ceremony custom_harness_routed retro_reader -> 10 passed 0 failed including view::flow::tests::the_retro_reader_accepts_pass_and_proposed_and_refuses_fail; REAL TREE: keel gate guard --no-receipt . -> [guard:ceremony] PASS - 711 scanned, 0 violation(s) with sprint708's closeOut fail 6f640d03 and retro pass in the tree, where the binary at 593147c reported FAIL Retro recorded but CloseOut (earlier) unrecorded; grep gate_recorded keel-cli/src -> callers guards.rs (now gate_has_result) and flow.rs:116 (unchanged); cargo clippy --release --all-targets -- -D warnings exit 0; guards.md ceremony row and the gates_recorded doc comment name fail as counting for order
        part storyCeremonyOrderCountsAFailedGateAsRecordedDoDR1 : TestResult { :>> id = "4e5b52a3-e8af-4b91-a9c6-e1a3d36c8d7a"; :>> outcome = VerdictKind::pass; :>> judgedAgainst = "593147c"; :>> judgedAt = "2026-09-14"; :>> judgedBy = "claudeFable5"; }
    }

    verification ceremonyOrderCountsAFailedGateAsRecordedRefineGate : Test { :>> id = "1c74ed07-0390-4b79-8dab-a2359943b42d"; :>> title = "Sprint 710 refine gate (DoR)"; :>> createdAt = "2026-09-14"; :>> createdBy = "claudeFable5"; :>> method = VerificationMethod::inspect; :>> procedureText = "Chartered by D0437, which carries the process-change marker and is accepted; a guard reader is an enforcement change, authorised by this co-committed record (D0465). One point: one new reader in orient.rs, one call site in guards.rs, one unit pair, two doc lines. DoR: dcCeremonyOrderCountsAFailedGateAsRecorded ranks second on keel show whats-next, directly after sprint 709's item; the pair is the DoD's own; the real tree is the known-negative because sprint708's failed closeOut is already in it."; }
    // RAN: D0437 carries the process-change marker and is accepted (no d0437 row on keel show authority-queue); this record co-committed with the guards.rs and orient.rs edit (D0465); 1 point; keel show whats-next line 2 is dcCeremonyOrderCountsAFailedGateAsRecorded directly after sprint 709's item; the DoD carries its own D0388 pair; the real tree holds sprint708's closeOut fail (6f640d03-285b-43be-a39a-4d63e1135c76 at 593147c) and retro pass and is the known-negative
    part ceremonyOrderCountsAFailedGateAsRecordedRefineGateR1 : TestResult { :>> id = "c2b91137-d48e-42cb-8f56-c1486b27f360"; :>> outcome = VerdictKind::proposed; :>> judgedAgainst = "593147c"; :>> judgedAt = "2026-09-14"; :>> judgedBy = "claudeFable5"; }
    verification ceremonyOrderCountsAFailedGateAsRecordedStandupGate : Test { :>> id = "55c1786a-a43f-43d9-a5c7-9c7c6a1d0d8f"; :>> title = "Sprint 710 standup gate"; :>> createdAt = "2026-09-14"; :>> createdBy = "claudeFable5"; :>> method = VerificationMethod::inspect; :>> procedureText = "Order: this record first (D0465); orient::gate_has_result counting the five VerdictKind members, gates_recorded in guards.rs reads it, gate_recorded and gate_passed untouched; the unit pair beside ceremony_order_reads_recorded_gates_not_passed_ones; the guards.md ceremony row; cargo build --release, copy to keel-serve.exe, cargo test --release --lib -- ceremony, clippy -D warnings; keel gate guard --no-receipt with ceremony PASS over the tree that holds sprint708's failed closeOut; gate and DoD results; then sprint 709's commit carries both records."; }
    // RAN: Order followed as written: record sprint 710 ... --charter d0437 --points 1 --fill fill710.md; orient::gate_has_result added beside gate_recorded listing the five VerdictKind members; guards.rs gates_recorded reads gate_has_result, doc comment names issue544; gate_recorded and gate_passed untouched, flow.rs:116 retro_recorded untouched; unit test ceremony_order_counts_a_failed_gate_as_recorded appended after ceremony_order_reads_recorded_gates_not_passed_ones; guards.md ceremony row rewritten; cargo build --release 2m41s, copied to keel-serve.exe
    part ceremonyOrderCountsAFailedGateAsRecordedStandupGateR1 : TestResult { :>> id = "91bfe32f-d58c-4684-bc2f-e99dc7aa057f"; :>> outcome = VerdictKind::proposed; :>> judgedAgainst = "593147c"; :>> judgedAt = "2026-09-14"; :>> judgedBy = "claudeFable5"; }
    verification ceremonyOrderCountsAFailedGateAsRecordedImplementGate : Test { :>> id = "8e13a5c2-37fb-4065-87d7-e43fd1949f32"; :>> title = "Sprint 710 implement gate"; :>> createdAt = "2026-09-14"; :>> createdBy = "claudeFable5"; :>> method = VerificationMethod::test; :>> procedureText = "The implement gate holds when: cargo test --release --lib -- ceremony passes with the new pair among them; cargo clippy --release --all-targets -- -D warnings exits 0; keel gate guard --no-receipt . reports ceremony PASS with sprint708's closeOut fail and retro pass both in the tree; flow's the_retro_reader_accepts_pass_and_proposed_and_refuses_fail still passes. Its evidence quotes those commands' own lines."; }
    // RAN: cargo test --release --lib -- ceremony custom_harness_routed retro_reader -> test result: ok. 10 passed; 0 failed, among them guards::tests::ceremony_order_counts_a_failed_gate_as_recorded ... ok and view::flow::tests::the_retro_reader_accepts_pass_and_proposed_and_refuses_fail ... ok; cargo clippy --release --all-targets -- -D warnings -> Finished, exit=0 (three missing-backticks doc lints on the new test's comment fixed first); keel gate guard --no-receipt . -> [guard:ceremony] PASS - 711 scanned, 0 warning(s) + 1 counted-history line(s), 0 violation(s) over the tree holding sprint708's closeOut fail and retro pass; before the fix the same tree read [guard:ceremony] FAIL sprint708_verifyLadderStopsAtTheFirstRed: Retro recorded but CloseOut (earlier) unrecorded
    part ceremonyOrderCountsAFailedGateAsRecordedImplementGateR1 : TestResult { :>> id = "1d92944e-6bff-470c-b82e-049a274fcb8c"; :>> outcome = VerdictKind::pass; :>> judgedAgainst = "593147c"; :>> judgedAt = "2026-09-14"; :>> judgedBy = "claudeFable5"; }
    verification ceremonyOrderCountsAFailedGateAsRecordedReviewGate : Test { :>> id = "2063e472-0f1d-455c-af65-f791b90978f7"; :>> title = "Sprint 710 review gate — three passes per D0172"; :>> createdAt = "2026-09-14"; :>> createdBy = "claudeFable5"; :>> method = VerificationMethod::inspect; :>> procedureText = "Three passes (D0172). Correctness: the new reader lists the enum's five members rather than negating pass, so a sixth verdict added later is a compile-visible edit here, not a silent inclusion; ordering_violations itself is untouched. Honesty: a failed gate now counts for order only - gate_passed, advance and the suspect algebra still say not passed, and the flow view still dates a sprint's finish by a pass or proposed retro. Scope: no other caller of gate_recorded changes; flow.rs:116 keeps it and its fail-refusing test stays green."; }
    // RAN: Correctness: gate_has_result lists pass, proposed, fail, inconclusive, error - the enum's five members at element.sysml:27 - rather than negating pass; ordering_violations is untouched; the new test asserts gate_passed and gate_recorded both still refuse the failed CloseOut. Honesty: order-only - advance, orient, the suspect algebra and the flow view's sprint-finish reader read exactly as before, and flow's fail-refusing test is in the 10 that passed. Scope: one caller changed (guards.rs gates_recorded); grep gate_recorded shows flow.rs:116 as the only other caller and it is unchanged
    part ceremonyOrderCountsAFailedGateAsRecordedReviewGateR1 : TestResult { :>> id = "18bce77a-8af0-421f-8bf4-ee77d0549853"; :>> outcome = VerdictKind::proposed; :>> judgedAgainst = "593147c"; :>> judgedAt = "2026-09-14"; :>> judgedBy = "claudeFable5"; }
    verification ceremonyOrderCountsAFailedGateAsRecordedCloseOutGate : Test { :>> id = "33b9da39-8b3b-46cd-97bd-89fe9f26abcd"; :>> title = "Sprint 710 closeOut gate (autonomous, D0049)"; :>> createdAt = "2026-09-14"; :>> createdBy = "claudeFable5"; :>> method = VerificationMethod::inspect; :>> procedureText = "Closes in sprint 709's CR: commit: keel-land runs the touched set from it; gate validate / check-engine / guard --no-receipt green over the tree with ceremony PASS; dcCeremonyOrderCountsAFailedGateAsRecordedDoD carries a pass; git status -sb shows main level with origin after the land."; }
    // RAN: FAIL at 6281526: keel-land ran the touched set from the CR commit (receipt .keel/metrics/touched-receipt.toml code_key caf8686da330eaaf, tree_key dad205bfa41758a6; log .keel/metrics/touched-1789384685.log:197) - 820 passed, 1 FAILED in 889 s: guards::guard_catalogue_tests::every_guard_has_a_constraint_def_identity, guards with no constraint-def identity (D0195 clause 1): custom-harness-routed. The land did not push; git status -sb reads main...origin/main [ahead 1], not level. The failed test is sprint 709's guard, not this sprint's reader, but the closeOut clause binds to the shared commit and is not met. Correction in the tree: constraint def customHarnessRouted added to .engine/rules/guard-constraints.sysml (cargo test --release --lib -- guard_catalogue_tests: 2 passed). Finding tracked as issue545 with resolver dcGuardIdentityIsCheckedAtTheGate.
    part ceremonyOrderCountsAFailedGateAsRecordedCloseOutGateR1 : TestResult { :>> id = "bad28a19-77d0-4792-bf49-587dce0f0a33"; :>> outcome = VerdictKind::fail; :>> judgedAgainst = "6281526"; :>> judgedAt = "2026-09-14"; :>> judgedBy = "claudeFable5"; }
    // RAN: PASS at 838f75f (R1 was the honest FAIL at 6281526, whose land failed sprint 709's identity test). The clause at the commit that landed both sprints: keel-land ran the touched set from 838f75f (receipt outcome pass, runner cargo-nextest 0.9.144; binaries green at the same content skipped under D0474, the rest rerun) after `keel verify .` climbed validate pass, guard ALL PASS (ceremony PASS across every sprint record, sprint 708's failed closeOut now recorded in sequence), clippy pass, touched 821 passed in 895 s; dcCeremonyOrderCountsAFailedGateAsRecordedDoD carries its pass (b450fe65, 593147c); `git status -sb` -> ## main...origin/main, level; CI for 838f75f read after completion: conclusion success.
    part ceremonyOrderCountsAFailedGateAsRecordedCloseOutGateR2 : TestResult { :>> id = "2a1e06f9-45e2-4e36-996d-03fe05825960"; :>> outcome = VerdictKind::proposed; :>> judgedAgainst = "838f75f"; :>> judgedAt = "2026-09-14"; :>> judgedBy = "claudeFable5"; }
    verification ceremonyOrderCountsAFailedGateAsRecordedRetroGate : Test { :>> id = "b79c673b-cc3b-44c1-aab2-1d706600f956"; :>> title = "Sprint 710 retro gate (autonomous, D0049)"; :>> createdAt = "2026-09-14"; :>> createdBy = "claudeFable5"; :>> method = VerificationMethod::analyze; :>> procedureText = "Avoidable issues scanned; findings are tracked items, not prose. The class is a reader widened to the case in hand and no further (D0437 added proposed for issue470 and left fail, inconclusive and error): where a predicate names enum members, the retro asks whether it names them all or says why not, and each such reader found becomes an Issue with a resolver. No new item from this scan - the one other reader of this shape, the flow view's, refuses fail on purpose and tests that it does."; }
    // RAN: Avoidable issues scanned at 6281526. Class named in the clause (a predicate over enum members that names some and not all): readers of VerdictKind grepped in keel-cli/src - orient::gate_passed (pass, done-ness, correct), orient::gate_recorded (pass|proposed, the flow view's finish reader, refuses fail on purpose and flow.rs:630 tests it), orient::gate_has_result (all five, this sprint). No new item of that class. One finding of a different class from this sprint's own land: a guard's constraint-def identity (D0195 clause 1, .engine/rules/guard-constraints.sysml) is checked by a unit test at land only, so custom-harness-routed passed gate validate, check-engine, guard --no-receipt and the fast tier with three of its four registration homes and failed keel-land 889 s later - tracked as issue545 (Medium), resolver dcGuardIdentityIsCheckedAtTheGate added to the backlog ranked after dcEvidenceGoesThroughAFile. Second finding: keel verify (D0476) was not climbed before the commit; the ladder would have run the lib tests and caught it at minute one - no new item, the ladder exists and the miss is the operator's, recorded here so the next retro can count a recurrence.
    part ceremonyOrderCountsAFailedGateAsRecordedRetroGateR1 : TestResult { :>> id = "7f514b90-ad07-414a-a022-1c40d5db4894"; :>> outcome = VerdictKind::proposed; :>> judgedAgainst = "6281526"; :>> judgedAt = "2026-09-14"; :>> judgedBy = "claudeFable5"; }
}
