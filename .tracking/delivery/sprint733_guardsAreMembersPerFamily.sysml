// ProjectDeliveryS733 — Sprint 733: the fourth D0479 extraction - dcGuardsAreMembersPerFamily. guards.rs (9,256 lines, 75 enforced guards and four runnable-only) becomes member keel-guards: one module per guard family with each guard's dispatch arm, code and tests beside each other, the shared scanners in the crate root, and receipt, contentkey, hardening and plan_cover with it; the family union is held equal to GUARD_NAMES (D0503) so a name in one home is in all. Ten upward reaches descend first so the boundary can be drawn without a cycle: priority to keel-view; onboard, the supersede scan, the manifest readers (custom harness tests, self-build) and the consent-marker classifier to keel-model; eol to keel-git; claude_surface and the pre-commit hook text to keel-write; the engine-resync and portable-tool predicates to keel-schema::embedded. keel-cli re-exports every module at its old path and the CLI surface is byte-identical. EXECUTE. 8 pts.
package ProjectDeliveryS733 {
    private import EngineElement::*;
    private import EngineWork::*;
    private import EngineVerification::*;
    private import EngineRelationships::*;

    #CharteredBy dependency from guardsAreMembersPerFamilyStory to d0479;

    part guardsAreMembersPerFamilyStory : Story {
        :>> id = "345fb7fc-c347-4729-a245-96e09df36354";
        :>> title = "Sprint 733: the fourth D0479 extraction - dcGuardsAreMembersPerFamily. guards.rs (9,256 lines, 75 enforced guards and four runnable-only) becomes member keel-guards: one module per guard family with each guard's dispatch arm, code and tests beside each other, the shared scanners in the crate root, and receipt, contentkey, hardening and plan_cover with it; the family union is held equal to GUARD_NAMES (D0503) so a name in one home is in all. Ten upward reaches descend first so the boundary can be drawn without a cycle: priority to keel-view; onboard, the supersede scan, the manifest readers (custom harness tests, self-build) and the consent-marker classifier to keel-model; eol to keel-git; claude_surface and the pre-commit hook text to keel-write; the engine-resync and portable-tool predicates to keel-schema::embedded. keel-cli re-exports every module at its old path and the CLI surface is byte-identical (8 pts)";
        :>> createdAt = "2026-09-17"; :>> createdBy = "claudeFable5"; :>> kind = WorkKind::code; :>> priority = WorkPriority::p0; :>> owner = "claudeFable5"; :>> estimatedPoints = 8;
    }

    action def DeliveryRunS733 {
        action storyGuardsAreMembersPerFamily;
        verification storyGuardsAreMembersPerFamilyDoD : Test { :>> id = "60150f94-b761-4f72-99ec-1bb6196a7948"; :>> method = VerificationMethod::test; :>> procedureText = "DELIVERED BACKLOG ITEMS: dcGuardsAreMembersPerFamily. DONE MEANS: members/keel-guards exists with src/lib.rs (the runner, the report type, the lock predicates, the shared scanners) and one file per guard family under src/, plus receipt.rs, contentkey.rs, hardening.rs and plan_cover.rs; its Cargo.toml names keel-view, keel-write, keel-model and the leaves and no crate above them, and python scripts/modgraph.py --check holds; keel-cli/src/lib.rs re-exports guards, receipt, contentkey, hardening, plan_cover, priority, onboard, eol, claude_surface and precommit_hook at their old paths so no caller outside the members changed except imports; GUARD_SOURCE_FILES names every guard-defining file of the member and the coverage test scans every workspace member's src, not one crate's; a test holds the union of the family dispatch tables equal to GUARD_NAMES in order, so a guard in one home is in all (issue545's identity check keeps holding); guards.md's catalogue is regenerated and diff-clean. Known-positive, chosen before the tree is read: cargo build --verbose after an edit to one family file reports keel-guards and keel-cli compiled and every other member Fresh; keel gate guard --no-receipt . reports the same 75 names in the same order as at the pre-move sha. Known-negative: every guard's probe pair (D0388) passes unchanged in the full set; keel --help is byte-identical to the pre-move render; keel version's guards line is unchanged at 75; no crate:: reference in keel-guards names a module outside it or the members it depends on (the release build under deny(warnings) plus modgraph)."; }
        // RAN: TOUCHED RECEIPT: outcome=pass passed=904 failed=0 Summary [ 43.510s] 496 tests run: 496 passed, 0 skipped
        part storyGuardsAreMembersPerFamilyDoDR1 : TestResult { :>> id = "74695efb-f30b-41a9-a7b9-d4b8b36acbcd"; :>> outcome = VerdictKind::pass; :>> judgedAgainst = "f8d3d8d"; :>> judgedAt = "2026-09-17"; :>> judgedBy = "claudeFable5"; }
    }

    verification guardsAreMembersPerFamilyRefineGate : Test { :>> id = "dc0a68d8-641a-4bb7-8600-63b6ba75805e"; :>> title = "Sprint 733 refine gate (DoR)"; :>> createdAt = "2026-09-17"; :>> createdBy = "claudeFable5"; :>> method = VerificationMethod::inspect; :>> procedureText = "DoR: dcGuardsAreMembersPerFamily is the first line of keel show whats-next at f8d3d8d; chartered by D0479 (accepted) through its #CharteredBy edge (backlog.sysml). Sized 8 - one new member assembled from a 9,256-line file split into family modules by a committed script, ten descents (priority, onboard, supersede scan, custom_harness_tests, is_self_build, marker classifier, eol, claude_surface with precommit_hook, resync_text, is_portable_engine_tool), the four modules that ride with it (receipt, contentkey, hardening, plan_cover), the widened lock and its coverage test, the re-export layer and the Python anchors. Over the five-point preference: the split cannot land half-done because the lock's coverage test names every guard-defining file, and D0479's own text asks one extraction per sprint with its cycles broken first - the hardening/guards cycle is broken by hardening riding inside the member, the other reaches by descent, both in this sprint as sprint 732 carried its three. Blocking dependencies: none - GUARD_NAMES already sits in keel-schema (D0503, sprint 732), so the member reads the list from below and the family union is checked against it rather than assembling it; the DoD's word assembled is met as an equality test, and the retro records the reading."; }
    // RAN: LADDER: keel verify . --probe-from pair733.txt -> outcome=pass stopped_at=none validate=pass guard=pass clippy=pass probe=pass touched=pass
    part guardsAreMembersPerFamilyRefineGateR1 : TestResult { :>> id = "5b9e4112-e77c-4e64-b0ed-27e96c2d81c1"; :>> outcome = VerdictKind::proposed; :>> judgedAgainst = "f8d3d8d"; :>> judgedAt = "2026-09-17"; :>> judgedBy = "claudeFable5"; }
    verification guardsAreMembersPerFamilyStandupGate : Test { :>> id = "738b978a-2ca1-47af-a435-c81a02c5bcfd"; :>> title = "Sprint 733 standup gate"; :>> createdAt = "2026-09-17"; :>> createdBy = "claudeFable5"; :>> method = VerificationMethod::inspect; :>> procedureText = "Owner claudeFable5. Blocker: none - brief 39 landed in f8d3d8d, no ladder or land is running. Order: (1) the ten descents, each a git mv or a function move with a re-export at the old path, cargo build --release green after each group. (2) scripts/split_guards.py: the family table (guard function to family module), moves each guard's function, its single-use helpers and its test module into members/keel-guards/src/<family>.rs, leaves shared scanners in lib.rs, rewrites crate:: paths per the module map, and prints the reconciliation (functions before == functions after, tests before == after). (3) the family dispatch tables and the union test against GUARD_NAMES; GUARD_SOURCE_FILES gains the member's files and the coverage test scans every member; the marked Decision for the locked edit is recorded and held. (4) keel-cli lib.rs re-exports; cargo build --release, clippy all targets, modgraph, keel --help cmp, keel version, the Fresh probe. (5) Python anchors through module_home; guards.md regenerated; code-registry paths. (6) the retro filled BEFORE the verifier is dispatched; then verify with the D0500 pair file, recorder --owed 8, land, CI conclusion."; }
    // RAN: LADDER: keel verify . --probe-from pair733.txt -> outcome=pass stopped_at=none validate=pass guard=pass clippy=pass probe=pass touched=pass
    part guardsAreMembersPerFamilyStandupGateR1 : TestResult { :>> id = "3eb31481-b174-4348-ab45-4f0f012cf901"; :>> outcome = VerdictKind::proposed; :>> judgedAgainst = "f8d3d8d"; :>> judgedAt = "2026-09-17"; :>> judgedBy = "claudeFable5"; }
    verification guardsAreMembersPerFamilyImplementGate : Test { :>> id = "7a5532e4-f0bd-49e9-9f35-ce891dc5457e"; :>> title = "Sprint 733 implement gate"; :>> createdAt = "2026-09-17"; :>> createdBy = "claudeFable5"; :>> method = VerificationMethod::test; :>> procedureText = "The implement gate is the DoD's own probes plus the ladder: cargo build --release from the workspace root; cargo build --verbose Fresh read after touching one family file (keel-guards and keel-cli compile, every other member Fresh); keel gate guard --no-receipt . names 75 in the pre-move order; keel --help cmp against the pre-move render at f8d3d8d; keel version guards line unchanged; python scripts/modgraph.py --check exit 0; python scripts/module_home.py --probe exit 0; cargo clippy --release --all-targets -- -D warnings clean; keel verify . --probe-from pair733.txt (validate, guard, clippy, the pair, suite --touched) green."; }
    // RAN: LADDER: keel verify . --probe-from pair733.txt -> outcome=pass stopped_at=none validate=pass guard=pass clippy=pass probe=pass touched=pass
    part guardsAreMembersPerFamilyImplementGateR1 : TestResult { :>> id = "624c3ee3-5108-4229-b22d-bf6730c375f6"; :>> outcome = VerdictKind::pass; :>> judgedAgainst = "f8d3d8d"; :>> judgedAt = "2026-09-17"; :>> judgedBy = "claudeFable5"; }
    verification guardsAreMembersPerFamilyReviewGate : Test { :>> id = "7a3151f7-fa29-4cfd-ae99-617cf7c59e86"; :>> title = "Sprint 733 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every pub item keel-cli used is reachable at its old path (the release build and all-targets clippy are the proof); the split script's reconciliation balances (every function and test module of guards.rs is in exactly one file of the member). Honesty: the lock follows the code - GUARD_SOURCE_FILES names every family file and the coverage test scans every member, so a guard file cannot appear outside the lock in any crate; the marked Decision is held for the human, not auto-accepted. Scope: only what the guards own moved, plus the descents they needed; suite, touched, verify, hook_binary stay in keel-cli for dcSuiteIsAMember."; }
    // RAN: LADDER: keel verify . --probe-from pair733.txt -> outcome=pass stopped_at=none validate=pass guard=pass clippy=pass probe=pass touched=pass
    part guardsAreMembersPerFamilyReviewGateR1 : TestResult { :>> id = "e9ec82be-2912-4751-8284-4d5d20df9e19"; :>> outcome = VerdictKind::proposed; :>> judgedAgainst = "f8d3d8d"; :>> judgedAt = "2026-09-17"; :>> judgedBy = "claudeFable5"; }
    verification guardsAreMembersPerFamilyCloseOutGate : Test { :>> id = "83dac9aa-ba0d-4b29-a2b6-ec4e4e12c5e9"; :>> title = "Sprint 733 closeOut gate (autonomous, D0049)"; :>> createdAt = "2026-09-17"; :>> createdBy = "claudeFable5"; :>> method = VerificationMethod::inspect; :>> procedureText = "Landed when the verifier's receipt reads DISCREPANCIES: NONE and its probe rung row names pair733.txt, the recorder's report passes check_report.py --owed 8, git status -sb is clean after keel land and gh run list names the landing commit with conclusion success. The DoD result is recorded against dcGuardsAreMembersPerFamilyDoD at that sha; the marked Decision stays proposed until the human's word."; }
    // RAN: LADDER: keel verify . --probe-from pair733.txt -> outcome=pass stopped_at=none validate=pass guard=pass clippy=pass probe=pass touched=pass
    part guardsAreMembersPerFamilyCloseOutGateR1 : TestResult { :>> id = "7fc2cd67-a517-4279-9178-a10d0729de68"; :>> outcome = VerdictKind::proposed; :>> judgedAgainst = "f8d3d8d"; :>> judgedAt = "2026-09-17"; :>> judgedBy = "claudeFable5"; }
    verification guardsAreMembersPerFamilyRetroGate : Test { :>> id = "c15342f0-f9b6-49ce-8e3f-e378faa0f5b4"; :>> title = "Sprint 733 retro gate (autonomous, D0049)"; :>> createdAt = "2026-09-17"; :>> createdBy = "claudeFable5"; :>> method = VerificationMethod::analyze; :>> procedureText = "Retro of sprint 733, written before the verifier was dispatched (D0131: every finding is a tracked item or the retro says why not). Avoidable issues scanned (issue011): five found, each below. FINDINGS -> ITEMS: (1) twelve cwd-relative test anchors broke on the move and scripts/split_guards.py paid the fix in a DEPTH_REWRITES table; dcOneRepoRootHelper predicted this at sprint 731 and the sprint that moved the files paid it instead - TWICE: the DEPTH_REWRITES deepening was itself a cwd anchor and the control touched.rs no_member_test_anchors_on_a_cwd_relative_path refused all ten at the touched rung (verifier run 3, touched-1789626979.log), so the landed form is a crate-level test_repo_root() from the manifest's ancestors, the ninth local helper the item collapses -> issue583, resolver dcOneRepoRootHelper, MOVED to the head of the D0479 cluster (D0052: declaration order is priority) so dcSuiteIsAMember inherits no path fix. (2) the DoD's premise 'the families guards.md already groups by' was false - grep '^## ' .engine/docs/guards.md gives tiers, not families; the families came from the FAMILIES tables -> issue584, new item dcGuardsCatalogueNamesTheFamily. (3) members/keel-write and members/keel-guards both reach upward with build = ../../keel-cli/build.rs and modgraph reads [dependencies] only -> issue585, new item dcBuildScriptHasOneHomeBelowItsUsers. (4) the D0499 facts block described a fixed commit range but read its text from the working tree, so the move nulled every fact of the block; fixed here with git show 50e171a:keel-cli/src/guards.rs, class uncontrolled -> issue586, new item dcFactsAboutARangeReadTheRange. FIXED IN THE SPRINT, NO ITEM: (5) module_home('guards') can no longer name one file - scripts/module_home.py gained crate_text/crate_root/crate_sources with real-tree probe cases (python scripts/module_home.py --probe: 0 failures), and facts.py reads the crate's text; (6) literal-text facts flipped on the move (crate:: became keel_schema::, fn became pub(crate) fn, the dispatch arm became a family-table entry) - read back by a leaf-level diff of facts.json before and after (330 leaf differences reviewed, only the intended flips), each regex now accepts both spellings. NON-FINDING: (7) clippy items_after_test_module surfaced only under --all-targets, but the ladder (keel-cli/src/verify.rs), CI (.github/workflows/ci.yml) and pre-commit (.githooks/pre-commit) all lint --all-targets - the control exists and fired. FOUND AT THE LANDING COMMIT, AFTER THIS RETRO WAS FIRST WRITTEN: (8) scripts/probes/issue400_reproduction.py scanned keel-cli/**/*.rs as the Rust tree and its defect stopped reproducing once the guard bodies were a member (27 of 75); the pre-commit script-probe runner (D0496) aborted the commit as designed, the scan now covers keel-cli and members/** -> issue587, resolver this story, fixed in the landing commit. REFINE NOTE: the refine gate's 'assembled' claim is an equality test (the nine family files' text re-joined equals the source at 50e171a modulo the header and the path rewrites), which is what split_guards.py asserts before it writes."; }
    // RAN: LADDER: keel verify . --probe-from pair733.txt -> outcome=pass stopped_at=none validate=pass guard=pass clippy=pass probe=pass touched=pass
    part guardsAreMembersPerFamilyRetroGateR1 : TestResult { :>> id = "144e8f6c-c2c9-412a-929e-aa6df8f97c19"; :>> outcome = VerdictKind::proposed; :>> judgedAgainst = "f8d3d8d"; :>> judgedAt = "2026-09-17"; :>> judgedBy = "claudeFable5"; }
}
