// ProjectDeliveryS720 — Sprint 720: Sprint 720: dcInstrumentAnswersCarryTheirSourceHash, the correction for issue560 - facts.py died at HEAD on sprint 719's edit, which had never been run, and the twenty-eighth brief was built from the previous run's answer. An answer now records the hash of the instrument that wrote it and a reader refuses one the instrument has changed under, or one read from another tree; the module resolver refuses a bare resolution of a module every crate has and its scan flags the call shape. EXECUTE. 1 pt.. EXECUTE. 1 pts.
package ProjectDeliveryS720 {
    private import EngineElement::*;
    private import EngineWork::*;
    private import EngineVerification::*;
    private import EngineRelationships::*;

    #CharteredBy dependency from instrumentAnswersCarryTheirSourceHashStory to d0387;

    part instrumentAnswersCarryTheirSourceHashStory : Story {
        :>> id = "5c8d08c1-c155-4135-a09c-de86d5eded6c";
        :>> title = "Sprint 720: Sprint 720: dcInstrumentAnswersCarryTheirSourceHash, the correction for issue560 - facts.py died at HEAD on sprint 719's edit, which had never been run, and the twenty-eighth brief was built from the previous run's answer. An answer now records the hash of the instrument that wrote it and a reader refuses one the instrument has changed under, or one read from another tree; the module resolver refuses a bare resolution of a module every crate has and its scan flags the call shape. EXECUTE. 1 pt. (1 pts)";
        :>> createdAt = "2026-09-15"; :>> createdBy = "claudeFable5"; :>> kind = WorkKind::code; :>> priority = WorkPriority::p0; :>> owner = "claudeFable5"; :>> estimatedPoints = 1;
    }

    action def DeliveryRunS720 {
        action storyInstrumentAnswersCarryTheirSourceHash;
        verification storyInstrumentAnswersCarryTheirSourceHashDoD : Test { :>> id = "68e00472-fda0-45d0-bf23-2d8a59e77b00"; :>> method = VerificationMethod::test; :>> procedureText = "DELIVERED BACKLOG ITEMS: dcInstrumentAnswersCarryTheirSourceHash. Done means: python scripts/artefact.py --probe and python scripts/module_home.py --probe exit 0 on this tree with the issue560 pairs in each; python scripts/exec_brief/facts.py exits 0 at HEAD, complete true, instrument.sources three entries; the twenty-ninth brief builder reads that answer through require_complete and refuses a re-read after facts.py is edited"; }
        // RAN: // RAN: python scripts/artefact.py --probe artefact probe: 0 failure(s) // RAN: python scripts/module_home.py --probe module_home probe: 0 failure(s) // RAN: python -c json.load(decision-facts-30.json) -> complete/tree/sources + sha256 of each source against the tree at ecc393e complete True tree cfb1cb8 sources 3 scripts/exec_brief/facts.py OK scripts/module_home.py OK scripts/artefact.py OK // RAN: gh run list --limit 1 --json conclusion,status,headSha [{'conclusion':'success','headSha':'ecc393ec9bbc17c3aaf6a4bd560abc216bc82357','status':'completed'}]
        part storyInstrumentAnswersCarryTheirSourceHashDoDR1 : TestResult { :>> id = "02d515b6-7985-4be2-9695-4c43a03f7a4a"; :>> outcome = VerdictKind::pass; :>> judgedAgainst = "ecc393e"; :>> judgedAt = "2026-09-14"; :>> judgedBy = "claudeFable5"; }
    }

    verification instrumentAnswersCarryTheirSourceHashRefineGate : Test { :>> id = "a7542ccf-44fb-4aae-8ee3-a051057cf440"; :>> title = "Sprint 720 refine gate (DoR)"; :>> createdAt = "2026-09-15"; :>> createdBy = "claudeFable5"; :>> method = VerificationMethod::inspect; :>> procedureText = "DoR: chartered by D0387 (accepted: a dead run leaves no answer that reads as current) through its #CharteredBy edge - this sprint extends the same refusal to an instrument that changed; sized 1 (two Python edits with probe pairs, one call-site change). Worked ahead of the ranked frontier because the twenty-ninth publish cannot be built until facts.py runs, and the queue changed (fourteen answered) so the page is owed now"; }
    // RAN: DoR read: #CharteredBy to d0387 in the sprint file; estimatedPoints 1; DoD Test present. Worked ahead of the frontier because the twenty-ninth publish needed facts.py to run.
    part instrumentAnswersCarryTheirSourceHashRefineGateR1 : TestResult { :>> id = "377c4b2c-3d58-4874-a509-451bf83564b3"; :>> outcome = VerdictKind::proposed; :>> judgedAgainst = "HEAD"; :>> judgedAt = "2026-09-14"; :>> judgedBy = "claudeFable5"; }
    verification instrumentAnswersCarryTheirSourceHashStandupGate : Test { :>> id = "14d79732-d86a-4793-8d89-34f8ccfd2ca3"; :>> title = "Sprint 720 standup gate"; :>> createdAt = "2026-09-15"; :>> createdBy = "claudeFable5"; :>> method = VerificationMethod::inspect; :>> procedureText = "Order: facts.py run first to see the failure whole (two defects: the bare lib resolution, then the removed _src with two uses left); the resolver's crate= and every-crate refusal with its probe pairs, the scan widened to the call shape; artefact's source hashes and tree check with its pairs; facts.py passes its three sources and runs green; then the Issue, the resolver item and this record"; }
    // RAN: Order followed as written: facts.py run first (two defects seen whole), module_home crate= and every-crate refusal with probe pairs, artefact source hashes and tree check with pairs, facts.py re-run with three sources, then issue560/issue561, the two backlog items and this record.
    part instrumentAnswersCarryTheirSourceHashStandupGateR1 : TestResult { :>> id = "55ce80d5-8190-4a4c-bc42-3b445a6d6de0"; :>> outcome = VerdictKind::proposed; :>> judgedAgainst = "HEAD"; :>> judgedAt = "2026-09-14"; :>> judgedBy = "claudeFable5"; }
    verification instrumentAnswersCarryTheirSourceHashImplementGate : Test { :>> id = "9a025b70-76e1-46b9-9082-7ede4e97df86"; :>> title = "Sprint 720 implement gate"; :>> createdAt = "2026-09-15"; :>> createdBy = "claudeFable5"; :>> method = VerificationMethod::test; :>> procedureText = "The implement gate is the two probes and the facts run: python scripts/module_home.py --probe exit 0 (19 checks, the tree scan clean), python scripts/artefact.py --probe exit 0 (16 checks), python scripts/exec_brief/facts.py exit 0 with complete true and instrument.sources of three at this tree"; }
    // RAN: // RAN: python scripts/module_home.py --probe pass this tree: guards resolves - C:/Users/WilliamWeatherholtz/claude_code/sysmlv2-ai-toolkit/keel-cli/src/guards.rs pass this tree: view resolves - C:/Users/WilliamWeatherholtz/claude_code/sysmlv2-ai-toolkit/keel-cli/src/view/mod.rs pass this tree: no script anchors a .rs file under keel-cli/src - none module_home probe: 0 failure(s) exit=0 // RAN: python scripts/artefact.py --probe pass known-negative: ...unless the reader asks for a historical answer pass claim() removes the previous page before the run pass claim() on nothing is not an error artefact probe: 0 failure(s) // RAN: python -c 'json.load(decision-facts-30.json)' instrument check complete True tree cfb1cb8 sources 3
    part instrumentAnswersCarryTheirSourceHashImplementGateR1 : TestResult { :>> id = "2d7c21b7-1423-45b6-8363-87d822c4b0b9"; :>> outcome = VerdictKind::pass; :>> judgedAgainst = "HEAD"; :>> judgedAt = "2026-09-14"; :>> judgedBy = "claudeFable5"; }
    verification instrumentAnswersCarryTheirSourceHashReviewGate : Test { :>> id = "5b6f014a-2e60-4a5f-a3b2-4764f232120c"; :>> title = "Sprint 720 review gate — three passes per D0172"; :>> createdAt = "2026-09-15"; :>> createdBy = "claudeFable5"; :>> method = VerificationMethod::inspect; :>> procedureText = "Three passes (D0172). Correctness: the every-crate refusal fires before any directory is read, so it does not depend on which crates exist; crate= filters by the crate directory's basename, which is what a caller knows; the tree check compares by prefix so a 7- and an 8-character short sha agree, and KEEL_ARTEFACT_ANY_TREE is the one named way to read history. Honesty: the previous answer (decision-facts-30.json, written before the source-hash change) carries no instrument block and is accepted by the new reader - a bootstrap gap; it was re-run after the last facts.py edit so the twenty-ninth page reads a hashed answer, and every answer from now on is refused on drift. Scope: no view, guard or write-path change; the two backlog items and two Issues recorded (issue560 here, issue561 the lens gap the same page exposed) are the only tracking edits besides this record"; }
    // RAN: Correctness/honesty/scope passes read against scripts/module_home.py, scripts/artefact.py and scripts/exec_brief/facts.py on this tree; the previous answer was re-run after the last facts.py edit (hashes verified equal: ce2b0cbf / d0087bf6 / b9127ee1); no view, guard or write-path change.
    part instrumentAnswersCarryTheirSourceHashReviewGateR1 : TestResult { :>> id = "4885dc6b-7df0-4ee4-b252-8274008ab992"; :>> outcome = VerdictKind::proposed; :>> judgedAgainst = "HEAD"; :>> judgedAt = "2026-09-14"; :>> judgedBy = "claudeFable5"; }
    verification instrumentAnswersCarryTheirSourceHashCloseOutGate : Test { :>> id = "dacb8431-f47b-493c-8c78-68d30149a1df"; :>> title = "Sprint 720 closeOut gate (autonomous, D0049)"; :>> createdAt = "2026-09-15"; :>> createdBy = "claudeFable5"; :>> method = VerificationMethod::inspect; :>> procedureText = "Close-out at the landing commit after the CI conclusion reads success: git status -sb level with origin, gh run conclusion, the DoD result recorded against dcInstrumentAnswersCarryTheirSourceHashDoD at that sha"; }
    // RAN: Close-out read at ecc393e: git status -sb level with origin (main...origin/main); gh run conclusion success at ecc393e; the DoD result for storyInstrumentAnswersCarryTheirSourceHash recorded against ecc393e with both probes, the hashed answer and the CI conclusion as its receipt.
    part instrumentAnswersCarryTheirSourceHashCloseOutGateR1 : TestResult { :>> id = "7af5b494-abaa-448e-8cd1-a48b5b7b0157"; :>> outcome = VerdictKind::proposed; :>> judgedAgainst = "ecc393e"; :>> judgedAt = "2026-09-14"; :>> judgedBy = "claudeFable5"; }
    verification instrumentAnswersCarryTheirSourceHashRetroGate : Test { :>> id = "5de4b1fa-43ef-49d2-ab6e-4a568b1342ed"; :>> title = "Sprint 720 retro gate (autonomous, D0049)"; :>> createdAt = "2026-09-15"; :>> createdBy = "claudeFable5"; :>> method = VerificationMethod::analyze; :>> procedureText = "Retro, avoidable-issue scan over the sprint: (1) AVOIDABLE - sprint 719's DoD said facts.py resolves its modules through the resolver and its review pass said cliFamilyCensus is computed again - both were read from the edit, not from a run; the twenty-eighth builder's docstring even recorded that the facts were from 15a8330. A claim that an instrument works is a claim it RAN: the new refusal makes the previous answer unusable once the instrument changes, so the run cannot be skipped - control, not reminder (D0047). (2) The Business gate for st126's Needs was invisible to keel show authority-queue (issue561, dcAuthorityQueueListsConfirmationGates): the lens enumerates two kinds; a view change, so a CR when worked. (3) Two Issues found while doing a Business-phase task; both got a resolver at record time and neither was fixed silently"; }
    // RAN: Retro read: the gate text names the avoidable-issue scan (findings 1-3). Added at this sitting, no new item: (4) the ceremony guard refused sprint 719 retro because its gate text lacked the scan wording - caught by the existing guard before the commit, the text was corrected and the result re-recorded in the same commit; (5) the two new backlog items were appended at the end of the backlog and the priority-inversion guard named 52 new inversions - reordered to where their computed class ranks them before the commit; both caught by controls already on the tree.
    part instrumentAnswersCarryTheirSourceHashRetroGateR1 : TestResult { :>> id = "22ea71de-21f4-4c3d-b036-5e3776d3a9e4"; :>> outcome = VerdictKind::proposed; :>> judgedAgainst = "ecc393e"; :>> judgedAt = "2026-09-14"; :>> judgedBy = "claudeFable5"; }
}
