// ProjectDeliveryS739 — Sprint 739: the Claude hooks are a member - dcHooksAreAMember, the ninth D0479 extraction and the first slice of dcKeelCliIsThinDispatch, chartered by D0479. The keel hook body (stop, post-edit, pre-bash, pre-write, config-change, subagent-stop, prompt - 1246 lines of main.rs), its override and ledger helpers, the two recall constants the prompt hook shares with keel recall and the two hook test modules are sliced out of keel-cli/src/main.rs into members/keel-hooks/src/lib.rs; shellcheck.rs and proactive.rs move beside them. find_repo_root and engine_version_skew, two dispatch-level helpers the hooks and the binary both call, descend to keel_process::workspace as pub must_use fns - a member cannot call into the binary. keel-cli's lib.rs re-exports keel_hooks as hooks and shellcheck and proactive at their old paths; main.rs imports the eight names it still calls. The hook dispatch line is unchanged and main.rs is outside the enforcement-surface lock, so D0511 (accepted under standing consent, #DependsOn d0479) records the layering with no marker. Three doc comments orphaned in main.rs by earlier moves are reattached to the fns they describe.. EXECUTE. 5 pts.
package ProjectDeliveryS739 {
    private import EngineElement::*;
    private import EngineWork::*;
    private import EngineVerification::*;
    private import EngineRelationships::*;

    #CharteredBy dependency from hooksAreAMemberStory to d0479;

    part hooksAreAMemberStory : Story {
        :>> id = "2a7a54ba-73a4-4af8-ba22-85201eee53c9";
        :>> title = "Sprint 739: the Claude hooks are a member - dcHooksAreAMember, the ninth D0479 extraction and the first slice of dcKeelCliIsThinDispatch, chartered by D0479. The keel hook body (stop, post-edit, pre-bash, pre-write, config-change, subagent-stop, prompt - 1246 lines of main.rs), its override and ledger helpers, the two recall constants the prompt hook shares with keel recall and the two hook test modules are sliced out of keel-cli/src/main.rs into members/keel-hooks/src/lib.rs; shellcheck.rs and proactive.rs move beside them. find_repo_root and engine_version_skew, two dispatch-level helpers the hooks and the binary both call, descend to keel_process::workspace as pub must_use fns - a member cannot call into the binary. keel-cli's lib.rs re-exports keel_hooks as hooks and shellcheck and proactive at their old paths; main.rs imports the eight names it still calls. The hook dispatch line is unchanged and main.rs is outside the enforcement-surface lock, so D0511 (accepted under standing consent, #DependsOn d0479) records the layering with no marker. Three doc comments orphaned in main.rs by earlier moves are reattached to the fns they describe. (5 pts)";
        :>> createdAt = "2026-09-17"; :>> createdBy = "claudeFable5"; :>> kind = WorkKind::code; :>> priority = WorkPriority::p0; :>> owner = "claudeFable5"; :>> estimatedPoints = 5;
    }

    action def DeliveryRunS739 {
        action storyHooksAreAMember;
        verification storyHooksAreAMemberDoD : Test { :>> id = "5142c6bb-1560-47ed-a78a-41c08fa9e2c5"; :>> method = VerificationMethod::test; :>> procedureText = "DELIVERED BACKLOG ITEMS: dcHooksAreAMember. DONE MEANS: members/keel-hooks holds src/lib.rs (1455 lines: the hook body with 58 keel_cli:: paths rewritten to the owning members, the override and ledger helpers, RECALL_CAP_MS / RECALL_BUDGET / OVERRIDE_TTL_SECS, the subagent-block and override test modules, and a mod tests holding the 92 lines of hook tests that lived in main.rs's), src/shellcheck.rs and src/proactive.rs under the member lint preamble, with a Cargo.toml naming keel-perf, keel-git, keel-actor, keel-model, keel-write, keel-view, keel-guards, keel-suite, keel-process and serde_json, dev-dep keel-fs and build = ../../keel-cli/build.rs; keel-cli/src holds neither shellcheck.rs nor proactive.rs and main.rs (4726 lines, from 6187) defines no fn cmd_hook while its Some('hook') => cmd_hook(rest) dispatch line is unchanged; members/keel-process/src/workspace.rs holds find_repo_root and engine_version_skew as pub must_use fns before its test module; the root manifest lists members/keel-hooks between keel-issues and keel-serve and keel-cli's manifest depends on it; scripts/extract_hooks.py is the idempotent transform (dry-run default; 2 files moved, 6 slices conserved out of main.rs, 6 fns + 3 consts published, 6 anchored edits in 5 staying files, 2 files written; re-run says already applied); cargo clippy --release --workspace --all-targets -D warnings clean; keel --help byte-identical to the pre-move render (cmp help_before739.txt, 15089 bytes) and keel version's guard line unchanged (75: 66 hard-blocking, 9 warning-only); python scripts/modgraph.py --check and python scripts/module_home.py --probe hold and module_home names members/keel-hooks for shellcheck and proactive. Known-positive, chosen before the tree is read (the DoD's own words): the three member files exist and the two keel-cli files do not; main.rs has no fn cmd_hook and keeps the dispatch line; cargo tree -p keel-hooks names no keel-cli, keel-serve or keel-issues; touching members/keel-hooks/src/lib.rs recompiles keel-hooks and keel-cli under cargo build --release --verbose with all sixteen other members Fresh; the keel-hooks unit tests (20) and the keel-process lib tests (29) pass; keel --help equals the pre-move capture (pos739.py). Known-negative: a pub use keel_serve::serve planted in members/keel-hooks/src/lib.rs fails cargo check -p keel-hooks naming the undeclared crate keel_serve, lib.rs restored bytes and mtime on every path (neg739.py). The DoD was authored this sprint with the tree already applied, so its prose and the tree hold at every point."; }
        // RAN: keel suite --touched: pass - 873 passed in 1016s; slowest federation f1_a_scaffolded_project_can_make_its_first_commit_at_any_path_shape 359.3s; 0 failed
        part storyHooksAreAMemberDoDR1 : TestResult { :>> id = "d6547782-a692-4fe7-b843-a90c8815e4ee"; :>> outcome = VerdictKind::pass; :>> judgedAgainst = "2ffa64b4"; :>> judgedAt = "2026-09-17"; :>> judgedBy = "claudeFable5"; }
    }

    verification hooksAreAMemberRefineGate : Test { :>> id = "243cbae5-6c94-4640-af17-ad9c57e438b5"; :>> title = "Sprint 739 refine gate (DoR)"; :>> createdAt = "2026-09-17"; :>> createdBy = "claudeFable5"; :>> method = VerificationMethod::inspect; :>> procedureText = "DoR: dcKeelCliIsThinDispatch was the second line of keel show whats-next at 2ffa64b4 (brief 44 landed, CI conclusion success); its DoD asks for main.rs under 800 lines with every cmd_ body in the member owning its verb, and the hook body is the one whose verb has no owning member, so the item is split: dcHooksAreAMember is recorded before it in EngineBuild (declaration order IS priority, D0052), chartered by D0479 through its #CharteredBy edge, #DependsOn dcServeAndGithubAreMembers (done), and dcKeelCliIsThinDispatch gains a #DependsOn edge to it; keel show whats-next reads dcHooksAreAMember second and the parent blocked. Sized 5 - one codemod that slices main.rs at six anchored ranges rather than moving files, one new member manifest with a build script, two file moves, two helpers descending to keel-process, nine publications, the D0388 pair as two scripts and an unmarked Decision; no locked path changes. Not split further: the hook body, its tests and its consts are one compilation unit. Blocking dependencies: none; the one locked path the parent will touch (keel-cli/src/adherence.rs, GUARD_SOURCE_FILES) is left for the parent's own marked Decision."; }
    // RAN: validate=pass guard=pass clippy=pass probe=pass touched=pass
    part hooksAreAMemberRefineGateR1 : TestResult { :>> id = "9eaf2f8e-e51f-41ac-a26b-4076fd9c758d"; :>> outcome = VerdictKind::proposed; :>> judgedAgainst = "2ffa64b4"; :>> judgedAt = "2026-09-17"; :>> judgedBy = "claudeFable5"; }
    verification hooksAreAMemberStandupGate : Test { :>> id = "23dbf032-655f-4140-ba03-ee3b0a3cd2ce"; :>> title = "Sprint 739 standup gate"; :>> createdAt = "2026-09-17"; :>> createdBy = "claudeFable5"; :>> method = VerificationMethod::inspect; :>> procedureText = "Owner claudeFable5. Blocker: none - 2ffa64b4 landed with CI success, no ladder or land is running; the human's serve runs from the pin cache, so the release image rebuilds freely. Order: (1) inventory main.rs (inv_main.py: every top-level item, its span and the crates it names; block_deps.py: every outside name the hook block and its two test slices call bare) before the script is written. (2) scripts/extract_hooks.py: git mv shellcheck.rs and proactive.rs, rewrite their crate:: paths, slice the six ranges (repo-root discovery, engine_version_skew, the hook block, the recall constants, the two hook test modules, the hook tests inside mod tests) out of main.rs, publish the fns and consts main.rs still calls, write the member's Cargo.toml and lib.rs, insert the two helpers into workspace.rs before its test module, edit the root and keel-cli manifests, keel-cli's lib.rs re-exports and main.rs's imports; dry-run reconciled, then --apply. (3) cargo build --release, clippy --workspace --all-targets, keel --help against help_before739.txt, keel version, cargo test -p keel-hooks and -p keel-process --lib; modgraph --check; module_home --probe. (4) pos739/neg739; pair739.txt. (5) the backlog item and its three edges, D0511, the retro Issue with its resolver, the sprint with the retro filled, sync-claude --check; verifier with the pair file; recorder --owed 7; land; CI conclusion. decision-surfacing: D0511 auto-accepts, so the pending set is unchanged and the page is silent."; }
    // RAN: validate=pass guard=pass clippy=pass probe=pass touched=pass
    part hooksAreAMemberStandupGateR1 : TestResult { :>> id = "7397af65-4df6-4559-a097-107df157881a"; :>> outcome = VerdictKind::proposed; :>> judgedAgainst = "2ffa64b4"; :>> judgedAt = "2026-09-17"; :>> judgedBy = "claudeFable5"; }
    verification hooksAreAMemberImplementGate : Test { :>> id = "5e15b05d-71ba-47c4-a7e0-ff68d55ad993"; :>> title = "Sprint 739 implement gate"; :>> createdAt = "2026-09-17"; :>> createdBy = "claudeFable5"; :>> method = VerificationMethod::test; :>> procedureText = "The implement gate is the DoD's own probes plus the ladder: python scripts/extract_hooks.py dry run reconciled (2 files moved, 6 slices conserved, 6 fns + 3 consts published, 6 anchored edits in 5 staying files, 2 files written), --apply, cargo build --release -p keel-cli Finished (2m05s); cargo clippy --release --workspace --all-targets -- -D warnings Finished clean; cmp help_before739.txt help_after.txt byte-identical (15089 bytes); keel version guards line 75 (66 hard-blocking, 9 warning-only); python scripts/modgraph.py --check exit 0 (71 modules, 7 edges); python scripts/module_home.py --probe 0 failures; cargo test --release -p keel-hooks 20 passed; cargo test --release -p keel-process --lib 29 passed; python pos739.py PASS; python neg739.py PASS (cargo check rc 101 naming keel_serve, lib.rs restored); python scripts/extract_hooks.py re-run: already applied; keel gate validate 854 clean with dcHooksAreAMember, its three edges, issue600 and its resolver item in the tree; keel gate check-engine clean with D0511 and its #DependsOn edge; keel sync-claude --check matches (47 skills). Two apply-and-revert rounds preceded the clean apply: the first build wanted KEEL_BUILD_COMMIT (the console-liveness probe's env!, answered by build = ../../keel-cli/build.rs) and OVERRIDE_TTL_SECS (a const the inventory missed, published), and clippy wanted must_use on the two descended helpers, their placement before workspace.rs's test module, and backticks on the hook event names in the member doc."; }
    // RAN: validate=pass guard=pass clippy=pass probe=pass touched=pass
    part hooksAreAMemberImplementGateR1 : TestResult { :>> id = "cc043981-e194-462f-8413-ed74a357b9a4"; :>> outcome = VerdictKind::pass; :>> judgedAgainst = "2ffa64b4"; :>> judgedAt = "2026-09-17"; :>> judgedBy = "claudeFable5"; }
    verification hooksAreAMemberReviewGate : Test { :>> id = "a7494678-ea65-48b6-ba50-39184a0073c8"; :>> title = "Sprint 739 review gate — three passes per D0172"; :>> createdAt = "2026-09-17"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every moved test passes in its new crate (20 in keel-hooks, the two hook test modules and the 92 lines from main.rs's mod tests among them), every caller of the moved names resolves through a re-export or the eight-name import (zero caller edits outside main.rs's import block and its test-module use line), the hook dispatch line is byte-identical, and the binary's help and guard count are the pre-move ones. Honesty: the negative plants in keel-hooks' lib.rs and asserts the compiler names the crate the member must not know, not merely that the build fails; the positive touches the member's own file and reads Fresh for all sixteen other members from cargo's verbose lines, checks the dependency tree by cargo tree rather than by reading the manifest, asserts the dispatch line is still there, and compares help to a capture taken before the move. Scope: no locked path is in the diff (main.rs is asserted NOT locked by is_enforcement_surface in members/keel-guards/src/lib.rs; adherence.rs stays), no hook script, CI yml or rule edit, so D0511 carries no marker and accepted under standing consent - NOT A PROCESS CHANGE: every hook fires from the same binary path through the same dispatch line."; }
    // RAN: validate=pass guard=pass clippy=pass probe=pass touched=pass
    part hooksAreAMemberReviewGateR1 : TestResult { :>> id = "175aeddf-1a41-48c8-8834-9a1d2d0c1998"; :>> outcome = VerdictKind::proposed; :>> judgedAgainst = "2ffa64b4"; :>> judgedAt = "2026-09-17"; :>> judgedBy = "claudeFable5"; }
    verification hooksAreAMemberCloseOutGate : Test { :>> id = "4a889db6-00bc-4d05-9046-174628eed7c8"; :>> title = "Sprint 739 closeOut gate (autonomous, D0049)"; :>> createdAt = "2026-09-17"; :>> createdBy = "claudeFable5"; :>> method = VerificationMethod::inspect; :>> procedureText = "Landed when the verifier's receipt reads DISCREPANCIES: NONE and its probe rung row names pair739.txt, the recorder's report passes check_report.py --owed 7, git status -sb is clean after keel land and gh run list names the landing commit with conclusion success. The DoD result is recorded against dcHooksAreAMemberDoD at that sha; D0511 is accepted (non-fork, no marker), so the authority queue's pending set is unchanged and decision-surfacing is silent. dcKeelCliIsThinDispatch's #DependsOn edge to this item is satisfied when the DoD result lands; it is the last extraction and its adherence.rs move needs its own marked Decision."; }
    // RAN: validate=pass guard=pass clippy=pass probe=pass touched=pass
    part hooksAreAMemberCloseOutGateR1 : TestResult { :>> id = "caf2b825-3b5c-412a-8861-f8602a27b21d"; :>> outcome = VerdictKind::proposed; :>> judgedAgainst = "2ffa64b4"; :>> judgedAt = "2026-09-17"; :>> judgedBy = "claudeFable5"; }
    verification hooksAreAMemberRetroGate : Test { :>> id = "41bc5267-7028-4812-986b-0962636c1351"; :>> title = "Sprint 739 retro gate (autonomous, D0049)"; :>> createdAt = "2026-09-17"; :>> createdBy = "claudeFable5"; :>> method = VerificationMethod::analyze; :>> procedureText = "Written at close-out, before the verifier is dispatched; avoidable issues scanned (issue011), each finding a tracked item or the reason it is not. (1) record task appends at the end of the def, so the split item landed at rank 26 below twenty-four items it now gates and was moved to rank 2 by a hand script (move739.py) - a backlog write the write lock and the record verb's validation never saw. Tracked: issue600, resolver dcRecordTaskPlacesTheItemBeforeANamedOne (added this sprint) - a --before flag that declares the item at its position. (2) The design inventory (block_deps.py) missed OVERRIDE_TTL_SECS because the const regex captured its trailing colon into the name, so the first build failed on one unpublished const and the script was reverted and re-applied; the build is the control that caught it and fired. Not tracked as an Issue: the inventory is a scratchpad script for a codemod that will be written once more (the parent), and a second miss of the same class would make it a pattern; the reconciliation line a codemod prints is where a names-the-staying-text-still-calls check belongs if it recurs. (3) Three doc comments were orphaned in main.rs before this sprint (cmd_check_engine's and keel gate --fast's above gate_subverb, keel why's above budget_arg) and the slice made the first two a three-doc merge on one fn; fixed in this commit by reattaching each to the fn it describes (redoc739.py, doc lines only, clippy clean). Not tracked: rustdoc has no lint for a doc that describes a different item and the parent sprint moves every remaining body out of main.rs, which is where the class ends. (4) The codemod's docstring said five names are published; the count was eight names imported from six fns and three consts by the time it applied clean - the dual-truth class in a comment. Fixed in this commit; not tracked: the reconciliation line prints the counts from the lists themselves, and the docstring now names the lists rather than restating a number that the line computes. (5) The backlog item was recorded after the code change was applied and verified, not before - recording rode with the sprint rather than ahead of it, and the DoD was written knowing the tree. Not a defect in the record (the DoD names the probes and both pass) but the order is the build-now-record-later shape; dcSprintNamesTheItemItDelivers on the frontier is the control that binds a sprint to an item, and this sprint's record names it. (6) The codemod applied clean on its third run with no fix-up pass after apply; the first two rounds were reverted whole by git checkout and git mv rather than patched in place, so the script is the only transform on the tree. Non-finding. (7) facts.py section 4's how-string cites keel-cli/src/shellcheck.rs by its old path while the fact itself reads the file through module_home (scripts/exec_brief/facts.py); the number is right and the citation is history. Not tracked separately: dcSourceCitationsOnTheLivingDocsResolve is the frontier item for stale path citations and this is one of its rows."; }
    // RAN: validate=pass guard=pass clippy=pass probe=pass touched=pass
    part hooksAreAMemberRetroGateR1 : TestResult { :>> id = "29c42ce2-720d-4bca-a078-b14c1d4973f9"; :>> outcome = VerdictKind::proposed; :>> judgedAgainst = "2ffa64b4"; :>> judgedAt = "2026-09-17"; :>> judgedBy = "claudeFable5"; }
}
