// ProjectDeliveryS729 — Sprint 729: dcUnitTestScratchIsPerProcess, the correction for issue570 - two overlapping lib runs during sprint 724's ceremony produced two different failing sets from unit tests that build their scratch trees at fixed names under temp_dir(). One helper, keel_fs::scratch(tag), suffixes the tag with the process id; a census test in the keel-cli lib reads every src tree and keel-cli/tests and fails any temp_dir().join( in test code whose argument carries no per-process token. EXECUTE. 3 pts.
package ProjectDeliveryS729 {
    private import EngineElement::*;
    private import EngineWork::*;
    private import EngineVerification::*;
    private import EngineRelationships::*;

    #CharteredBy dependency from unitTestScratchIsPerProcessStory to d0498;

    part unitTestScratchIsPerProcessStory : Story {
        :>> id = "9ed22cea-4098-49e7-a1cc-82827b8cfca0";
        :>> title = "Sprint 729: dcUnitTestScratchIsPerProcess, the correction for issue570 - two overlapping lib runs during sprint 724's ceremony produced two different failing sets from unit tests that build their scratch trees at fixed names under temp_dir(). One helper, keel_fs::scratch(tag), suffixes the tag with the process id; a census test in the keel-cli lib reads every src tree and keel-cli/tests and fails any temp_dir().join( in test code whose argument carries no per-process token (3 pts)";
        :>> createdAt = "2026-09-16"; :>> createdBy = "claudeFable5"; :>> kind = WorkKind::code; :>> priority = WorkPriority::p0; :>> owner = "claudeFable5"; :>> estimatedPoints = 3;
    }

    action def DeliveryRunS729 {
        action storyUnitTestScratchIsPerProcess;
        verification storyUnitTestScratchIsPerProcessDoD : Test { :>> id = "9188bf4b-3237-480e-8f4f-eb4fd159b826"; :>> method = VerificationMethod::test; :>> procedureText = "DELIVERED BACKLOG ITEMS: dcUnitTestScratchIsPerProcess. DONE MEANS: keel_fs::scratch(tag) exists in members/keel-fs/src/fsx.rs (re-exported at the crate root) and returns temp_dir()/<tag>-<process id>; every fixed-name temp_dir().join( site in test code under keel-cli/src, keel-cli/tests and members/*/src calls it; keel-actor gains keel-fs as a dev-dependency; the census test in keel-cli/src/touched.rs reads those three trees and fails on a temp_dir().join( at or below a file's first bare #[cfg(test)] line (or anywhere under keel-cli/tests) whose argument has neither process::id() nor gen_uuid(), naming file and line; the production worktree sites (history.rs keel-audit, reports.rs keel-trend, view/mod.rs keel-bl) are above their files' first #[cfg(test)] and are not named. The D0388 pair is the two touched::tests unit tests named in standup, both green, and the real-tree census passes."; }
        // RAN: TOUCHED RECEIPT: outcome=pass passed=900 failed=0
        part storyUnitTestScratchIsPerProcessDoDR1 : TestResult { :>> id = "1db6c8ce-c02a-41fe-aa2c-19db6cb8af3f"; :>> outcome = VerdictKind::pass; :>> judgedAgainst = "1ecbef0"; :>> judgedAt = "2026-09-16"; :>> judgedBy = "claudeFable5"; }
    }

    verification unitTestScratchIsPerProcessRefineGate : Test { :>> id = "04cf6bf0-b9a3-4c6e-8ce0-b8a43d504582"; :>> title = "Sprint 729 refine gate (DoR)"; :>> createdAt = "2026-09-16"; :>> createdBy = "claudeFable5"; :>> method = VerificationMethod::inspect; :>> procedureText = "Chartered by D0498 (accepted at record time under standing consent: a rule about how test code is written, held by a lib test; no gate, hook, workflow step or skill changes). One backlog item, ranked first on the frontier after brief 35 landed (issue570 Medium). 3 points: a two-line helper with its test, some thirty-five mechanical site edits across four crates, one dev-dependency, and a census with its probe pair. No schema change."; }
    // RAN: LADDER: KEEL verify . -> outcome=pass
    part unitTestScratchIsPerProcessRefineGateR1 : TestResult { :>> id = "7d7a7672-bb1c-4b22-9a50-4d90743f4d78"; :>> outcome = VerdictKind::proposed; :>> judgedAgainst = "1ecbef0"; :>> judgedAt = "2026-09-16"; :>> judgedBy = "claudeFable5"; }
    verification unitTestScratchIsPerProcessStandupGate : Test { :>> id = "7f93ecfd-e966-40cd-a5a5-285cc1c43884"; :>> title = "Sprint 729 standup gate"; :>> createdAt = "2026-09-16"; :>> createdBy = "claudeFable5"; :>> method = VerificationMethod::inspect; :>> procedureText = "Owner claudeFable5. Blocker: none - no land or ladder was running when the build started (tasklist showed no cargo, rustc, nextest or keel-land). The D0388 pair is stated before the tree is read and lives in keel-cli/src/touched.rs: known-positive is cargo test --release --lib -- touched::tests::the_scratch_census_names_a_fixed_join_in_test_code (a synthetic source whose #[cfg(test)] line is followed by temp_dir().join('keel-x') and by temp_dir().join(format!('keel-k6-{tag}')) names both lines; a keel-cli/tests source names its fixed join with no #[cfg(test)] line at all); known-negative is cargo test --release --lib -- touched::tests::the_scratch_census_passes_per_process_joins_and_production_sites (scratch('keel-x'), temp_dir().join(format!('keel-x-{}', std::process::id())), a gen_uuid() interpolation, and a fixed join above the #[cfg(test)] line all pass). The real-tree census is touched::tests::no_test_names_a_scratch_directory_two_processes_could_share."; }
    // RAN: LADDER: KEEL verify . -> outcome=pass
    part unitTestScratchIsPerProcessStandupGateR1 : TestResult { :>> id = "c3668a83-3819-40fa-bfb1-78202218d90e"; :>> outcome = VerdictKind::proposed; :>> judgedAgainst = "1ecbef0"; :>> judgedAt = "2026-09-16"; :>> judgedBy = "claudeFable5"; }
    verification unitTestScratchIsPerProcessImplementGate : Test { :>> id = "de626cc8-4aaf-4d6c-99d8-2447f76de3a5"; :>> title = "Sprint 729 implement gate"; :>> createdAt = "2026-09-16"; :>> createdBy = "claudeFable5"; :>> method = VerificationMethod::test; :>> procedureText = "members/keel-fs/src/fsx.rs: pub fn scratch(tag: &str) -> PathBuf, temp_dir().join(format!('{tag}-{pid}')), with one unit test (two tags differ, one tag is stable within the process, the pid is in the name); members/keel-fs/src/lib.rs re-exports it. members/keel-actor/Cargo.toml: [dev-dependencies] keel-fs. Every fixed-name site in test code under keel-cli/src, keel-cli/tests and members/*/src rewritten to keel_fs::scratch(...) - a bare literal becomes scratch('lit'), a format! with no per-process token becomes scratch(&format!(...)). keel-cli/src/touched.rs: fixed_scratch_joins(source, always_test) returns the (line, text) pairs the census names; the three tests above; the walk reuses member_sources and adds keel-cli/src and keel-cli/tests."; }
    // RAN: LADDER: KEEL verify . -> outcome=pass
    part unitTestScratchIsPerProcessImplementGateR1 : TestResult { :>> id = "c849aa25-474c-426b-8556-c02d410c4d72"; :>> outcome = VerdictKind::pass; :>> judgedAgainst = "1ecbef0"; :>> judgedAt = "2026-09-16"; :>> judgedBy = "claudeFable5"; }
    verification unitTestScratchIsPerProcessReviewGate : Test { :>> id = "7b2803b1-532f-4ba8-a285-96d820637d8f"; :>> title = "Sprint 729 review gate — three passes per D0172"; :>> createdAt = "2026-09-16"; :>> createdBy = "claudeFable5"; :>> method = VerificationMethod::inspect; :>> procedureText = "Verifier receipt only: keel gate validate, check-engine, guard --no-receipt, sync-claude --check, the verify ladder with --probe naming the two touched::tests filters above, read back through keel verify --wait (D0497). The recorder for this sprint is dispatched with --owed 8 (D0492): six gates, the story DoD and the backlog DoD."; }
    // RAN: LADDER: KEEL verify . -> outcome=pass
    part unitTestScratchIsPerProcessReviewGateR1 : TestResult { :>> id = "76eddeac-338f-42e3-ab94-83706e6c2d75"; :>> outcome = VerdictKind::proposed; :>> judgedAgainst = "1ecbef0"; :>> judgedAt = "2026-09-16"; :>> judgedBy = "claudeFable5"; }
    verification unitTestScratchIsPerProcessCloseOutGate : Test { :>> id = "29359bd9-2a63-48c3-8b12-c9b7a7b824e3"; :>> title = "Sprint 729 closeOut gate (autonomous, D0049)"; :>> createdAt = "2026-09-16"; :>> createdBy = "claudeFable5"; :>> method = VerificationMethod::inspect; :>> procedureText = "Landed when the verifier's receipt reads DISCREPANCIES: NONE, the recorder's report passes check_report.py --owed 8, keel show verification . --pending shows the eight results on the tree, and the CI conclusion on the landed head is success."; }
    // RAN: LADDER: KEEL verify . -> outcome=pass
    part unitTestScratchIsPerProcessCloseOutGateR1 : TestResult { :>> id = "5a3cac7f-d54e-4fd6-8fde-c8ee68c7f434"; :>> outcome = VerdictKind::proposed; :>> judgedAgainst = "1ecbef0"; :>> judgedAt = "2026-09-16"; :>> judgedBy = "claudeFable5"; }
    verification unitTestScratchIsPerProcessRetroGate : Test { :>> id = "cbaafd97-d3d3-43b7-baac-ac1316221182"; :>> title = "Sprint 729 retro gate (autonomous, D0049)"; :>> createdAt = "2026-09-16"; :>> createdBy = "claudeFable5"; :>> method = VerificationMethod::analyze; :>> procedureText = "Avoidable issues scanned (issue011): issue570 was a convention applied by memory thirty-odd times with a dozen misses - the class D0047 names, and the correction is a helper plus a census that fails the lib set, not a sweep. Finding: three production sites name a stable scratch path on purpose (audit history's keel-audit, the report trend's keel-trend-<sha> worktrees, baseline-compare's keel-bl-<tag>-<sha> worktrees); two concurrent runs of the same command would `worktree remove --force` each other's checkout. Tracked as issue577 with resolver dcWorktreeScratchIsPerProcess. Finding: the census scopes test code as everything from a file's first bare #[cfg(test)] line, so a production fn below that line is scanned too - conservative, and no such site exists today; no new item. Finding: the first verifier dispatch named the D0388 pair as bare test functions, and a --probe side is a command line (verify.rs:210); the ladder refused at the probe rung with `program not found`, exit 2, after an 80-second climb, and the pair was re-dispatched as cargo test command lines. The refusal at the rung is the control and it held; no new item."; }
    // RAN: LADDER: KEEL verify . -> outcome=pass
    part unitTestScratchIsPerProcessRetroGateR1 : TestResult { :>> id = "c62fa99d-4773-44e3-8cfd-e18f90af4061"; :>> outcome = VerdictKind::proposed; :>> judgedAgainst = "1ecbef0"; :>> judgedAt = "2026-09-16"; :>> judgedBy = "claudeFable5"; }
}
