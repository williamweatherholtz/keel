// ProjectDeliveryS747 — Sprint 747: The sitting review is finished by analysis, not confirmation (D0510, accepted): the sprint-review skill records a method = analysis Test the AI judges with #Covers edges and the per-item asks listed by verb; sittingReviewVP leaves the act surface for assurance; sitting-coverage says `unpresented`, not `due`; guard `sitting-review-method` (the 77th) refuses a confirmation sitting review added after D0510. Resolves issue597. The human's words: 'change the method for finishing a review to not be confirmation. what should there be to confirm? on a sprint review' (2026-09-17). EXECUTE.. EXECUTE. 5 pts.
package ProjectDeliveryS747 {
    private import EngineElement::*;
    private import EngineWork::*;
    private import EngineVerification::*;
    private import EngineRelationships::*;

    #CharteredBy dependency from sittingReviewByAnalysisStory to d0510;
    #Delivers dependency from sittingReviewByAnalysisStory to dcSittingReviewIsFinishedByAnalysis;
    #Delivers dependency from sittingReviewByAnalysisStory to dcGuardReaderSkipsStringLiterals;

    part sittingReviewByAnalysisStory : Story {
        :>> id = "545c072f-fca7-43d0-8835-bcf8c89de4d4";
        :>> title = "Sprint 747: The sitting review is finished by analysis, not confirmation (D0510, accepted): the sprint-review skill records a method = analysis Test the AI judges with #Covers edges and the per-item asks listed by verb; sittingReviewVP leaves the act surface for assurance; sitting-coverage says `unpresented`, not `due`; guard `sitting-review-method` (the 77th) refuses a confirmation sitting review added after D0510. Resolves issue597. The human's words: 'change the method for finishing a review to not be confirmation. what should there be to confirm? on a sprint review' (2026-09-17). EXECUTE. (5 pts)";
        :>> createdAt = "2026-09-19"; :>> createdBy = "claudeFable5"; :>> kind = WorkKind::code; :>> priority = WorkPriority::p0; :>> owner = "claudeFable5"; :>> estimatedPoints = 5;
    }

    action def DeliveryRunS747 {
        action storySittingReviewByAnalysis;
        verification storySittingReviewByAnalysisDoD : Test { :>> id = "ca11f8b0-e7b8-401c-9feb-74696ea2f7c7"; :>> method = VerificationMethod::test; :>> procedureText = "DELIVERED BACKLOG ITEM: dcSittingReviewIsFinishedByAnalysis; also dcGuardReaderSkipsStringLiterals, the retro's finding (issue629) resolved in the same commit. DONE MEANS: the task's DoD passes as written - skill phase 4 and record shape say analysis judged by the AI actor, #Covers edges, asks by verb, no sentence asking the human to confirm the sitting; sittingReviewVP retired by a #Supersede edge from sittingReviewVP2 (surface assurance, the presented-concern; D0108, the old fact is claudeOpus5's) and a retired viewpoint dropped from surfaces_json; /api/obligations on a served copy returns no sittingReviewVP class; sitting-coverage keeps its numbers under `unpresented`/`unpresented_sprints`; the doc-sync rides the commit (usage.md row, skill registry, sprint-closeout sentences, CLI synopsis fact superseded per D0108, guards.md row, guard-constraints clause, control-map constraint); guard `sitting-review-method` green on the tree with its pre-D0510 confirmation Tests counted as one HISTORY line and red on a planted confirmation sittingRevProbe; `keel version` counts 77."; }
        // RAN: // RAN: ./target/release/keel-serve.exe verify . --probe-from C:/Users/WilliamWeatherholtz/AppData/Local/Temp/claude/C--Users-WilliamWeatherholtz-claude-code-sysmlv2-ai-toolkit/b43aa4fc-84f7-4c3d-bc35-61eccafbbda8/scratchpad/pair747.txt -> outcome=pass stopped_at=none seconds=969 at=1789810795 (1789810795>1789809822: ok) // RAN: outcome=pass passed=943 failed=0 seconds=850 at=1789810795 launch=1789809822 (1789810795>1789809822: ok)
        part storySittingReviewByAnalysisDoDR1 : TestResult { :>> id = "a2c5780d-babc-455e-aa5d-35946fbbd271"; :>> outcome = VerdictKind::pass; :>> judgedAgainst = "abe64e84"; :>> judgedAt = "2026-09-19"; :>> judgedBy = "claudeFable5"; }
    }

    verification sittingReviewByAnalysisRefineGate : Test { :>> id = "3113e2c9-0408-4e33-8e85-46af3de2e3ab"; :>> title = "Sprint 747 refine gate (DoR)"; :>> createdAt = "2026-09-19"; :>> createdBy = "claudeFable5"; :>> method = VerificationMethod::inspect; :>> procedureText = "DoR: one task, 5 points - a new guard family arm with a git-resolved boundary (a module with four tests), a viewpoint move, a key rename across the view, the serve counter, three Python readers and the brief's facts, a skill rewrite and its doc-sync. Charter d0510, accepted by the human with process-change marked, so the process-change guard's lock on the skill files and guard source is discharged by this record (D0465). No blocking dependency: D0510 is committed (its introduction commit resolves), issue597 names this task as resolver. The D0388 pair is two cargo test lines in pair747.txt, written before the tree was read."; }
    // RAN: verify . --probe-from pair747.txt -> outcome=pass stopped_at=none
    part sittingReviewByAnalysisRefineGateR1 : TestResult { :>> id = "f731f4f1-03c1-4150-9464-7d284ee39a4f"; :>> outcome = VerdictKind::proposed; :>> judgedAgainst = "abe64e84"; :>> judgedAt = "2026-09-19"; :>> judgedBy = "claudeFable5"; }
    verification sittingReviewByAnalysisStandupGate : Test { :>> id = "60b43141-c54a-458a-a230-79f89de4dddc"; :>> title = "Sprint 747 standup gate"; :>> createdAt = "2026-09-19"; :>> createdBy = "claudeFable5"; :>> method = VerificationMethod::inspect; :>> procedureText = "Owner claudeFable5. Blocker: none. Risk: the guard's population is `verification NAME : Test` blocks, so the 75 human Critiques the deck writes as sitting reviews are outside it by type and the three confirmation Tests are the counted history - stated in the DoD result rather than widened silently. A second risk: the CLI synopsis is a fact claudeOpus5 owns, so it is retired by a #Supersede edge beside a new fact, never edited (D0108); the cli-surface-declared guard holds facts = help = dispatch. The ladder runs detached; the verifier climbs it and writes the receipt."; }
    // RAN: verify . --probe-from pair747.txt -> outcome=pass stopped_at=none
    part sittingReviewByAnalysisStandupGateR1 : TestResult { :>> id = "ca1f6ee0-a699-4bcd-ae03-bccf81afcfed"; :>> outcome = VerdictKind::proposed; :>> judgedAgainst = "abe64e84"; :>> judgedAt = "2026-09-19"; :>> judgedBy = "claudeFable5"; }
    verification sittingReviewByAnalysisImplementGate : Test { :>> id = "5499cdb8-b428-4721-8669-761e2e094d8d"; :>> title = "Sprint 747 implement gate"; :>> createdAt = "2026-09-19"; :>> createdBy = "claudeFable5"; :>> method = VerificationMethod::test; :>> procedureText = "The implement gate is the change itself under the ladder: keel verify . --probe-from pair747.txt (validate, check-engine, guard with 77, clippy, the pair, suite --touched), stopping at the first red; plus /api/obligations read from a served copy with no sittingReviewVP class."; }
    // RAN: verify . --probe-from pair747.txt -> outcome=pass stopped_at=none
    part sittingReviewByAnalysisImplementGateR1 : TestResult { :>> id = "072e044c-0328-47c8-9787-a64c41cf6e51"; :>> outcome = VerdictKind::pass; :>> judgedAgainst = "abe64e84"; :>> judgedAt = "2026-09-19"; :>> judgedBy = "claudeFable5"; }
    verification sittingReviewByAnalysisReviewGate : Test { :>> id = "00f7f625-7154-430d-a28e-06196163fd26"; :>> title = "Sprint 747 review gate — three passes per D0172"; :>> createdAt = "2026-09-19"; :>> createdBy = "claudeFable5"; :>> method = VerificationMethod::inspect; :>> procedureText = "Verifier receipt read against the DoD: the guard passes on the tree and its four tests pass; the pair's positive and negative each exit 0; validate, check-engine, guard, clippy, sync-claude --check clean; three passes per D0172 (substance: the skill, the viewpoint, the view keys, the guard; ceremony: this record, the DoD result with its RAN receipt, the gates; doc-sync: usage.md, guards.md, guard-constraints, control-map, the registry purpose, the closeout skill, the CLI fact)."; }
    // RAN: verify . --probe-from pair747.txt -> outcome=pass stopped_at=none
    part sittingReviewByAnalysisReviewGateR1 : TestResult { :>> id = "a2d3e89a-68eb-4bc9-b2aa-b5170b2ddd72"; :>> outcome = VerdictKind::proposed; :>> judgedAgainst = "abe64e84"; :>> judgedAt = "2026-09-19"; :>> judgedBy = "claudeFable5"; }
    verification sittingReviewByAnalysisCloseOutGate : Test { :>> id = "ae0c0e08-f274-4c62-9c21-3aa760e39998"; :>> title = "Sprint 747 closeOut gate (autonomous, D0049)"; :>> createdAt = "2026-09-19"; :>> createdBy = "claudeFable5"; :>> method = VerificationMethod::inspect; :>> procedureText = "Landed by keel land with the touched set green and CI concluding success at the landing commit; issue597 resolves by its #Resolves edge to dcSittingReviewIsFinishedByAnalysis, read from keel show open-issues; the act tab of a served copy no longer counts sittings."; }
    // RAN: verify . --probe-from pair747.txt -> outcome=pass stopped_at=none
    part sittingReviewByAnalysisCloseOutGateR1 : TestResult { :>> id = "c920b9cf-d0b2-4ad3-ab52-447d0a099bf6"; :>> outcome = VerdictKind::proposed; :>> judgedAgainst = "abe64e84"; :>> judgedAt = "2026-09-19"; :>> judgedBy = "claudeFable5"; }
    verification sittingReviewByAnalysisRetroGate : Test { :>> id = "51d6571a-100a-42fc-9de8-4fc7da3068e3"; :>> title = "Sprint 747 retro gate (autonomous, D0049)"; :>> createdAt = "2026-09-19"; :>> createdBy = "claudeFable5"; :>> method = VerificationMethod::analyze; :>> procedureText = "Written at closeOut, after the verifier's receipt and before the recorder; avoidable issues scanned (issue011), each finding a tracked item or the reason it is not. Finding 1, tracked and resolved here: the new guard's reader declared_tests decided confirmation, title and block end from raw text including string literals; the first draft of this very sentence quoted VerificationMethod::confirmation (as this one does, so the tree itself carries the known-positive) and the guard went red on this retro gate (its name matches sittingRev), reproducing the finding live - issue629, resolver dcGuardReaderSkipsStringLiterals, both added in this commit, the resolver delivered in it: the reader masks string literals (block_and_mask, masked_field) and two tests hold the D0388 pair. Finding 2, no item: sittingReviewVP was first edited in place though claudeOpus5 owns it; the ownership guard named the edit and D0108 before the ladder climbed, the edit was reverted and sittingReviewVP2 with a #Supersede edge authored instead, and surfaces_json now drops a retired viewpoint with a unit test - the control that caught it exists and fired, so no new item. Finding 3, no item: the verifier's ladder stopped at guard on two reds of my own making (retro-backlog, ownership) and had to be re-dispatched; that is the ladder doing its job, not a defect in it."; }
    // RAN: verify . --probe-from pair747.txt -> outcome=pass stopped_at=none
    part sittingReviewByAnalysisRetroGateR1 : TestResult { :>> id = "aabea767-12ef-45f9-88d3-0204097ec5ce"; :>> outcome = VerdictKind::proposed; :>> judgedAgainst = "abe64e84"; :>> judgedAt = "2026-09-19"; :>> judgedBy = "claudeFable5"; }
}
