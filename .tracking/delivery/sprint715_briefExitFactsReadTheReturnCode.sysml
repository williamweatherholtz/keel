// ProjectDeliveryS715 — Sprint 715: Every fact the decision brief publishes under a name that asserts an exit reads the exit code, and the sensor carries its own probe pair (dcBriefExitFactsReadTheReturnCode, issue553, D0359). EXECUTE. 1 pts.
package ProjectDeliveryS715 {
    private import EngineElement::*;
    private import EngineWork::*;
    private import EngineVerification::*;
    private import EngineRelationships::*;

    #CharteredBy dependency from briefExitFactsReadTheReturnCodeStory to d0359;

    part briefExitFactsReadTheReturnCodeStory : Story {
        :>> id = "50fad6d4-386b-4be4-880a-2abf89e0523b";
        :>> title = "Sprint 715: Every fact the decision brief publishes under a name that asserts an exit reads the exit code, and the sensor carries its own probe pair (dcBriefExitFactsReadTheReturnCode, issue553, D0359) (1 pts)";
        :>> createdAt = "2026-09-14"; :>> createdBy = "claudeFable5"; :>> kind = WorkKind::code; :>> priority = WorkPriority::p0; :>> owner = "claudeFable5"; :>> estimatedPoints = 1;
    }

    action def DeliveryRunS715 {
        action storyBriefExitFactsReadTheReturnCode;
        verification storyBriefExitFactsReadTheReturnCodeDoD : Test { :>> id = "3e5b1fce-f92e-4be2-bd82-ba1affb65102"; :>> method = VerificationMethod::test; :>> procedureText = "DELIVERED: scripts/exec_brief/facts.py carries run_rc (returncode, stdout); the four exit0 / probeExit0 facts (cliReferenceProcedure.gateLinesRun, recorderCheckerLive.perFixture and probeExit0, cliSurfaceLive) read rc == 0; before any fact is computed facts.py runs the D0388 pair on the sensor - a python -c that prints and exits 1 reads rc 1, one that prints and exits 0 reads rc 0 - and a source scan refuses any exit0 or probeExit0 key assigned from an ok flag; either failing refuses the whole emission. VERIFY: facts.py complete=true at 130675d with recorderCheckerLive.perFixture exit0 false for each positive-* fixture and true for each negative-*; check_report.py on a positive fixture exits 1 by hand; the source-scan regex probed on the four old shapes (each caught) and the four new (each clean) before the live source was read (0 matches); the twenty-sixth builder passes its D0473 block and check_templates --brief is clean."; }
        // RAN: // RAN: python scripts/exec_brief/facts.py (repo root, 130675d) -> exit 0, complete=true, 200 facts; recorderCheckerLive.perFixture exit0: positive-undeclared-marker false, positive-sprint703-textpatch-write false, positive-sprint703-retro-recorded-twice false, negative-sprint647-receipt-driven true, negative-sprint703-record-only true; python check_report.py <positive-sprint703-textpatch-write> --root . -> exit 1 by hand; source-scan pair probed before the tree was read: the four old shapes ('exit0': _ok / bool(_fok) / bool(ok), 'probeExit0': bool(ok)) each caught, the four new shapes (_rc == 0 ...) each clean, live source 0 matches; runtime pair: python -c print+exit 1 -> rc 1, print+exit 0 -> rc 0 (facts.py refuses to emit otherwise); build_2026_09_14_facts_in_force_layering_build_skill.py -> wrote decision-brief.html, check_templates --brief clean
        part storyBriefExitFactsReadTheReturnCodeDoDR1 : TestResult { :>> id = "dc804822-0b2b-4fab-a69d-a2a1f571c75c"; :>> outcome = VerdictKind::pass; :>> judgedAgainst = "130675d"; :>> judgedAt = "2026-09-14"; :>> judgedBy = "claudeFable5"; }
    }

    verification briefExitFactsReadTheReturnCodeRefineGate : Test { :>> id = "f86ca25e-c233-49de-a3ff-5b39edeefac2"; :>> title = "Sprint 715 refine gate (DoR)"; :>> createdAt = "2026-09-14"; :>> createdBy = "claudeFable5"; :>> method = VerificationMethod::inspect; :>> procedureText = "READY. A correction found by the twenty-sixth builder's own refusal, not the frontier: the fact's name said exit0 and its how said produced-stdout. Sized 1: one helper, four call sites, a probe, a scan. Chartered by D0359 (the page is the channel; its numbers are computed, and a computed number whose name lies is the failure the page exists to prevent)."; }
    // RAN: // RAN: keel show whats-next . -> dcBriefExitFactsReadTheReturnCode was not on the frontier; it is a correction the twenty-sixth builder refused into existence; git diff --stat scripts/exec_brief/facts.py -> one file; estimatedPoints 1 recorded on the Story; #CharteredBy d0359 authored by record sprint
    part briefExitFactsReadTheReturnCodeRefineGateR1 : TestResult { :>> id = "c1603266-7d92-4f96-a8e8-386ef34c65da"; :>> outcome = VerdictKind::proposed; :>> judgedAgainst = "130675d"; :>> judgedAt = "2026-09-14"; :>> judgedBy = "claudeFable5"; }
    verification briefExitFactsReadTheReturnCodeStandupGate : Test { :>> id = "78748512-11c9-4b78-b814-511280b9a972"; :>> title = "Sprint 715 standup gate"; :>> createdAt = "2026-09-14"; :>> createdBy = "claudeFable5"; :>> method = VerificationMethod::inspect; :>> procedureText = "Blockers: none. facts.py is a script under scripts/, not a locked surface; no schema, process or enforcement file moves, so no marked Decision is owed (NOT A PROCESS CHANGE: a sensor inside the brief's builder is corrected, the process that publishes the brief is unchanged)."; }
    // RAN: // RAN: git status -sb at 130675d -> facts.py, the twenty-sixth builder, backlog.sysml, issues-claudeFable5.sysml, 0484 modified; none under .engine/schema, .engine/processes, .githooks or .github; no marked Decision owed
    part briefExitFactsReadTheReturnCodeStandupGateR1 : TestResult { :>> id = "847b74fa-c063-4093-bb8b-9c8db18ce5f8"; :>> outcome = VerdictKind::proposed; :>> judgedAgainst = "130675d"; :>> judgedAt = "2026-09-14"; :>> judgedBy = "claudeFable5"; }
    verification briefExitFactsReadTheReturnCodeImplementGate : Test { :>> id = "6fb0b3d5-d126-4666-bc36-981a991f6c1a"; :>> title = "Sprint 715 implement gate"; :>> createdAt = "2026-09-14"; :>> createdBy = "claudeFable5"; :>> method = VerificationMethod::test; :>> procedureText = "facts.py: run_rc added beside run (same exception handling, returns the real return code); the four sites rewritten to rc == 0; startup probe pair and source scan added between run_rc and as_json. Also corrected on the way, each at the root and each read from the tree rather than typed: the checker's REFUSED first line is `check_report: REFUSED (N):`, the recorderRefusalIssue resolver sits in EngineBuild (232 of 346) not NextWork, and sprint 704's seven results read 2 pass 5 proposed, not 7 pass - the builder now reads all three from facts."; }
    // RAN: // RAN: python scripts/exec_brief/facts.py (repo root, 130675d) -> exit 0, complete=true, 200 facts; grep -c 'run_rc' scripts/exec_brief/facts.py -> 4 call sites + definition + 2 probe calls; grep -nE '/'(exit0|probeExit0)/':' scripts/exec_brief/facts.py -> every site reads _rc == 0 / _frc == 0 / _probe_rc == 0; python scripts/exec_brief/build_2026_09_14_facts_in_force_layering_build_skill.py facts.json prev.html out.html -> wrote decision-brief.html; python scripts/check_templates.py --brief decision-brief.html -> clean
    part briefExitFactsReadTheReturnCodeImplementGateR1 : TestResult { :>> id = "60f2d349-600f-4e0b-a881-5471471eface"; :>> outcome = VerdictKind::pass; :>> judgedAgainst = "130675d"; :>> judgedAt = "2026-09-14"; :>> judgedBy = "claudeFable5"; }
    verification briefExitFactsReadTheReturnCodeReviewGate : Test { :>> id = "74a1af79-5818-47b7-944c-9416e2ee1274"; :>> title = "Sprint 715 review gate — three passes per D0172"; :>> createdAt = "2026-09-14"; :>> createdBy = "claudeFable5"; :>> method = VerificationMethod::inspect; :>> procedureText = "Pass 1 (intent): each DoD VERIFY clause is a command that was run and is quoted in the DoD result's RAN receipt. Pass 2 (defects): the source-scan regex was probed positive-then-negative on the four old and four new shapes before the live source was scanned (D0388); the runtime pair runs on every facts.py start. Pass 3 (residual): run() itself still answers ok=True for a printing failure - callers that mean 'produced output' keep it; only names that assert an exit are held to run_rc, which is what the scan enforces."; }
    // RAN: // RAN: three passes read against the diff of scripts/exec_brief/facts.py; source-scan regex probed by hand: four old shapes ('exit0': _ok / bool(_fok) / bool(ok) / 'probeExit0': bool(ok)) each matched, four new shapes (_rc == 0 forms) each clean, live source 0 matches; residual named: run() keeps ok=True for a printing failure by design for produced-output callers
    part briefExitFactsReadTheReturnCodeReviewGateR1 : TestResult { :>> id = "63e691ad-1d63-4233-a290-4887df60589c"; :>> outcome = VerdictKind::proposed; :>> judgedAgainst = "130675d"; :>> judgedAt = "2026-09-14"; :>> judgedBy = "claudeFable5"; }
    verification briefExitFactsReadTheReturnCodeCloseOutGate : Test { :>> id = "c18748b2-2346-4a65-be25-fc2433c02ac8"; :>> title = "Sprint 715 closeOut gate (autonomous, D0049)"; :>> createdAt = "2026-09-14"; :>> createdBy = "claudeFable5"; :>> method = VerificationMethod::inspect; :>> procedureText = "A fact named exit0 now measures an exit. The one control that caught this was the builder's cross-check against a page sentence; the sensor now refuses on its own before a page is built."; }
    // RAN: // RAN: keel gate --fast . after the sprint record -> reading below; keel gate guard --no-receipt . -> sprint-coverage PASS is the closeOut condition (read back after this write)
    part briefExitFactsReadTheReturnCodeCloseOutGateR1 : TestResult { :>> id = "edef2fce-cdc2-40bb-ac57-715f76022998"; :>> outcome = VerdictKind::proposed; :>> judgedAgainst = "130675d"; :>> judgedAt = "2026-09-14"; :>> judgedBy = "claudeFable5"; }
    verification briefExitFactsReadTheReturnCodeRetroGate : Test { :>> id = "d3c8c4c4-41c7-4846-9dc2-72dd495d4b7f"; :>> title = "Sprint 715 retro gate (autonomous, D0049)"; :>> createdAt = "2026-09-14"; :>> createdBy = "claudeFable5"; :>> method = VerificationMethod::analyze; :>> procedureText = "Retro held; avoidable-issue scan: the same class as issue533 (a claim recorded without the read that would establish it) - here the claim was a fact's NAME. Three more typed shapes were found by the builder's refusals in the same pass (the REFUSED first line, the resolver's def, the sprint-704 outcomes), all typed in the unpublished twenty-fifth builder and never observed against the tree: a builder assertion authored without a build is a claim without its check. Already tracked: D0388 (probe before the answer) covers the sensor; the typed-shape class has no control yet beyond the builder's refusal at build time, which is late but does fire - no new item, the refusal IS the control and it held four times today."; }
    // RAN: // RAN: keel show open-issues . -> issue553 resolver dcBriefExitFactsReadTheReturnCode done; avoidable-issue scan against issue533 class; no new item: the builder refusal at build time is the standing control for typed builder assertions and fired four times in this pass
    part briefExitFactsReadTheReturnCodeRetroGateR1 : TestResult { :>> id = "87fb8db1-2985-49f5-83cf-39e9b129bac7"; :>> outcome = VerdictKind::proposed; :>> judgedAgainst = "130675d"; :>> judgedAt = "2026-09-14"; :>> judgedBy = "claudeFable5"; }
}
