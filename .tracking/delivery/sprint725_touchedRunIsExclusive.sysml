// ProjectDeliveryS725 — Sprint 725: Sprint 725: dcTouchedRunIsExclusive, the correction for issue569 - sprint 724's verifier launched the verify ladder twice two seconds apart, nothing refused the second launch, and the two touched runs raced on the receipt rename and the lib tests' fixed scratch dirs into five reds no single run produces. The D0387 running stub now names its writer (pid), and keel suite --touched, keel land's touched run and keel verify refuse a second launch (exit 2, nothing written, no cargo started) while that process is alive; a dead writer's stub is replaced (D0493).. EXECUTE. 2 pts.
package ProjectDeliveryS725 {
    private import EngineElement::*;
    private import EngineWork::*;
    private import EngineVerification::*;
    private import EngineRelationships::*;

    #CharteredBy dependency from touchedRunIsExclusiveStory to d0493;

    part touchedRunIsExclusiveStory : Story {
        :>> id = "b662827f-4b11-4fd3-9d0a-47acf42fccda";
        :>> title = "Sprint 725: Sprint 725: dcTouchedRunIsExclusive, the correction for issue569 - sprint 724's verifier launched the verify ladder twice two seconds apart, nothing refused the second launch, and the two touched runs raced on the receipt rename and the lib tests' fixed scratch dirs into five reds no single run produces. The D0387 running stub now names its writer (pid), and keel suite --touched, keel land's touched run and keel verify refuse a second launch (exit 2, nothing written, no cargo started) while that process is alive; a dead writer's stub is replaced (D0493). (2 pts)";
        :>> createdAt = "2026-09-15"; :>> createdBy = "claudeFable5"; :>> kind = WorkKind::code; :>> priority = WorkPriority::p0; :>> owner = "claudeFable5"; :>> estimatedPoints = 2;
    }

    action def DeliveryRunS725 {
        action storyTouchedRunIsExclusive;
        verification storyTouchedRunIsExclusiveDoD : Test { :>> id = "004698d2-3012-4e7e-a13d-e8d3aaa09c8b"; :>> method = VerificationMethod::test; :>> procedureText = "DELIVERED BACKLOG ITEMS: dcTouchedRunIsExclusive. DONE MEANS: the running stub of .keel/metrics/touched-receipt.toml and .keel/metrics/verify-receipt.toml carries pid; touched::run() reads the receipt on disk before its first write and returns Err (keel suite --touched exits 2, keel land refuses to push) while it says running and the pid is alive, naming the pid, its at and its log; verify::cmd does the same against its own receipt before its first stub. A stub whose pid is gone, a stub from before the pid rode it, and a finished receipt refuse nothing. D0493 (non-fork, accepted under standing consent) is co-committed; both help texts name the refusal. Resolves issue569. VERIFIED BY: the D0388 pair in touched.rs (a_second_launch_is_refused_while_the_stub_writer_is_alive - this process's own pid, the real pid_alive; a_stub_whose_writer_is_gone_is_replaced - a spawned-and-exited child's pid) and its twin in verify.rs; the live check on the built binary - a stub naming a live pid, keel suite --touched exits 2 with the refusal line, the stub unchanged, zero cargo processes; cargo clippy --release --all-targets -D warnings clean; the verify ladder green."; }
        // RAN: TOUCHED RECEIPT: outcome=pass passed=865 failed=0
        part storyTouchedRunIsExclusiveDoDR1 : TestResult { :>> id = "78ed0b8d-5c4a-4677-a80c-c7e6d065c676"; :>> outcome = VerdictKind::pass; :>> judgedAgainst = "ea02af5"; :>> judgedAt = "2026-09-15"; :>> judgedBy = "claudeFable5"; }
    }

    verification touchedRunIsExclusiveRefineGate : Test { :>> id = "ddef30e7-835e-4dc3-a044-183a77681392"; :>> title = "Sprint 725 refine gate (DoR)"; :>> createdAt = "2026-09-15"; :>> createdBy = "claudeFable5"; :>> method = VerificationMethod::inspect; :>> procedureText = "Chartered by D0493 (accepted under standing consent d0207 - a non-fork: the lock-file alternative is the same fact with a second home) which extends D0387's running stub with the writer's pid. One backlog item, ranked first on the frontier by the sprint 724 retro (issue569, High). 2 points: two Rust modules gain a field, a pure control, a host read and a launch refusal, with the D0388 pair in each; a Decision."; }
    // RAN: validate=pass
    part touchedRunIsExclusiveRefineGateR1 : TestResult { :>> id = "a692d04e-01db-4196-98d3-211975642dc2"; :>> outcome = VerdictKind::proposed; :>> judgedAgainst = "ea02af5"; :>> judgedAt = "2026-09-15"; :>> judgedBy = "claudeFable5"; }
    verification touchedRunIsExclusiveStandupGate : Test { :>> id = "0d628196-ce8c-40fa-ab38-44c87518bb04"; :>> title = "Sprint 725 standup gate"; :>> createdAt = "2026-09-15"; :>> createdBy = "claudeFable5"; :>> method = VerificationMethod::inspect; :>> procedureText = "Owner claudeFable5. Blocker: none - the change is in keel-cli only; keel-serve.exe is rebuilt from the build. The D0388 pair is stated before the tree is read: known-positive is a running stub naming this process's own pid, refused naming the pid and at; known-negative is a running stub naming a spawned-and-exited child's pid, the launch proceeds and the stub is replaced. Host note for the live check: tasklist's /FI is path-mangled under git-bash (the first live attempt planted a stub with no pid, was not refused, and started cargo - killed; the second used a pid read from the plain tasklist listing and was refused as designed)."; }
    // RAN: guard=pass
    part touchedRunIsExclusiveStandupGateR1 : TestResult { :>> id = "587ffbf3-8dcb-4773-aa69-0a5bdf5853a3"; :>> outcome = VerdictKind::proposed; :>> judgedAgainst = "ea02af5"; :>> judgedAt = "2026-09-15"; :>> judgedBy = "claudeFable5"; }
    verification touchedRunIsExclusiveImplementGate : Test { :>> id = "eea1b596-21b9-4339-b696-8049993b5ce5"; :>> title = "Sprint 725 implement gate"; :>> createdAt = "2026-09-15"; :>> createdBy = "claudeFable5"; :>> method = VerificationMethod::test; :>> procedureText = "touched.rs: Phase::Running { pid }; render writes pid = N; pid_alive (tasklist on Windows, /proc or kill -0 elsewhere; 0 never alive); LiveRun + live_run_in read a stub back; exclusive_refusal(text, alive) is the pure control; run() returns Err(refusal) before nothing_to_run and before any write, so cmd exits 2 and after_gate refuses the push with the line. verify.rs: Ladder.pid rendered after running and parsed with 0 as the pre-pid default; exclusive_refusal(text, alive) over parse_receipt; cmd refuses exit 2 before the first stub. suite.rs and verify.rs help texts name the refusal. Tests: the two pairs plus the stub round-trip tests asserting pid; 31 touched/verify lib tests pass. D0493 recorded via record decision --from, accepted under d0207."; }
    // RAN: clippy=pass
    part touchedRunIsExclusiveImplementGateR1 : TestResult { :>> id = "0b873656-d2a4-4ee3-a04b-56803fd3a7e1"; :>> outcome = VerdictKind::pass; :>> judgedAgainst = "ea02af5"; :>> judgedAt = "2026-09-15"; :>> judgedBy = "claudeFable5"; }
    verification touchedRunIsExclusiveReviewGate : Test { :>> id = "7ca13868-e292-4e8a-8d96-4ebcb8b98a15"; :>> title = "Sprint 725 review gate — three passes per D0172"; :>> createdAt = "2026-09-15"; :>> createdBy = "claudeFable5"; :>> method = VerificationMethod::inspect; :>> procedureText = "Verifier receipt only: keel gate validate, check-engine, guard --no-receipt, sync-claude --check, the verify ladder with --probe naming the two lib tests of the touched.rs pair, run once. The recorder for this sprint is dispatched with --owed 7 (D0492)."; }
    // RAN: probe=pass positive: pass; negative: pass
    part touchedRunIsExclusiveReviewGateR1 : TestResult { :>> id = "2c6045fb-0899-46c1-a300-a915b203b7b6"; :>> outcome = VerdictKind::proposed; :>> judgedAgainst = "ea02af5"; :>> judgedAt = "2026-09-15"; :>> judgedBy = "claudeFable5"; }
    verification touchedRunIsExclusiveCloseOutGate : Test { :>> id = "d35d5b0f-53d0-4591-b7f2-e67f0027470f"; :>> title = "Sprint 725 closeOut gate (autonomous, D0049)"; :>> createdAt = "2026-09-15"; :>> createdBy = "claudeFable5"; :>> method = VerificationMethod::inspect; :>> procedureText = "Landed when the verifier's receipt reads DISCREPANCIES: NONE, the recorder's report passes check_report.py --owed 7, and keel show verification . --pending shows the seven results on the tree."; }
    // RAN: touched=pass passed=865 failed=0
    part touchedRunIsExclusiveCloseOutGateR1 : TestResult { :>> id = "fd871716-3356-4211-a9fc-e58f0b538956"; :>> outcome = VerdictKind::proposed; :>> judgedAgainst = "ea02af5"; :>> judgedAt = "2026-09-15"; :>> judgedBy = "claudeFable5"; }
    verification touchedRunIsExclusiveRetroGate : Test { :>> id = "7f28b443-7487-422d-8e07-e11022df2824"; :>> title = "Sprint 725 retro gate (autonomous, D0049)"; :>> createdAt = "2026-09-15"; :>> createdBy = "claudeFable5"; :>> method = VerificationMethod::analyze; :>> procedureText = "Avoidable issues scanned (issue011): the finding this sprint corrects (issue569) was found by reading two task outputs with different totals, not by any control - the stub named no writer. The correction puts the writer's pid in the stub and the refusal at the launch. One residual, already tracked: issue570 - the lib tests' fixed scratch directories are the second half of the same race and remain shared until dcUnitTestScratchIsPerProcess, next on the frontier; the launch refusal covers two keel runs, not a keel run beside a bare cargo test. One finding from this sprint's own work: the first live probe planted a stub with an EMPTY pid because git-bash rewrote tasklist's /FI flag as a path, the stub was rightly not refused (no writer named), and cargo started under a 60-second timeout - the control behaved as specified and the probe was the fault; no new item, the standup names the host rule (read the pid from the plain tasklist listing). No new item."; }
    // RAN: first red line: none
    part touchedRunIsExclusiveRetroGateR1 : TestResult { :>> id = "f4e0812b-22a4-4507-aa90-251a54dcfc90"; :>> outcome = VerdictKind::proposed; :>> judgedAgainst = "ea02af5"; :>> judgedAt = "2026-09-15"; :>> judgedBy = "claudeFable5"; }
}
