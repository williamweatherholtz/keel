// ProjectDeliveryS740 — Sprint 740: the shared helpers descend below the verbs - dcSharedHelpersDescendBelowTheVerbs, the tenth D0479 extraction and the second slice of dcKeelCliIsThinDispatch, chartered by D0479. Before this sprint no cmd_ body could leave keel-cli: each reached project discovery (keel-process), the hook ledger writers (keel-hooks), fork detection (keel-serve), walk_longest (a pub fn of keel-cli's own lib.rs) or the nine private argument helpers of main.rs. scripts/verb_homes.py is written to measure that claim - for every top-level item of main.rs, the members its body reaches and the least member that could hold it - and scripts/extract_seams.py moves the five seams: project discovery to keel_git::projects (keel_process::workspace keeps the gate and re-exports the names), the ledger writers and the slow-fire threshold to keel_write::ledger (keel-hooks drops keel-process), fork detection to keel_model::textscan (deck re-exports), walk_longest to keel-fs, and the argument helpers to a new member keel-args that depends on keel-git alone. D0512 records the placement rule (a helper every verb shares lives in the lowest member that reaches what it needs) and reverses D0511's clause that put discovery in the process layer and the ledger writers in keel-hooks; the rest of D0511 stands.. EXECUTE. 5 pts.
package ProjectDeliveryS740 {
    private import EngineElement::*;
    private import EngineWork::*;
    private import EngineVerification::*;
    private import EngineRelationships::*;

    #CharteredBy dependency from sharedHelpersDescendBelowTheVerbsStory to d0479;
    #Delivers dependency from sharedHelpersDescendBelowTheVerbsStory to dcSharedHelpersDescendBelowTheVerbs;

    part sharedHelpersDescendBelowTheVerbsStory : Story {
        :>> id = "cd9bce9a-beee-4160-87b2-79ac880a027a";
        :>> title = "Sprint 740: the shared helpers descend below the verbs - dcSharedHelpersDescendBelowTheVerbs, the tenth D0479 extraction and the second slice of dcKeelCliIsThinDispatch, chartered by D0479. Before this sprint no cmd_ body could leave keel-cli: each reached project discovery (keel-process), the hook ledger writers (keel-hooks), fork detection (keel-serve), walk_longest (a pub fn of keel-cli's own lib.rs) or the nine private argument helpers of main.rs. scripts/verb_homes.py is written to measure that claim - for every top-level item of main.rs, the members its body reaches and the least member that could hold it - and scripts/extract_seams.py moves the five seams: project discovery to keel_git::projects (keel_process::workspace keeps the gate and re-exports the names), the ledger writers and the slow-fire threshold to keel_write::ledger (keel-hooks drops keel-process), fork detection to keel_model::textscan (deck re-exports), walk_longest to keel-fs, and the argument helpers to a new member keel-args that depends on keel-git alone. D0512 records the placement rule (a helper every verb shares lives in the lowest member that reaches what it needs) and reverses D0511's clause that put discovery in the process layer and the ledger writers in keel-hooks; the rest of D0511 stands. (5 pts)";
        :>> createdAt = "2026-09-18"; :>> createdBy = "claudeFable5"; :>> kind = WorkKind::code; :>> priority = WorkPriority::p0; :>> owner = "claudeFable5"; :>> estimatedPoints = 5;
    }

    action def DeliveryRunS740 {
        action storySharedHelpersDescendBelowTheVerbs;
        verification storySharedHelpersDescendBelowTheVerbsDoD : Test { :>> id = "be70a863-496d-4aa9-a2eb-2ea6ad3151e3"; :>> method = VerificationMethod::test; :>> procedureText = "DELIVERED BACKLOG ITEMS: dcSharedHelpersDescendBelowTheVerbs. DONE MEANS: members/keel-git/src/projects.rs (386 lines) holds Workspace, is_project, missing_project_dirs, require_project, canon, discover, find_repo_root, engine_version_skew and the private walkers, and members/keel-process/src/workspace.rs (394 lines, from the gate plus re-exports) keeps cmd, gate_cmd, gate_problems, gate_outcome, gate_one, declared_rule_violations, unowned_keystone_events; members/keel-write/src/ledger.rs (126 lines) holds ledger_gate, ledger_refused, refused_injected_prose, ledger_line, ledger_actor_kind, SLOW_FIRE_MS and slow_fire_phases, keel-write gains keel-perf, keel-hooks re-exports the three the binary calls and no longer depends on keel-process, pm re-exports the threshold; fork_options, NOT_A_FORK, fork_signals, disguised_fork and their tests are in members/keel-model/src/textscan.rs and re-exported by keel_serve::deck; walk_longest is in members/keel-fs/src/lib.rs and re-exported by keel-cli's lib.rs; members/keel-args/src/lib.rs (293 lines, member lint preamble, Cargo.toml naming keel-git alone) holds the nine argument helpers as pub fns with root_arg's test, keel-cli's lib.rs re-exports keel_args as args and main.rs (4497 lines, from 4726) imports them by name. scripts/verb_homes.py (411 lines, # ci-probe: --probe) computes the least member per item under the rule that a member holds a crate it could add without widening its reach, labels the addition (+keel-args), and --check exits 1 naming exactly audit_subverb, cmd_audit and cmd_enroll on the applied tree. scripts/extract_seams.py (502 lines) is the idempotent transform: dry run reconciled 17 slices conserved out of 5 source files, 9 fns published, 2 orphaned docs reattached, 19 anchored edits in 16 staying files, 4 files written; re-run says already applied. cargo clippy --release --workspace --all-targets -D warnings clean; keel --help byte-identical to the pre-move render (cmp help_before740.txt, 15089 bytes); keel version's guard line unchanged (75: 66 hard-blocking, 9 warning-only); python scripts/modgraph.py --check (74 modules, 7 edges) and python scripts/module_home.py --probe hold and module_home names keel-git/projects.rs, keel-write/ledger.rs, keel-process/workspace.rs; no path under GUARD_SOURCE_FILES or GUARD_SOURCE_DIRS changes. Known-positive (pos740.py): verb_homes.py --check exits 1 naming exactly the three items that reach keel-cli's own modules. Known-negative (neg740.py): a pub use keel_process::workspace planted in members/keel-args/src/lib.rs fails cargo check -p keel-args naming the undeclared crate, lib.rs restored on every path. The DoD's known-positive was amended three times this sprint as the least-member rule was refined; the final text and the tree hold at every point."; }
        // RAN: TOUCHED RECEIPT: outcome=pass passed=874 failed=0
        part storySharedHelpersDescendBelowTheVerbsDoDR1 : TestResult { :>> id = "0bd5d673-b283-4a2e-89f7-53594f5dffaf"; :>> outcome = VerdictKind::pass; :>> judgedAgainst = "b93cb8de"; :>> judgedAt = "2026-09-17"; :>> judgedBy = "claudeFable5"; }
    }

    verification sharedHelpersDescendBelowTheVerbsRefineGate : Test { :>> id = "65544c9e-9afc-4d4c-a26c-3857fb5e8a10"; :>> title = "Sprint 740 refine gate (DoR)"; :>> createdAt = "2026-09-18"; :>> createdBy = "claudeFable5"; :>> method = VerificationMethod::inspect; :>> procedureText = "DoR: dcSharedHelpersDescendBelowTheVerbs was the first line of keel show whats-next at b93cb8de (sprint 739 landed, CI conclusion success), recorded there last sprint as the split of dcKeelCliIsThinDispatch, chartered by D0479 through its #CharteredBy edge, #DependsOn dcHooksAreAMember (done); dcTheFourStayingModulesAreMembers and dcKeelCliIsThinDispatch depend on it. Sized 5 - one measuring tool with a probe fixture, one codemod slicing five source files at seventeen anchored ranges, one new member, five re-export surfaces, the D0388 pair as two scripts and an unmarked Decision with a #SupersedeClause edge; no locked path changes. Not split further: the five seams are one claim (every cmd_ body has a member home) and the tool that measures it is only meaningful against all five. Blocking dependencies: none."; }
    // RAN: outcome=pass validate=pass guard=pass clippy=pass probe=pass touched=pass
    part sharedHelpersDescendBelowTheVerbsRefineGateR1 : TestResult { :>> id = "16d4178d-13f2-4e83-9fa8-2d27121189f3"; :>> outcome = VerdictKind::proposed; :>> judgedAgainst = "b93cb8de"; :>> judgedAt = "2026-09-17"; :>> judgedBy = "claudeFable5"; }
    verification sharedHelpersDescendBelowTheVerbsStandupGate : Test { :>> id = "65e6a18f-46c8-4426-b69c-c074abad535e"; :>> title = "Sprint 740 standup gate"; :>> createdAt = "2026-09-18"; :>> createdBy = "claudeFable5"; :>> method = VerificationMethod::inspect; :>> procedureText = "Owner claudeFable5. Blocker: none - b93cb8de landed with CI success, no ladder or land is running; the human's serve runs from the pin cache, so the release image rebuilds freely. Order: (1) scripts/verb_homes.py with its --probe fixture, run against HEAD to name the seams (every cmd_ body's least member was keel-cli, keel-hooks or keel-serve(+keel-hooks)). (2) scripts/extract_seams.py: slice the five seams out of workspace.rs, keel-hooks' lib.rs, deck.rs, pm.rs and main.rs, publish the fns main.rs still calls, write keel-args' manifest and lib.rs, projects.rs and ledger.rs, edit the manifests, re-exports and imports; dry-run reconciled, then --apply. (3) cargo check --workspace --all-targets, clippy, cargo build --release, keel --help against help_before740.txt, keel version, cargo test --lib for the nine touched members, modgraph --check, module_home --probe, verb_homes --check. (4) pos740/neg740; pair740.txt. (5) D0512 with --supersedes-clause d0511 and a #DependsOn edge to d0479, the DoD amendment, issue601 with its resolver, the sprint with the retro filled; verifier with the pair file; recorder --owed 8; land; CI conclusion. decision-surfacing: D0512 auto-accepts (non-fork, no marker), the pending set (15 ids) equals the page, silent."; }
    // RAN: outcome=pass validate=pass guard=pass clippy=pass probe=pass touched=pass
    part sharedHelpersDescendBelowTheVerbsStandupGateR1 : TestResult { :>> id = "bb4136cb-fb47-4c05-a61b-8e51e57df5d7"; :>> outcome = VerdictKind::proposed; :>> judgedAgainst = "b93cb8de"; :>> judgedAt = "2026-09-17"; :>> judgedBy = "claudeFable5"; }
    verification sharedHelpersDescendBelowTheVerbsImplementGate : Test { :>> id = "d890b576-cd8d-4178-b653-f14ab79debf4"; :>> title = "Sprint 740 implement gate"; :>> createdAt = "2026-09-18"; :>> createdBy = "claudeFable5"; :>> method = VerificationMethod::test; :>> procedureText = "The implement gate is the DoD's own probes plus the ladder: python scripts/verb_homes.py --probe 0 failures (19 checks); python scripts/extract_seams.py dry run reconciled (17 slices conserved out of 5 source files, 9 fns published, 2 orphaned docs reattached, 19 anchored edits in 16 staying files, 4 files written), --apply, re-run already applied; cargo check --workspace --all-targets Finished; cargo clippy --release --workspace --all-targets -- -D warnings exit 0; cargo build --release Finished (2m41s); cmp help_before740.txt help_after740.txt byte-identical (15089 bytes); keel version guards 75 (66 hard-blocking, 9 warning-only); python scripts/modgraph.py --check layering holds (74 modules, 7 edges); python scripts/module_home.py --probe 0 failures; cargo tree -p keel-hooks --depth 1 names no keel-process; cargo tree -p keel-args -e normal is keel-args, keel-git, keel-perf; cargo test --release --lib for keel-args (1), keel-fs (3), keel-git (10), keel-hooks (20), keel-model (56), keel-process (26), keel-serve (35), keel-view (162), keel-write (57) all ok; python pos740.py pass (exit 1, named audit_subverb, cmd_audit, cmd_enroll); python neg740.py pass (cargo check exit 101 naming keel_process, lib.rs restored); keel gate validate 855 clean with the amended DoDs and issue601 in the tree; keel gate check-engine clean with D0512, its #SupersedeClause edge to d0511 and #DependsOn edge to d0479. The least-member rule was refined three times against the applied tree before --check named three: the first draft counted only crates a member already reaches (69 named, keel-args a leaf nobody depended on), the second let a member add a crate that depends on it (keel-perf(+keel-git), a cycle), the third let the binary win every tie with zero additions; each refinement was written into the probe fixture first (the sibling fixture and the two-members-each-holding-a-dependency negative)."; }
    // RAN: outcome=pass validate=pass guard=pass clippy=pass probe=pass touched=pass
    part sharedHelpersDescendBelowTheVerbsImplementGateR1 : TestResult { :>> id = "bc3fc0e2-a418-4ccd-9074-68a993d5b37e"; :>> outcome = VerdictKind::pass; :>> judgedAgainst = "b93cb8de"; :>> judgedAt = "2026-09-17"; :>> judgedBy = "claudeFable5"; }
    verification sharedHelpersDescendBelowTheVerbsReviewGate : Test { :>> id = "0e7d347d-aca8-402e-85be-cb4ef97ccdb3"; :>> title = "Sprint 740 review gate — three passes per D0172"; :>> createdAt = "2026-09-18"; :>> createdBy = "claudeFable5"; :>> method = VerificationMethod::inspect; :>> procedureText = "Verifier receipt only: keel gate validate, check-engine, guard --no-receipt, sync-claude --check, the verify ladder with --probe-from naming this sprint's pair file (D0500), cargo clippy; the recorder writes this gate from the receipt. Three passes per D0172. Correctness: every moved test passes in its new crate (root_arg's in keel-args, the fork tests in keel-model, the walker tests in keel-git), every caller of a moved name resolves through a re-export (keel_process::workspace::, keel_cli::workspace::, keel_serve::deck::, keel_cli::walk_longest, keel_hooks::ledger_*) or main.rs's named import, and the binary's help and guard count are the pre-move ones. Honesty: the negative plants in keel-args' lib.rs and asserts the compiler names the crate the member must not know; the positive asserts the exact set --check names, not its count, so a helper added to main.rs that a verb shares would fail it as a fourth name; the pre-move claims in the DoD were read from a git archive of HEAD (head740), not remembered. Scope: no locked path is in the diff (GUARD_SOURCE_FILES and GUARD_SOURCE_DIRS in members/keel-guards/src/enforcement.rs unchanged, no moved file under them), no hook script, CI yml or rule edit, so D0512 carries no marker and accepted under standing consent - NOT A PROCESS CHANGE: every hook and verb fires the same body through a re-export."; }
    // RAN: outcome=pass validate=pass guard=pass clippy=pass probe=pass touched=pass
    part sharedHelpersDescendBelowTheVerbsReviewGateR1 : TestResult { :>> id = "b11de018-d4db-4c9e-a478-efcc9866c6b7"; :>> outcome = VerdictKind::proposed; :>> judgedAgainst = "b93cb8de"; :>> judgedAt = "2026-09-17"; :>> judgedBy = "claudeFable5"; }
    verification sharedHelpersDescendBelowTheVerbsCloseOutGate : Test { :>> id = "795dd111-70d9-4ea1-926c-fb4736c561d3"; :>> title = "Sprint 740 closeOut gate (autonomous, D0049)"; :>> createdAt = "2026-09-18"; :>> createdBy = "claudeFable5"; :>> method = VerificationMethod::inspect; :>> procedureText = "Landed when the verifier's receipt reads DISCREPANCIES: NONE and its probe rung row names pair740.txt, the recorder's report passes check_report.py --owed 8, git status -sb is clean after keel land and gh run list names the landing commit with conclusion success. The DoD result is recorded against dcSharedHelpersDescendBelowTheVerbsDoD at that sha; D0512 is accepted (non-fork, no marker), so the authority queue's pending set is unchanged and decision-surfacing is silent. dcTheFourStayingModulesAreMembers' #DependsOn edge to this item is satisfied when the DoD result lands; it moves history, adherence, cursor and enroll, after which verb_homes.py --check should exit 0 and dcKeelCliIsThinDispatch's amended DoD makes that its gate."; }
    // RAN: outcome=pass validate=pass guard=pass clippy=pass probe=pass touched=pass
    part sharedHelpersDescendBelowTheVerbsCloseOutGateR1 : TestResult { :>> id = "8c0f2aa9-ad2f-4331-a26e-c136d5e7b5a8"; :>> outcome = VerdictKind::proposed; :>> judgedAgainst = "b93cb8de"; :>> judgedAt = "2026-09-17"; :>> judgedBy = "claudeFable5"; }
    verification sharedHelpersDescendBelowTheVerbsRetroGate : Test { :>> id = "2a072bb8-844b-41be-92e0-a524bd7074d0"; :>> title = "Sprint 740 retro gate (autonomous, D0049)"; :>> createdAt = "2026-09-18"; :>> createdBy = "claudeFable5"; :>> method = VerificationMethod::analyze; :>> procedureText = "Written at close-out, before the verifier is dispatched; avoidable issues scanned (issue011), each finding a tracked item or the reason it is not. (1) Two more doc comments stranded by earlier slices (root_arg's in workspace.rs, cmd_init's above positional_arg) were reattached by hand in the transform - the second sprint running (739 reattached three and called it a one-off). Tracked: issue601, resolver dcKeelCliIsThinDispatch, whose DoD now says the transform's plan asserts no slice starts below a doc line or attribute and a fixture negative fails the dry run; rustdoc and clippy have no lint for a doc describing a different item, so the control is in the transform class that strands them. (2) The DoD's known-positive was amended three times in one sprint because it predicted the tool's counts (thirteen, then six) and the tool's rule changed under it. Not tracked as an Issue: the amendments were to my own not-done item (D0108) and the D0388 pair scripts, not the counts, were the control that had to pass; the shape to prefer is in the amended text - name the set the check names, not its size - and dcKeelCliIsThinDispatch's DoD written this sprint names exit codes and sets only. (3) The least-member rule needed three refinements (already-reaches only, acyclicity, the binary winning ties) before --check named three items; each was caught by the probe fixture or by a row of the real table (keel-perf(+keel-git)) that a reader could see was a cycle. Not tracked: the probe fixture is the control and it grew a case per refinement (sibling, the two-members negative); a fourth refinement would make it a pattern. (4) textscan's module doc said no filesystem while fork_options reads a file; fixed in the transform's rewrite of the doc. Not tracked: dual-truth in a comment with no lint, same class as 739's finding (4), and the moved fn now sits under a doc that says what it reads. (5) D0511 placed project discovery in the process layer and the ledger writers in keel-hooks one sprint before verb_homes.py existed to measure placement; D0512 reverses that clause with a #SupersedeClause edge and the rest of D0511 stands. Not tracked separately: the tool is now committed and its --check is the control; a placement Decision recorded before the tool ran is what D0388 (probe before the answer) already forbids, and dcKeelCliIsThinDispatch's DoD now cites the tool's table for every move. (6) verb_homes.py --check exits 1 on the tree and will until dcTheFourStayingModulesAreMembers lands, so it cannot be a CI gate yet and its # ci-probe marker runs only the fixture. Non-finding: the exit-0 gate is dcKeelCliIsThinDispatch's DoD, recorded this sprint, and the three named items are the next sprint's own seam. (7) issue601 was recorded with its resolver an existing item whose DoD was amended, rather than a new task appended at the end of EngineBuild - the issue600 shape (record task appends, then a hand move) was avoided by not recording a task. Non-finding, noted because it is a workaround for issue600 and not its fix."; }
    // RAN: outcome=pass validate=pass guard=pass clippy=pass probe=pass touched=pass
    part sharedHelpersDescendBelowTheVerbsRetroGateR1 : TestResult { :>> id = "9d7281ce-f699-493c-a208-2eae27ac907f"; :>> outcome = VerdictKind::proposed; :>> judgedAgainst = "b93cb8de"; :>> judgedAt = "2026-09-17"; :>> judgedBy = "claudeFable5"; }
}
