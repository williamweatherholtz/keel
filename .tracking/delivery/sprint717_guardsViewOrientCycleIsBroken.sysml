// ProjectDeliveryS717 — Sprint 717: The guards-view-orient cycles in keel-cli are broken so the next member boundaries (dcModelAndWriteAreMembers onward) can be drawn mechanically: a view runs no guard, the report and priority compositions sit above view and orient, the shared helpers sit in leaves below them, and scripts/modgraph.py --check is the instrument that says so (dcGuardsViewOrientCycleIsBroken, chartered by D0479, shape recorded as D0485).. EXECUTE. 3 pts.
package ProjectDeliveryS717 {
    private import EngineElement::*;
    private import EngineWork::*;
    private import EngineVerification::*;
    private import EngineRelationships::*;

    #CharteredBy dependency from guardsViewOrientCycleIsBrokenStory to d0479;

    part guardsViewOrientCycleIsBrokenStory : Story {
        :>> id = "ff59f1a1-8162-4e6c-af22-2588117ce215";
        :>> title = "Sprint 717: The guards-view-orient cycles in keel-cli are broken so the next member boundaries (dcModelAndWriteAreMembers onward) can be drawn mechanically: a view runs no guard, the report and priority compositions sit above view and orient, the shared helpers sit in leaves below them, and scripts/modgraph.py --check is the instrument that says so (dcGuardsViewOrientCycleIsBroken, chartered by D0479, shape recorded as D0485). (3 pts)";
        :>> createdAt = "2026-09-14"; :>> createdBy = "claudeFable5"; :>> kind = WorkKind::code; :>> priority = WorkPriority::p0; :>> owner = "claudeFable5"; :>> estimatedPoints = 3;
    }

    action def DeliveryRunS717 {
        action storyGuardsViewOrientCycleIsBroken;
        verification storyGuardsViewOrientCycleIsBrokenDoD : Test { :>> id = "f9db466f-152b-46a1-80b3-1855e2755aa4"; :>> method = VerificationMethod::test; :>> procedureText = "scripts/modgraph.py --check reports zero references from view, orient, write or scaffold into guards and zero from view into orient (known-positive, chosen before the tree was read); a fixture with one view -> guards reference is reported naming both ends and its file:line (known-negative, probe-neg.sh); the touched test set passes; keel --help is byte-identical to the pre-change binary; the guard count line of keel version is unchanged."; }
        // RAN: // RAN: DoD for dcGuardsViewOrientCycleIsBroken at 6a22002 (2026-09-14), working tree. keel verify . --probe 'python scripts/modgraph.py --check,sh probe-neg.sh' --no-receipt from target/release/keel-verify.exe (run 4, scratchpad s717/verify4.log): validate pass 0 s (822 files), guard pass 2 s (ALL PASS, 75 guards, 0 violations; process-change satisfied by the co-committed marked D0485; instruments-declared by Sensor snModGraph), clippy pass 76 s (cargo clippy --release --all-targets -- -D warnings, deny(pedantic, nursery) in lib.rs), probe pass 0 s, touched pass 570 s; every rung green in 650 s. Known-positive: python scripts/modgraph.py --check -> 'modgraph: layering holds - no reference from view, orient, write or scaffold into guards; none from view into orient (71 modules, 272 edges)', exit 0; at 6a22002 the same script read 32 references across the five pairs. Known-negative (probe-neg.sh): the fixture with one reference -> 'FORBIDDEN view -> guards (1 reference(s))' and 'view/mod.rs:2: pub fn lens() { crate::guards::run(); }', exit 1; the probe checks both ends and the file:line. Full set: keel suite --touched pass - 878 passed, 0 failed in 568 s over 74 integration binaries plus the lib unit tests (every module changed: algo, attestation, binding, cli_facts, contentkey, control_structure, critique, cursor, done, evidence, flow, gitfacts, govern, guards, hardening, ident, init, intake_write, launcher, orient, priority, process_cmd, queries, reports, scaffold, serve, staleness, suspect, textscan, touched, view, write); slowest lib reports::tests::report_produces_cards_and_rejects_unknown 233.7 s; receipt .keel/metrics/touched-receipt.toml. keel --help: cmp help-old.txt help-new.txt identical (14593 bytes, old = the 6a22002 binary). keel version guards line identical before and after: 'guards: 75 (66 hard-blocking, 9 warning-only)'. No trait object introduced: the five back-edges were removed by moving down (textscan, ident, done, evidence, suspect, gitfacts, binding, keel-schema cli_facts) or up (reports, priority, guards::compute_readiness); the diff adds no `dyn` and no `Box<dyn` (grep over keel-cli/src: 0 new).
        part storyGuardsViewOrientCycleIsBrokenDoDR1 : TestResult { :>> id = "d776eb1a-2836-4478-8419-8760f262a6ef"; :>> outcome = VerdictKind::pass; :>> judgedAgainst = "6a22002"; :>> judgedAt = "2026-09-14"; :>> judgedBy = "claudeFable5"; }
    }

    verification guardsViewOrientCycleIsBrokenRefineGate : Test { :>> id = "5cc5e6d7-46ee-4f76-83e8-392c4c3e25d8"; :>> title = "Sprint 717 refine gate (DoR)"; :>> createdAt = "2026-09-14"; :>> createdBy = "claudeFable5"; :>> method = VerificationMethod::inspect; :>> procedureText = "Sized 3 points: five back-edges, 32 references at 6a22002, three of them one shape (view::compute_readiness running the suite). Scope fixed to breaking the edges by moving code down (leaf modules textscan, ident, done, evidence, suspect, gitfacts, binding, keel-schema cli_facts) or up (reports, priority, guards::compute_readiness); no trait object, no guard predicate change, no member boundary drawn yet. Probe pair chosen before the tree was read: modgraph --check on keel-cli/src (positive) and on a one-reference fixture (negative)."; }
    // RAN: Refine (D0388 pair chosen before the tree was read): positive = python scripts/modgraph.py --check over keel-cli/src; negative = probe-neg.sh over a fixture holding one view -> guards reference. Sized 3 points: 32 references across five pairs at 6a22002, three of them one shape (view::compute_readiness running the suite). Scope: break edges by moving down or up, no trait object, no guard predicate change, no member boundary drawn. Charter: #CharteredBy dcGuardsViewOrientCycleIsBroken -> d0479 (backlog.sysml:3289).
    part guardsViewOrientCycleIsBrokenRefineGateR1 : TestResult { :>> id = "d57f33c4-8629-41cf-8cc0-cc243e59ef45"; :>> outcome = VerdictKind::proposed; :>> judgedAgainst = "6a22002"; :>> judgedAt = "2026-09-14"; :>> judgedBy = "claudeFable5"; }
    verification guardsViewOrientCycleIsBrokenStandupGate : Test { :>> id = "158bce40-67df-4df1-b8b4-791ed26b7f79"; :>> title = "Sprint 717 standup gate"; :>> createdAt = "2026-09-14"; :>> createdBy = "claudeFable5"; :>> method = VerificationMethod::inspect; :>> procedureText = "Stage 1 moved the shared helpers into leaves; stage 2a moved the report and priority compositions up; stage 2b moved compute_readiness, assured_blockers and assured_report into guards and gave view a readiness(root, task_suspect, invariant_violations) that takes the suite's violations as an input. Blockers met and cleared: duplicate assured symbol (renamed assured_report), visibility of Model internals (pub(crate) plus pub submodules under the nursery lints), items_after_test_module in gitfacts and binding, three tests that lived in the module of their fixture rather than their function."; }
    // RAN: Standup: three stages (leaves; reports/priority up; compute_readiness into guards). Blockers met and cleared in the tree: duplicate assured symbol -> assured_report; private Model internals -> pub(crate) with critique/reports/staleness made pub mod (redundant_pub_crate); items_after_test_module in gitfacts.rs and binding.rs -> hoisted; three tests moved to the module of the function they exercise (suspect.rs, guards.rs retro_backlog_tests and scaffold_placeholder_tests). Two guard reds met at the ladder and cleared: instruments-declared (Sensor snModGraph) and process-change (D0485, marked, HELD proposed).
    part guardsViewOrientCycleIsBrokenStandupGateR1 : TestResult { :>> id = "79258f8c-8382-4ef6-a2ad-7680aebe2ab0"; :>> outcome = VerdictKind::proposed; :>> judgedAgainst = "6a22002"; :>> judgedAt = "2026-09-14"; :>> judgedBy = "claudeFable5"; }
    verification guardsViewOrientCycleIsBrokenImplementGate : Test { :>> id = "37886fe3-d812-44e0-93f1-530b50f1d912"; :>> title = "Sprint 717 implement gate"; :>> createdAt = "2026-09-14"; :>> createdBy = "claudeFable5"; :>> method = VerificationMethod::test; :>> procedureText = "cargo build --release -p keel-cli and cargo clippy --release -p keel-cli --all-targets both clean under deny(warnings, pedantic, nursery). modgraph --check: layering holds (71 modules, 272 edges), exit 0; the fixture reports FORBIDDEN view -> guards at view/mod.rs:2, exit 1. Callers repointed in main.rs and serve.rs (priority::priority, reports::report/report_html/orient_html, guards::assured_report). A Sensor snModGraph declares the script as an instrument (instruments-declared); D0485 carries the process-change marker the guards.rs edit requires under D0209 clause 2."; }
    // RAN: // RAN: keel verify . run 4 (s717/verify4.log): validate pass, guard pass (ALL PASS 75 guards), clippy pass 76 s (cargo clippy --release --all-targets -- -D warnings), probe pass (modgraph --check exit 0 'layering holds ... 71 modules, 272 edges'; probe-neg.sh exit 0 naming FORBIDDEN view -> guards at view/mod.rs:2), touched pass 570 s (878 passed, 0 failed); every rung green in 650 s. cargo build --release -p keel-cli 0 errors. Callers repointed: main.rs keel_cli::priority::priority, reports::report/report_html/orient_html, guards::assured_report; serve.rs reports::report.
    part guardsViewOrientCycleIsBrokenImplementGateR1 : TestResult { :>> id = "086d0bf3-ca50-4ed0-be54-79706eedb0d0"; :>> outcome = VerdictKind::pass; :>> judgedAgainst = "6a22002"; :>> judgedAt = "2026-09-14"; :>> judgedBy = "claudeFable5"; }
    verification guardsViewOrientCycleIsBrokenReviewGate : Test { :>> id = "103e2ab0-d079-4027-b130-19e0a8ae34e8"; :>> title = "Sprint 717 review gate — three passes per D0172"; :>> createdAt = "2026-09-14"; :>> createdBy = "claudeFable5"; :>> method = VerificationMethod::inspect; :>> procedureText = "keel --help compared byte-for-byte between the pre-change and post-change binaries (cmp, 14593 bytes, identical). keel version guards line identical before and after: 75 guards, 66 hard-blocking, 9 warning-only. The verify ladder (validate, guard, clippy, D0388 pair, suite --touched) is the review evidence; its receipt is what the gate results below quote."; }
    // RAN: // RAN: cmp help-old.txt help-new.txt (keel --help from the 6a22002 binary vs the rebuilt one): identical, 14593 bytes. keel version guards line before and after: 'guards: 75 (66 hard-blocking, 9 warning-only)' (only the build commit differs). git diff -U0 over keel-cli/src and members: 0 added lines containing 'dyn '; the seven new files (done, evidence, ident, priority, reports, suspect, textscan) contain 0. The retro-backlog, issues and process-change guards each went red once during the ladder and are green at the recorded state (verify4.log guard rung: ALL PASS).
    part guardsViewOrientCycleIsBrokenReviewGateR1 : TestResult { :>> id = "c476985d-1e1a-41c7-8f5a-c938eee6bc09"; :>> outcome = VerdictKind::proposed; :>> judgedAgainst = "6a22002"; :>> judgedAt = "2026-09-14"; :>> judgedBy = "claudeFable5"; }
    verification guardsViewOrientCycleIsBrokenCloseOutGate : Test { :>> id = "fd539994-023a-4890-94d6-780ceac0d9df"; :>> title = "Sprint 717 closeOut gate (autonomous, D0049)"; :>> createdAt = "2026-09-14"; :>> createdBy = "claudeFable5"; :>> method = VerificationMethod::inspect; :>> procedureText = "The five forbidden pairs are listed in scripts/modgraph.py and hold at HEAD; the next item, dcWorkspaceLayeringIsGuarded (D0483), turns that check into a guard so a back-edge fails at the gate rather than in a DoD. view still owns Model, ViewError and the pure report vocabulary through a wildcard import; that is the boundary the following extraction draws."; }
    // RAN: CloseOut: the five forbidden pairs are listed in scripts/modgraph.py and hold at the working tree (exit 0); Sensor snModGraph declares the script (instruments-declared PASS 21 scanned). Deferred by design to dcWorkspaceLayeringIsGuarded (D0483, held): turning the check into a guard. Left standing: view owns Model, ViewError and the pure report vocabulary read by reports through a wildcard import - the boundary dcModelAndWriteAreMembers draws next. Slowest test in the set is the moved reports::tests::report_produces_cards_and_rejects_unknown at 233.7 s (it composes readiness = one guard suite per report); no prior touched receipt is tracked to compare against.
    part guardsViewOrientCycleIsBrokenCloseOutGateR1 : TestResult { :>> id = "2e232177-40da-4a87-9c17-147664c1dc70"; :>> outcome = VerdictKind::proposed; :>> judgedAgainst = "6a22002"; :>> judgedAt = "2026-09-14"; :>> judgedBy = "claudeFable5"; }
    verification guardsViewOrientCycleIsBrokenRetroGate : Test { :>> id = "cea939cf-7c85-4d25-b3b3-8a00f312a9e5"; :>> title = "Sprint 717 retro gate (autonomous, D0049)"; :>> createdAt = "2026-09-14"; :>> createdBy = "claudeFable5"; :>> method = VerificationMethod::analyze; :>> procedureText = "Avoidable-issue scan held over the sprint 717 verify logs and the fixes between them. One avoidable finding, tracked: the moves into guards.rs were built and clippy-clean before anything said the file is a D0070 locked surface - hook_pre_write never asks is_locked_path, so the process-change guard at rung 2 of keel verify was the first word, after the code was done. Recorded as issue555 with resolver dcLockedSurfaceEditIsNamedAtWriteTime, added to the backlog in this commit. A second candidate was checked and dropped: modgraph DOES strip doc comments (strip_comments drops everything after // once string literals are blanked; probed on a /// line naming crate::guards); what it does not strip is a /* */ block comment, and the tree holds none naming crate:: - the Sensor's failure-mode note now says so, and no item is needed."; }
    // RAN: Retro (D0131): one finding tracked - issue555 'A write to a D0070 locked surface draws no word until the process-change guard refuses the commit', resolver dcLockedSurfaceEditIsNamedAtWriteTime added to EngineBuild in this commit (#Resolves edge at record time). Check that established it: main.rs:730-826 hook_pre_write never calls guards::is_locked_path (guards.rs:1215). One candidate checked and dropped: modgraph strips doc comments (probed strip_comments on a /// line naming crate::guards -> empty); the unstripped case is /* */ block comments, of which the tree holds none naming crate:: (grep), so the Sensor's failure-mode note was corrected and no item recorded.
    part guardsViewOrientCycleIsBrokenRetroGateR1 : TestResult { :>> id = "2f60b0d1-adab-4d73-86de-7422d3a9c8e1"; :>> outcome = VerdictKind::proposed; :>> judgedAgainst = "6a22002"; :>> judgedAt = "2026-09-14"; :>> judgedBy = "claudeFable5"; }
}
