// ProjectDeliveryS708 — Sprint 708: Implement D0476 through dcVerifyLadderStopsAtTheFirstRed: `keel verify` runs the pre-commit checks as one ladder in cost order - gate validate, gate guard (from its receipt, D0371), cargo clippy -D warnings, the D0388 probe pair named by --probe, then suite --touched (keyed per D0474) - and stops at the first red, writing one receipt that names the rung. The pain: in sprint705 a clippy lint was found after a 20-minute test run because the five checks ran as separate commands in no enforced order, and with the verifier suspended (single-agent mode) the order was the AI's discipline alone - manual vigilance is not a control (D0047). The panel of 2026-09-13 ranked this third: a sequence is not a mechanism until it is one command. Chartered by D0476 (process-change, accepted by the human 2026-09-14). 3 pts.. EXECUTE. 3 pts.
package ProjectDeliveryS708 {
    private import EngineElement::*;
    private import EngineWork::*;
    private import EngineVerification::*;
    private import EngineRelationships::*;

    #CharteredBy dependency from verifyLadderStopsAtTheFirstRedStory to d0476;

    part verifyLadderStopsAtTheFirstRedStory : Story {
        :>> id = "c9618658-4bd7-4f23-be18-b8376392d611";
        :>> title = "Sprint 708: Implement D0476 through dcVerifyLadderStopsAtTheFirstRed: `keel verify` runs the pre-commit checks as one ladder in cost order - gate validate, gate guard (from its receipt, D0371), cargo clippy -D warnings, the D0388 probe pair named by --probe, then suite --touched (keyed per D0474) - and stops at the first red, writing one receipt that names the rung. The pain: in sprint705 a clippy lint was found after a 20-minute test run because the five checks ran as separate commands in no enforced order, and with the verifier suspended (single-agent mode) the order was the AI's discipline alone - manual vigilance is not a control (D0047). The panel of 2026-09-13 ranked this third: a sequence is not a mechanism until it is one command. Chartered by D0476 (process-change, accepted by the human 2026-09-14). 3 pts. (3 pts)";
        :>> createdAt = "2026-09-14"; :>> createdBy = "claudeFable5"; :>> kind = WorkKind::code; :>> priority = WorkPriority::p0; :>> owner = "claudeFable5"; :>> estimatedPoints = 3;
    }

    action def DeliveryRunS708 {
        action storyVerifyLadderStopsAtTheFirstRed;
        verification storyVerifyLadderStopsAtTheFirstRedDoD : Test { :>> id = "8bf81c85-c712-409a-b8df-624d52ecbd3c"; :>> method = VerificationMethod::test; :>> procedureText = "keel-cli/src/verify.rs orchestrates the five existing entry points as child processes of the running binary with inherited stdio, in the order validate, guard, clippy, probe, touched; a red rung stops the ladder and every later rung is recorded not-run; a probe rung with no --probe pair is recorded not-named and the ladder continues; --probe takes exactly two non-empty comma-separated shell-free command lines, both must exit 0, and the value is never mistaken for a root; --no-receipt forces the guard and touched rungs to run rather than answer from their receipts; the own-image refusal (issue150) is up front; every child has KEEL_PERF scrubbed. The receipt .keel/metrics/verify-receipt.toml carries head, at, seconds, outcome, stopped_at and one [[rung]] row each with name, verdict, exit, seconds, command, and round-trips through its parser. verify is a CliCommand in .engine/cli/commands.sysml, in CLI_FACTS and COMMAND_NAMES, dispatched in main.rs, so --help, dispatch and the facts agree (guard cli-surface-declared). The test-verify and delegated-ceremony skills and CLAUDE.md name the ladder instead of listing the rungs. Unit tests cover the stop, the green climb, the not-named pair, the pair's arity, the root resolution and the receipt round-trip. D0388 pair, run on the real tree from a copy of the binary: known-positive - with one clippy lint injected into keel-cli/src, `keel verify . --probe ...` stops at clippy within a minute of reaching that rung, the receipt says stopped_at = clippy with probe and touched not-run, and no test binary compiled; known-negative - with the lint removed, the same command climbs every rung green, writes verify-receipt.toml with stopped_at = none, and leaves touched-receipt.toml at the current code key so the next keel land skips what it observed."; }
        // RAN: Every clause of the story DoD is read from the tree at 593147c: keel-cli/src/verify.rs Rung::ORDER is [Validate, Guard, Clippy, Probe, Touched] and climb() reads it; a red sets stopped_at and later rungs are NotRun; an absent pair is NotNamed; own_args refuses any count but two; --no-receipt forces the guard and touched rungs; the own-image refusal is first in cmd(); run_rung env_remove(KEEL_PERF). verify-receipt.toml as written by the green ladder carries head, at, seconds, outcome, stopped_at and five [[rung]] rows (name, verdict, exit, seconds, command) and unit receipt_round_trips parses it back. cliVerify is in .engine/cli/commands.sysml, CLI_FACTS is 86, COMMAND_NAMES is 35, main.rs dispatches verify; guard cli-surface-declared PASS 86 scanned; keel sync-claude --check clean at 47 registry skills. test-verify SKILL.md 0.3.0, delegated-ceremony SKILL.md and CLAUDE.md sect.4/5 name the ladder. Unit tests: 6 in verify:: (stop, green climb, not-named pair, arity, root resolution, receipt round-trip). D0388 pair receipts quoted in dcVerifyLadderStopsAtTheFirstRedDoD's result: positive stopped at clippy after 74 s with nothing compiled past cargo check; negative green in 1071 s and the land at 593147c skipped 49 binaries at the observed code key.
        part storyVerifyLadderStopsAtTheFirstRedDoDR1 : TestResult { :>> id = "9d5dcdcf-e1a3-4f1e-b4f0-57d3c5292886"; :>> outcome = VerdictKind::pass; :>> judgedAgainst = "593147c"; :>> judgedAt = "2026-09-14"; :>> judgedBy = "claudeFable5"; }
    }

    verification verifyLadderStopsAtTheFirstRedRefineGate : Test { :>> id = "92dfd07a-a6a9-44b9-83b0-346431f187a5"; :>> title = "Sprint 708 refine gate (DoR)"; :>> createdAt = "2026-09-14"; :>> createdBy = "claudeFable5"; :>> method = VerificationMethod::inspect; :>> procedureText = "Chartered by D0476, accepted by the human 2026-09-14 with the process-change marker (a new command on the CLI surface; two skills and CLAUDE.md change meaning). Three points: one new module with its unit pair, the surface wiring in four homes, doc-sync, and two real-tree runs - the sprint-planning table puts a module with tests at 3. DoR: dcVerifyLadderStopsAtTheFirstRed ranks first on keel show whats-next after sprint707 closed at 1e2ed25 (declaration order is priority, D0052); the pair is the DoD's own; issue477 binds - no keel-cli/src or .engine edit while cargo or the ladder runs; the probe value is a command line and the root resolution must not consume it (repo_arg takes the first non-flag argument)."; }
    // RAN: KEEL show whats-next . at 1e2ed25 -> dcVerifyLadderStopsAtTheFirstRed first (then dcReportTestBuildsTheModelOnce, dcBuildScriptDoesNotWatchTheGitIndex); d0476 accepted by wweatherholtz 2026-09-14 at 8b731e6 with the process-change marker; 3 points by the sprint-planning table (a module with tests); the D0388 pair is the DoD's own (a clippy lint injected / removed)
    part verifyLadderStopsAtTheFirstRedRefineGateR1 : TestResult { :>> id = "23ce1217-d230-46b2-85b1-3429a6936730"; :>> outcome = VerdictKind::proposed; :>> judgedAgainst = "1e2ed25"; :>> judgedAt = "2026-09-14"; :>> judgedBy = "claudeFable5"; }
    verification verifyLadderStopsAtTheFirstRedStandupGate : Test { :>> id = "8912ff9c-be81-45e3-b908-0ef9622d7a81"; :>> title = "Sprint 708 standup gate"; :>> createdAt = "2026-09-14"; :>> createdBy = "claudeFable5"; :>> method = VerificationMethod::inspect; :>> procedureText = "Order: verify.rs with its unit tests first (the climb is a pure function over a runner closure so the stop is tested without a child process); wire lib.rs, main.rs dispatch, COMMAND_NAMES, CLI_FACTS and commands.sysml together so cli-surface-declared judges all four at once; build, clippy -D warnings, keel sync-claude; --help and the --probe arity refusal from the copy; the capability_refusal_bites inventory test; doc-sync of test-verify (procedure and registry purpose), delegated-ceremony and CLAUDE.md sect.4/5; the sprint record before the real-tree runs because process-change is red until it exists (D0465) and the ladder will stop there; the known-positive with an injected lint, detached; remove the lint; the known-negative green ladder, detached; the gate results and the DoD result quoting both receipts; one CR: commit detached; keel-land; git status -sb and the CI conclusion read back."; }
    // RAN: Order followed as the standup names it with one correction recorded in the retro: verify.rs and its unit tests first; lib.rs, main.rs dispatch, COMMAND_NAMES 35, CLI_FACTS 86 and commands.sysml cliVerify wired together (scratch s708/wire.py); build, clippy, sync-claude; --help and the --probe arity refusal; capability_refusal_bites; doc-sync (test-verify SKILL.md 0.3.0 + registry purpose, delegated-ceremony, CLAUDE.md sect.4 and sect.5); the sprint record BEFORE the real-tree runs (the first known-positive launch stopped at guard: process-change red until the record existed, D0465); known-positive with the lint, lint removed, known-negative; issue477 held - no keel-cli/src or .engine edit while cargo or the ladder ran
    part verifyLadderStopsAtTheFirstRedStandupGateR1 : TestResult { :>> id = "8ed7d768-c0b0-4c95-ba0d-d19eee5244e6"; :>> outcome = VerdictKind::proposed; :>> judgedAgainst = "1e2ed25"; :>> judgedAt = "2026-09-14"; :>> judgedBy = "claudeFable5"; }
    verification verifyLadderStopsAtTheFirstRedImplementGate : Test { :>> id = "27322cc4-cc5e-4fc8-8492-a18e292b39dc"; :>> title = "Sprint 708 implement gate"; :>> createdAt = "2026-09-14"; :>> createdBy = "claudeFable5"; :>> method = VerificationMethod::test; :>> procedureText = "The implement gate holds when: cargo test --release --lib -- verify:: passes every unit test; cargo clippy --release --all-targets -- -D warnings exits 0; keel sync-claude --check reports the surface in step; keel verify --help renders from the fact and `keel verify . --probe onlyone` is refused with exit 2 naming the count; the capability_refusal_bites inventory test passes with verify in COMMAND_NAMES and the dispatch. Its evidence quotes those commands' own lines."; }
    // RAN: cargo test --release --lib -- verify:: -> 6 passed, 0 failed (a_red_rung_stops_the_ladder_before_the_test_binaries_compile, a_green_ladder_reaches_the_touched_run_last, an_unnamed_probe_pair_is_recorded_not_invented, probe_flag_takes_exactly_a_pair, the_probe_value_is_not_mistaken_for_a_root, receipt_round_trips); cargo clippy --release --all-targets -- -D warnings -> exit 0 after three fixes (missing_const_for_fn x2, unnecessary_debug_formatting); KEEL --help line 86 is verify [ROOT] [--probe POSITIVE,NEGATIVE] [--no-receipt]; KEEL verify . --probe onlyone -> --probe names 1 side(s); a D0388 pair is exactly two, exit=2; cargo test --release --test capability_refusal_bites -> 9 passed (the_command_inventory_matches_the_dispatch with verify); KEEL sync-claude --check . -> keel-owned subset matches this binary's generator (47 registry skill(s)); guard cli-surface-declared PASS 86 scanned
    part verifyLadderStopsAtTheFirstRedImplementGateR1 : TestResult { :>> id = "8ecddb11-de25-4149-94e8-a7bd18711110"; :>> outcome = VerdictKind::pass; :>> judgedAgainst = "1e2ed25"; :>> judgedAt = "2026-09-14"; :>> judgedBy = "claudeFable5"; }
    verification verifyLadderStopsAtTheFirstRedReviewGate : Test { :>> id = "e9ce247d-1d5d-4738-8181-ae5cecd6f5cc"; :>> title = "Sprint 708 review gate — three passes per D0172"; :>> createdAt = "2026-09-14"; :>> createdBy = "claudeFable5"; :>> method = VerificationMethod::inspect; :>> procedureText = "Three passes (D0172). Correctness: the ladder's order is a const array read by the climb, not five call sites; a red sets stopped_at and the loop records the rest not-run without asking them; the probe rung is not-named rather than pass when no pair is given, so a green receipt never claims a pair that was not run; both probe sides must exit 0. Honesty: the receipt names the command each rung ran, including the receipt-answering forms of guard and touched, so a reader can tell a receipt answer from a run; the exit code is the first red rung's own. Scope: the command adds no check (D0476 rationale) - gate check-engine and sync-claude --check stay outside the ladder and the test-verify skill says so; the full keel suite is untouched."; }
    // RAN: KEEL gate validate . -> 812 tracking file(s) validated clean.; KEEL gate check-engine . -> .engine instance files validated clean (kernel-free; D0112 phase 2).; KEEL gate guard --no-receipt . -> [guard] ALL PASS - 338 actionable warning(s) across 9 guard(s); exit=0 (process-change: locked edit authorised by d0476 cited as the charter of the co-committed sprint record, D0465; retro-backlog PASS after the retro named d0465 for its closed-in-sprint finding). Three passes per D0172 read against verify.rs: Rung::ORDER is the one order and climb() reads it; a red sets stopped_at and the loop records every later rung not-run without spawning it (unit a_red_rung_stops_the_ladder...); an absent pair is not-named, never pass; both probe sides must exit 0; every receipt row names the command it ran so a D0371 receipt answer is distinguishable from a run; exit code is the first red rung's own; check-engine and sync-claude --check stay outside the ladder and the test-verify skill says so
    part verifyLadderStopsAtTheFirstRedReviewGateR1 : TestResult { :>> id = "944b7f43-55f6-45c7-862d-4bb8bbf6fe38"; :>> outcome = VerdictKind::proposed; :>> judgedAgainst = "1e2ed25"; :>> judgedAt = "2026-09-14"; :>> judgedBy = "claudeFable5"; }
    verification verifyLadderStopsAtTheFirstRedCloseOutGate : Test { :>> id = "62565ec4-56cc-4570-89e2-465985880e83"; :>> title = "Sprint 708 closeOut gate (autonomous, D0049)"; :>> createdAt = "2026-09-14"; :>> createdBy = "claudeFable5"; :>> method = VerificationMethod::inspect; :>> procedureText = "Closes at the CR: commit that lands verify.rs, the four surface homes, the doc-sync, the regenerated .claude surface, the touched.rs land line naming nextest, and this record together: keel-land runs the touched set from that commit: a binary observed green at this content is skipped (D0474, code key 593ea821b10f6d8e from the green ladder), and one that reads this repo reruns because the tree key moved with the ceremony; gate validate / check-engine / guard --no-receipt green over that tree; dcVerifyLadderStopsAtTheFirstRedDoD carries a pass with both real-tree receipts quoted; the CI conclusion for the landing commit is read back as success; git status -sb shows main level with origin."; }
    // RAN: FAIL on one clause, the rest hold. Commit 593147c (CR: keel verify runs the pre-commit ladder ...) landed verify.rs, the four surface homes, the doc-sync, the regenerated .claude surface, touched.rs and the sprint record together; keel-land ran the touched set: touched-receipt.toml head 593147c at 1789381323 outcome pass 662 passed 0 failed 498 s, ran 12 (the repo-reading binaries plus lib), skipped 49 at code_key 593ea821b10f6d8e (D0474, as the clause says); gate validate 812 clean, check-engine clean, guard --no-receipt ALL PASS before the commit; dcVerifyLadderStopsAtTheFirstRedDoD carries a pass at 593147c quoting both ladder receipts; git status -sb reads main...origin/main level. The clause not met: gh run list --json conclusion for 593147c (run 34832819487) reads failure, step test, cause keel-parser::lexer_bdd --list unexpected argument, nextest exit 104 - issue542, present since 1e2ed25 and not this sprint's to fix; resolver dcCiNextestExcludesEveryCustomHarness is the next sprint. Recorded as the fail it is; a later result on this gate may cite the first green CI over a tree holding this work.
    part verifyLadderStopsAtTheFirstRedCloseOutGateR1 : TestResult { :>> id = "6f640d03-285b-43be-a39a-4d63e1135c76"; :>> outcome = VerdictKind::fail; :>> judgedAgainst = "593147c"; :>> judgedAt = "2026-09-14"; :>> judgedBy = "claudeFable5"; }
    verification verifyLadderStopsAtTheFirstRedRetroGate : Test { :>> id = "3a5039da-b641-4351-83b7-b6c7ab139c09"; :>> title = "Sprint 708 retro gate (autonomous, D0049)"; :>> createdAt = "2026-09-14"; :>> createdBy = "claudeFable5"; :>> method = VerificationMethod::analyze; :>> procedureText = "Avoidable issues scanned; findings are tracked items, not prose. The known-positive run before this record existed stopped at guard (process-change red, D0465) - the ladder did what it is for, and the order of the standup was corrected to record the sprint before the runs. Finding one, closed in-sprint: the known-positive run launched before this record existed stopped at guard (process-change red until the chartered sprint record is co-committed, D0465) - the ladder did what it is for; the standup's order was corrected to record the sprint before the runs. No new item - the control that caught it is d0465's process-change guard, already in force. Finding two, not reproduced: the validate rung took 34 s inside the first ladder against 0.4 s standalone; in the second known-positive and the known-negative ladders it took 0 s (verify-receipt rows), so no item - a single unrepeated reading is an observation, not a defect (D0151). Finding three, tracked: recording the implement gate result passed evidence with two backtick spans as a double-quoted shell argument and the shell emptied both (D0224, fifth occurrence) because record result and gate-result have no file form for --evidence - issue543, resolver dcEvidenceGoesThroughAFile, ranked third. Finding four, tracked: while this sprint ran, the CI conclusion for 1e2ed25 (sprint707) was read back as failure - nextest --workspace lists keel-parser four harness = false binaries the keel-cli-only exclusion missed; sprint707 retro had dismissed that drift and its closeOut clause naming CI success is false - issue542, resolver dcCiNextestExcludesEveryCustomHarness, ranked second."; }
    // RAN: Four findings, each tracked or its non-item justified in the gate text: (1) known-positive launched before the sprint record existed stopped at guard, process-change red (D0465) - no new item, d0465's guard is the control; (2) 34 s validate rung in the first ladder, 0 s in the next two - not reproduced, no item (D0151); (3) D0224 fifth occurrence in this sprint's own implement gate evidence - issue543 with resolver dcEvidenceGoesThroughAFile, third on keel show whats-next; (4) CI red at 1e2ed25 and again at 593147c from the keel-cli-only nextest exclusion - issue542 with resolver dcCiNextestExcludesEveryCustomHarness, second on keel show whats-next. Read back: keel show whats-next . lists dcCiNextestExcludesEveryCustomHarness then dcEvidenceGoesThroughAFile directly after this sprint's item; guard retro-backlog PASS with both named.
    part verifyLadderStopsAtTheFirstRedRetroGateR1 : TestResult { :>> id = "89d663e5-03fc-48f0-b0d2-f88f61a411f2"; :>> outcome = VerdictKind::proposed; :>> judgedAgainst = "593147c"; :>> judgedAt = "2026-09-14"; :>> judgedBy = "claudeFable5"; }
}
