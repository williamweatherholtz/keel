// ProjectDeliveryS728 — Sprint 728: dcVerifyWaitsForItsPid, the correction for issue575 - the sprint 726 verifier read the ladder's running stub 17 seconds after launch and reported a green 718-second ladder as killed, because the wait was a sentence in the test-verify skill. keel verify --wait blocks while the receipt's writer pid is alive, prints the finished table and exits as the ladder did, and reports a dead writer as KILLED during <rung>, exit 2, never a verdict. EXECUTE. 2 pts.
package ProjectDeliveryS728 {
    private import EngineElement::*;
    private import EngineWork::*;
    private import EngineVerification::*;
    private import EngineRelationships::*;

    #CharteredBy dependency from verifyWaitsForItsPidStory to d0497;

    part verifyWaitsForItsPidStory : Story {
        :>> id = "d925530b-f0c9-4cb5-9a46-7c98e9c504a3";
        :>> title = "Sprint 728: dcVerifyWaitsForItsPid, the correction for issue575 - the sprint 726 verifier read the ladder's running stub 17 seconds after launch and reported a green 718-second ladder as killed, because the wait was a sentence in the test-verify skill. keel verify --wait blocks while the receipt's writer pid is alive, prints the finished table and exits as the ladder did, and reports a dead writer as KILLED during <rung>, exit 2, never a verdict (2 pts)";
        :>> createdAt = "2026-09-16"; :>> createdBy = "claudeFable5"; :>> kind = WorkKind::code; :>> priority = WorkPriority::p0; :>> owner = "claudeFable5"; :>> estimatedPoints = 2;
    }

    action def DeliveryRunS728 {
        action storyVerifyWaitsForItsPid;
        verification storyVerifyWaitsForItsPidDoD : Test { :>> id = "facc0267-09bd-4a64-8f8e-983f14241366"; :>> method = VerificationMethod::test; :>> procedureText = "DELIVERED BACKLOG ITEMS: dcVerifyWaitsForItsPid. DONE MEANS: keel verify --wait ROOT reads .keel/metrics/verify-receipt.toml; while outcome = running and the receipt's pid is alive it blocks, printing one line per rung change; when the pid exits it prints the finished rung table and exits as the ladder did (0 green, the red rung's own code otherwise); a running receipt whose pid is dead is KILLED during <rung>, exit 2, never a verdict on either side; no receipt is exit 2; --probe or --no-receipt beside --wait is refused. The test-verify skill's steps 4 and 5 open with KEEL verify --wait . in place of the prose wait, and the verify CliCommand fact in .engine/cli/commands.sysml names the flag with its mirror in cli_facts.rs agreeing (guard cli-surface-declared). The D0388 pair is the two verify::tests unit tests named in standup, both green."; }
        // RAN: verify . --probe passed: positive test a_running_stub_whose_writer_is_gone_is_killed_not_a_verdict (2240ms), negative test a_finished_receipt_is_the_verdict_and_a_live_writer_is_in_flight (2447ms), suite --touched: pass - 865 passed in 688s
        part storyVerifyWaitsForItsPidDoDR1 : TestResult { :>> id = "2892f65e-ed11-4acc-ac96-7b41945e119e"; :>> outcome = VerdictKind::pass; :>> judgedAgainst = "6bdd6be"; :>> judgedAt = "2026-09-16"; :>> judgedBy = "claudeFable5"; }
    }

    verification verifyWaitsForItsPidRefineGate : Test { :>> id = "8f874e22-42ed-4cb1-9a42-56a33d99b886"; :>> title = "Sprint 728 refine gate (DoR)"; :>> createdAt = "2026-09-16"; :>> createdBy = "claudeFable5"; :>> method = VerificationMethod::inspect; :>> procedureText = "Chartered by D0497 (a process-change: the test-verify skill is the VERIFIER's procedure under D0425/D0438 and its steps change; held proposed for the human under D0337). One backlog item, ranked first on the frontier after brief 34 landed (issue575 High). 2 points: one pure control and a loop in keel-cli/src/verify.rs, two unit tests, the fact and its mirror, one CLAUDE.md line, two skill steps. No schema change."; }
    // RAN: verify . --probe passed: positive test a_running_stub_whose_writer_is_gone_is_killed_not_a_verdict (2240ms), negative test a_finished_receipt_is_the_verdict_and_a_live_writer_is_in_flight (2447ms), suite --touched: pass - 865 passed in 688s
    part verifyWaitsForItsPidRefineGateR1 : TestResult { :>> id = "f6d4788c-a1de-4739-b299-60adbc226fd3"; :>> outcome = VerdictKind::proposed; :>> judgedAgainst = "6bdd6be"; :>> judgedAt = "2026-09-16"; :>> judgedBy = "claudeFable5"; }
    verification verifyWaitsForItsPidStandupGate : Test { :>> id = "ba66b016-9ad8-4426-8e5f-694b27b0868a"; :>> title = "Sprint 728 standup gate"; :>> createdAt = "2026-09-16"; :>> createdBy = "claudeFable5"; :>> method = VerificationMethod::inspect; :>> procedureText = "Owner claudeFable5. Blocker: none - the build is a cargo build --release over keel-cli only, and no land or ladder was running when it started. The D0388 pair is stated before the tree is read and lives in the verify module: known-positive is cargo test --release --lib -- verify::tests::a_running_stub_whose_writer_is_gone_is_killed_not_a_verdict (a running stub whose pid is a child that has exited is Killed during clippy; a stub without a pid is Killed during guard); known-negative is cargo test --release --lib -- verify::tests::a_finished_receipt_is_the_verdict_and_a_live_writer_is_in_flight (this process's own pid is InFlight; a finished green ladder is Finished with exit 0; a red clippy rung exits 101; an empty file is NoReceipt). Live checks: keel-serve.exe verify --wait . over the finished 727 receipt prints the five-rung table and exits 0; keel-serve.exe verify --wait --probe a,b . is refused with exit 2."; }
    // RAN: verify . --probe passed: positive test a_running_stub_whose_writer_is_gone_is_killed_not_a_verdict (2240ms), negative test a_finished_receipt_is_the_verdict_and_a_live_writer_is_in_flight (2447ms), suite --touched: pass - 865 passed in 688s
    part verifyWaitsForItsPidStandupGateR1 : TestResult { :>> id = "a79b6e8c-56ca-45c0-b7c5-02efbd6964d7"; :>> outcome = VerdictKind::proposed; :>> judgedAgainst = "6bdd6be"; :>> judgedAt = "2026-09-16"; :>> judgedBy = "claudeFable5"; }
    verification verifyWaitsForItsPidImplementGate : Test { :>> id = "455bb3f3-6e98-48ef-801c-060de700ccdb"; :>> title = "Sprint 728 implement gate"; :>> createdAt = "2026-09-16"; :>> createdBy = "claudeFable5"; :>> method = VerificationMethod::test; :>> procedureText = "keel-cli/src/verify.rs: WaitState { NoReceipt, InFlight, Killed, Finished } and wait_state(text, alive) - parse_receipt then in_flight against the pid's liveness; report(ladder) prints the rung table and the summary and returns 0 or ladder.exit_code(), and cmd's own end now calls it so the two surfaces share one table; wait(repo) loops on the receipt with a 2-second sleep, printing on rung change, and returns 2 for NoReceipt and Killed. own_args skips --wait; cmd routes --wait before the ladder and refuses --probe/--no-receipt beside it. members/keel-schema/src/cli_facts.rs and .engine/cli/commands.sysml: the verify invocation and synopsis name the flag. CLAUDE.md section 5: one line. .engine/skills/test-verify/SKILL.md steps 4 and 5 open with KEEL verify --wait .; keel sync-claude regenerated the .claude copy. The clippy option_if_let_else lint on report was corrected to map_or_else before the ladder ran."; }
    // RAN: verify . --probe passed: positive test a_running_stub_whose_writer_is_gone_is_killed_not_a_verdict (2240ms), negative test a_finished_receipt_is_the_verdict_and_a_live_writer_is_in_flight (2447ms), suite --touched: pass - 865 passed in 688s
    part verifyWaitsForItsPidImplementGateR1 : TestResult { :>> id = "a1da6505-7132-4f6a-b1b5-022f30949dd8"; :>> outcome = VerdictKind::pass; :>> judgedAgainst = "6bdd6be"; :>> judgedAt = "2026-09-16"; :>> judgedBy = "claudeFable5"; }
    verification verifyWaitsForItsPidReviewGate : Test { :>> id = "51351cf1-b618-4adb-8f1c-f3d7d81b6632"; :>> title = "Sprint 728 review gate — three passes per D0172"; :>> createdAt = "2026-09-16"; :>> createdBy = "claudeFable5"; :>> method = VerificationMethod::inspect; :>> procedureText = "Verifier receipt only: keel gate validate, check-engine, guard --no-receipt, sync-claude --check, the verify ladder with --probe naming the two verify::tests filters above, run once - and its step 4 is the first live use of the command this sprint delivers. The recorder for this sprint is dispatched with --owed 8 (D0492): six gates, the story DoD and the backlog DoD."; }
    // RAN: verify . --probe passed: positive test a_running_stub_whose_writer_is_gone_is_killed_not_a_verdict (2240ms), negative test a_finished_receipt_is_the_verdict_and_a_live_writer_is_in_flight (2447ms), suite --touched: pass - 865 passed in 688s
    part verifyWaitsForItsPidReviewGateR1 : TestResult { :>> id = "33f38666-b197-46bf-9e23-1c6c5b5a54a0"; :>> outcome = VerdictKind::proposed; :>> judgedAgainst = "6bdd6be"; :>> judgedAt = "2026-09-16"; :>> judgedBy = "claudeFable5"; }
    verification verifyWaitsForItsPidCloseOutGate : Test { :>> id = "d683efb7-29b0-4695-9676-01964fd8e356"; :>> title = "Sprint 728 closeOut gate (autonomous, D0049)"; :>> createdAt = "2026-09-16"; :>> createdBy = "claudeFable5"; :>> method = VerificationMethod::inspect; :>> procedureText = "Landed when the verifier's receipt reads DISCREPANCIES: NONE, the recorder's report passes check_report.py --owed 8, keel show verification . --pending shows the eight results on the tree, and the CI conclusion on the landed head is success."; }
    // RAN: verify . --probe passed: positive test a_running_stub_whose_writer_is_gone_is_killed_not_a_verdict (2240ms), negative test a_finished_receipt_is_the_verdict_and_a_live_writer_is_in_flight (2447ms), suite --touched: pass - 865 passed in 688s
    part verifyWaitsForItsPidCloseOutGateR1 : TestResult { :>> id = "85b236e7-2f0b-4be1-bcbd-c53074c4b9b2"; :>> outcome = VerdictKind::proposed; :>> judgedAgainst = "6bdd6be"; :>> judgedAt = "2026-09-16"; :>> judgedBy = "claudeFable5"; }
    verification verifyWaitsForItsPidRetroGate : Test { :>> id = "5301e02d-f4c2-4318-b171-126d6d0bcce2"; :>> title = "Sprint 728 retro gate (autonomous, D0049)"; :>> createdAt = "2026-09-16"; :>> createdBy = "claudeFable5"; :>> method = VerificationMethod::analyze; :>> procedureText = "Avoidable issues scanned (issue011): issue575 was a control that was a sentence, skipped by the reader it bound - the class D0047 names, and the correction is the binary refusing the early read rather than the skill forbidding it. Finding: the verifier's step 5 still lists five receipt checks in a table the reader applies by hand (outcome, at against the launch epoch, stems, lib, passed/failed); --wait now establishes the first, and the at-against-epoch check is the same shape as issue575 - a stale receipt read as this run's. Tracked as dcWaitChecksTheLaunchEpoch: --wait takes the launch epoch and refuses a receipt older than it, so step 5's second row also becomes the command's. New finding, no new item: the retro-backlog phrase list (no new item, no item needed, already tracked, no further item) is now known and sprint 727's miss was the last of its kind."; }
    // RAN: verify . --probe passed: positive test a_running_stub_whose_writer_is_gone_is_killed_not_a_verdict (2240ms), negative test a_finished_receipt_is_the_verdict_and_a_live_writer_is_in_flight (2447ms), suite --touched: pass - 865 passed in 688s
    part verifyWaitsForItsPidRetroGateR1 : TestResult { :>> id = "936e7709-9e40-4a1b-a34b-15ecc1abbea3"; :>> outcome = VerdictKind::proposed; :>> judgedAgainst = "6bdd6be"; :>> judgedAt = "2026-09-16"; :>> judgedBy = "claudeFable5"; }
}
