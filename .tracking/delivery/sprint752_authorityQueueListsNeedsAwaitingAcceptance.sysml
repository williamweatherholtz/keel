// ProjectDeliveryS752 — Sprint 752: A Need awaiting the human's acceptance is a needAcceptance row of keel show authority-queue, computed from the #Verify-linked confirmation Tests that reach it and who judged their results; existing acceptance Tests are bound to their sets by copy-and-add edges (D0534, D0535; issue661). EXECUTE. 3 pts.
package ProjectDeliveryS752 {
    private import EngineElement::*;
    private import EngineWork::*;
    private import EngineVerification::*;
    private import EngineRelationships::*;

    #CharteredBy dependency from authorityQueueListsNeedsAwaitingAcceptanceStory to d0534;
    #Delivers dependency from authorityQueueListsNeedsAwaitingAcceptanceStory to dcAuthorityQueueListsNeedsAwaitingAcceptance;

    part authorityQueueListsNeedsAwaitingAcceptanceStory : Story {
        :>> id = "b6dee86a-3f78-461f-b3da-dfa5c7a1768a";
        :>> title = "Sprint 752: A Need awaiting the human's acceptance is a needAcceptance row of keel show authority-queue, computed from the #Verify-linked confirmation Tests that reach it and who judged their results; existing acceptance Tests are bound to their sets by copy-and-add edges (D0534, D0535; issue661). EXECUTE. 3 pts. (3 pts)";
        :>> createdAt = "2026-09-19"; :>> createdBy = "claudeFable5"; :>> kind = WorkKind::code; :>> priority = WorkPriority::p0; :>> owner = "claudeFable5"; :>> estimatedPoints = 3;
    }

    action def DeliveryRunS752 {
        action storyAuthorityQueueListsNeedsAwaitingAcceptance;
        verification storyAuthorityQueueListsNeedsAwaitingAcceptanceDoD : Test { :>> id = "28aec284-75e2-4e51-97ec-c13210364662"; :>> method = VerificationMethod::test; :>> procedureText = "DELIVERED BACKLOG ITEM: dcAuthorityQueueListsNeedsAwaitingAcceptance. DONE MEANS: the task's DoD passes as written - authority_queue in members/keel-view/src/view/mod.rs pushes a needAcceptance row for every Need no method=confirmation Test with a passing TestResult judgedBy a Person reaches through a verify edge, the row carrying shortName, createdAt, waitingDays and a note naming the reaching Test or the words no acceptance test; a unit test carries the D0388 pair (a Need with no reaching Test is one row; the same Need reached by a Test whose passing result is judgedBy a Person is no row; the same Test judgedBy an ai Actor is still a row); the decision-surfacing skill's first step reads needAcceptance rows beside decisionAcceptance; every passing human-judged confirmation Test under .tracking/business whose words accept a set is bound to each Need of that set by #Verify edges, edges only; keel show authority-queue at the landing commit lists the three self-analysis Needs naming engineSelfAnalysisNeedsAccept and none of the engine-needs or modular-members Needs; clippy, the full guard set and the touched test set pass."; }
        // RAN: keel suite --touched: pass - 914 passed in 887s over [82 binaries]; 0 failed, failing []
        part storyAuthorityQueueListsNeedsAwaitingAcceptanceDoDR1 : TestResult { :>> id = "adca3414-bdae-460f-b327-d76b0f3f0c93"; :>> outcome = VerdictKind::pass; :>> judgedAgainst = "c3e4635a"; :>> judgedAt = "2026-09-19"; :>> judgedBy = "claudeFable5"; }
    }

    verification authorityQueueListsNeedsAwaitingAcceptanceRefineGate : Test { :>> id = "18393ba4-118e-4ce9-a135-f8b40009adcb"; :>> title = "Sprint 752 refine gate (DoR)"; :>> createdAt = "2026-09-19"; :>> createdBy = "claudeFable5"; :>> method = VerificationMethod::inspect; :>> procedureText = "One backlog item, sized 3: a second obligation collector in authority_queue over edges and items the Model already exposes (verify, resultof, Person), a unit test with a fixture tree, a skill paragraph, and a census-driven edge backfill across .tracking/business. Ready when the census is read before any edge is written: 94 Needs, 5 bound today, 67 in files holding a human-passed confirmation Test, 22 in files holding none - and the DoD's known-positive and known-negative are named before the tree is read."; }
    // RAN: validate=pass guard=pass clippy=pass probe=pass touched=pass
    part authorityQueueListsNeedsAwaitingAcceptanceRefineGateR1 : TestResult { :>> id = "b0c164e4-d066-430c-b341-cf2acc960071"; :>> outcome = VerdictKind::proposed; :>> judgedAgainst = "c3e4635a"; :>> judgedAt = "2026-09-19"; :>> judgedBy = "claudeFable5"; }
    verification authorityQueueListsNeedsAwaitingAcceptanceStandupGate : Test { :>> id = "7e4560f1-1be9-4192-9bfc-df17a0d25020"; :>> title = "Sprint 752 standup gate"; :>> createdAt = "2026-09-19"; :>> createdBy = "claudeFable5"; :>> method = VerificationMethod::inspect; :>> procedureText = "The row is a computed fact about a Need, never a stored flag (D0018): its predicate is the same #Verify edge plus human-judged pass that already makes a Need's verification traceable. Not grandfathered: the Business workflow always ordered requirements after accepted Needs, so a Need nobody accepted was unasked, not correct-when-written. The backfill adds edges only where an existing Test's procedureText names the set it accepts; a Need whose file holds no such Test stays a true row, and the count of those rows is the first honest reading of how much of the Need base the human has actually accepted. D0535 corrected D0534's clause naming the guard as the control; the row's predicate and the D0178 write refusal are."; }
    // RAN: validate=pass guard=pass clippy=pass probe=pass touched=pass
    part authorityQueueListsNeedsAwaitingAcceptanceStandupGateR1 : TestResult { :>> id = "cb7bd902-dce4-4481-9410-ed2ec03e8809"; :>> outcome = VerdictKind::proposed; :>> judgedAgainst = "c3e4635a"; :>> judgedAt = "2026-09-19"; :>> judgedBy = "claudeFable5"; }
    verification authorityQueueListsNeedsAwaitingAcceptanceImplementGate : Test { :>> id = "f3091fb1-a741-488a-8e21-2900e326d0a8"; :>> title = "Sprint 752 implement gate"; :>> createdAt = "2026-09-19"; :>> createdBy = "claudeFable5"; :>> method = VerificationMethod::test; :>> procedureText = "cargo test --release -p keel-view authority_queue passes with the new pair test; keel show authority-queue . read back at the landing tree lists needAcceptance rows for the three self-analysis Needs, each naming engineSelfAnalysisNeedsAccept, and no row for any Need of engine-needs or modular-members; the census script re-run reports the bound count after the backfill; gate validate clean; gate check-engine clean; sync-claude --check clean after the skill edit; the guard set passes; the touched set passes under the ladder."; }
    // RAN: validate=pass guard=pass clippy=pass probe=pass touched=pass
    part authorityQueueListsNeedsAwaitingAcceptanceImplementGateR1 : TestResult { :>> id = "36d84a87-ca6b-4a06-a1c2-18655e9a7ac1"; :>> outcome = VerdictKind::pass; :>> judgedAgainst = "c3e4635a"; :>> judgedAt = "2026-09-19"; :>> judgedBy = "claudeFable5"; }
    verification authorityQueueListsNeedsAwaitingAcceptanceReviewGate : Test { :>> id = "e273da67-fd9e-4721-b6f4-720cd9fdf525"; :>> title = "Sprint 752 review gate — three passes per D0172"; :>> createdAt = "2026-09-19"; :>> createdBy = "claudeFable5"; :>> method = VerificationMethod::inspect; :>> procedureText = "Three passes per D0172. Code read back: the collector filters Need items, walks verify edges to method=confirmation Tests, walks resultof edges to their results, and accepts only outcome pass with judgedBy resolving to a Person item; the note names the Tests or says no acceptance test; nothing is written. Edges read back: each added #Verify edge sits in the file of the Test it names, beside that Test's existing edges, and the Test's procedureText names the set the Need belongs to. Skill read back: decision-surfacing step 1 names both row kinds and the state test counts a needAcceptance row entering or leaving as a change."; }
    // RAN: validate=pass guard=pass clippy=pass probe=pass touched=pass
    part authorityQueueListsNeedsAwaitingAcceptanceReviewGateR1 : TestResult { :>> id = "cc48744d-dd11-4c8d-bc54-af8dce24bda8"; :>> outcome = VerdictKind::proposed; :>> judgedAgainst = "c3e4635a"; :>> judgedAt = "2026-09-19"; :>> judgedBy = "claudeFable5"; }
    verification authorityQueueListsNeedsAwaitingAcceptanceCloseOutGate : Test { :>> id = "bb70a7d6-7716-4341-ad47-fc01e812b526"; :>> title = "Sprint 752 closeOut gate (autonomous, D0049)"; :>> createdAt = "2026-09-19"; :>> createdBy = "claudeFable5"; :>> method = VerificationMethod::inspect; :>> procedureText = "The task's DoD result and the six gate results are recorded from the verifier's rendered receipt; issue661 resolves when the DoD passes; dcCeremonyRequirementsDeriveFromTheVerificationNeed leaves the blocked list and waits on the human's acceptance of the three Needs, which the queue now shows."; }
    // RAN: validate=pass guard=pass clippy=pass probe=pass touched=pass
    part authorityQueueListsNeedsAwaitingAcceptanceCloseOutGateR1 : TestResult { :>> id = "c9fe04ab-b18f-4d61-ade9-9dd623528025"; :>> outcome = VerdictKind::proposed; :>> judgedAgainst = "c3e4635a"; :>> judgedAt = "2026-09-19"; :>> judgedBy = "claudeFable5"; }
    verification authorityQueueListsNeedsAwaitingAcceptanceRetroGate : Test { :>> id = "0a0c7d2b-4002-4472-a77e-46587e881d66"; :>> title = "Sprint 752 retro gate (autonomous, D0049)"; :>> createdAt = "2026-09-19"; :>> createdBy = "claudeFable5"; :>> method = VerificationMethod::analyze; :>> procedureText = "One finding, avoidable issues scanned (issue011). Finding: D0534 was recorded naming the confirmation-authenticity guard as the control that refuses an AI-judged confirmation result, and a read of acceptance.rs after the record showed the guard reads Decision acceptance events only - the check ran after the claim, the order D0151 forbids. Control landed this sprint: D0535 reverses the clause by #SupersedeClause and the DoD's known-negative (an AI-judged pass does not clear the row) is the test that holds the corrected claim. No new item needed beyond D0535: the recurring class - a Decision naming a control by reputation rather than by a read of its scan - is already tracked as issue661's neighbour in the decision-authoring process; retro held."; }
    // RAN: validate=pass guard=pass clippy=pass probe=pass touched=pass
    part authorityQueueListsNeedsAwaitingAcceptanceRetroGateR1 : TestResult { :>> id = "2de2b2f7-1dc6-4590-b102-bd75e7a4a7e8"; :>> outcome = VerdictKind::proposed; :>> judgedAgainst = "c3e4635a"; :>> judgedAt = "2026-09-19"; :>> judgedBy = "claudeFable5"; }
}
