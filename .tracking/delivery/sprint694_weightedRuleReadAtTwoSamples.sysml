// ProjectDeliveryS694 — Sprint 694: Apply D0464 option B (accepted 2026-09-13): author the two #SupersedeClause edges from D0464 to D0364 and D0365, re-read the weighted rule against the tree as it stands on both bench arms, and record what falls out. What fell out is that the rule's verdict depends on the sample size - 1.1 at the bench's 50, 1.25 at 100 - so the sprint's deliverable is the measurement and a fork Decision (D0466) for the human; DOMINANCE stays 1.25. EXECUTE; 2 pts; continues dcDominanceRechosenUnderItsOwnRule (issue430), which still carries no result.. EXECUTE. 2 pts.
package ProjectDeliveryS694 {
    private import EngineElement::*;
    private import EngineWork::*;
    private import EngineVerification::*;
    private import EngineRelationships::*;

    #CharteredBy dependency from weightedRuleReadAtTwoSamplesStory to d0464;

    part weightedRuleReadAtTwoSamplesStory : Story {
        :>> id = "74ab0a97-e4b5-4c40-a3ee-34979e16d198";
        :>> title = "Sprint 694: Apply D0464 option B (accepted 2026-09-13): author the two #SupersedeClause edges from D0464 to D0364 and D0365, re-read the weighted rule against the tree as it stands on both bench arms, and record what falls out. What fell out is that the rule's verdict depends on the sample size - 1.1 at the bench's 50, 1.25 at 100 - so the sprint's deliverable is the measurement and a fork Decision (D0466) for the human; DOMINANCE stays 1.25. EXECUTE; 2 pts; continues dcDominanceRechosenUnderItsOwnRule (issue430), which still carries no result. (2 pts)";
        :>> createdAt = "2026-09-13"; :>> createdBy = "claudeFable5"; :>> kind = WorkKind::code; :>> priority = WorkPriority::p0; :>> owner = "claudeFable5"; :>> estimatedPoints = 2;
    }

    action def DeliveryRunS694 {
        action storyWeightedRuleReadAtTwoSamples;
        verification storyWeightedRuleReadAtTwoSamplesDoD : Test { :>> id = "1bbb7256-0e56-4da3-9caf-9857c40a6216"; :>> method = VerificationMethod::test; :>> procedureText = "DELIVERED: #SupersedeClause dependency from d0464 to d0364 and to d0365 in D0464's file, dated to its acceptance; the four-setting sweep re-run at 50 cases on both arms (tree 25e4c04) and the three-setting sweep at 100 cases on both arms (tree eda9647), every row with KEEL_RECALL_DOMINANCE set; the rebuilt binary's plain runs read against the 1.25 rows; the hand set read at 1.25, 1.1 and 0; D0466 recording the fork with OPTION A (read at the default, 1.1), OPTION B (read at 100, 1.25, sample becomes a clause), OPTION C (win at both), DO NOTHING, each with its COST, the six verdict lines verbatim in its research line, DependsOn D0464, held proposed. dcDominanceRechosenUnderItsOwnRuleDoD has no result: its VERIFY asks for the recorded choice's predicted lines, and the choice is the human's. knowledge.rs is not edited, not even its provenance comment, because the comment's wording depends on the answer."; }
        // RAN: recall_bench.py --sweep DOMINANCE=0,1.1,1.25,1.5 at 25e4c04 one-hop 46/46/46/46 md 3/4/3/3 top-3 30/20/27/30, --hops 2 20/24/23/20 md 5/3/4/5; --cases 100 --sweep 0,1.1,1.25 at eda9647 one-hop 89/90/90 md 2/4/3 top-3 57/39/51, --hops 2 39/53/48 md 5/3/4 top-3 3/31/18 (s692/sweep100_hop*.txt); plain runs 46/50 md 3 27/46 and 23/50 md 4 8/23; recall_ab.py 1.25 MET 7/7, 1.1 MET 7/7, 0 NOT MET 6/7; keel record decision -> D0466 proposed FORK
        part storyWeightedRuleReadAtTwoSamplesDoDR1 : TestResult { :>> id = "be4d3bf2-c470-4b7e-ab0e-cd4e56089bf5"; :>> outcome = VerdictKind::pass; :>> judgedAgainst = "eda9647"; :>> judgedAt = "2026-09-13"; :>> judgedBy = "claudeFable5"; }
    }

    verification weightedRuleReadAtTwoSamplesRefineGate : Test { :>> id = "55d92fc2-391f-4648-98fc-0e1c205e27a7"; :>> title = "Sprint 694 refine gate (DoR)"; :>> createdAt = "2026-09-13"; :>> createdBy = "claudeFable5"; :>> method = VerificationMethod::inspect; :>> procedureText = "Chartered by D0464 (accepted, option B). Two points: seven bench runs of one to four minutes each, two edges, one Decision, no code. DoR: D0464 accepted with the human's words quoting option B; the DoD on dcDominanceRechosenUnderItsOwnRule names the fork branch; recall_bench.py --sweep and --cases exist. Not a fork here: the sprint records one, it does not take one; the fork is D0466's."; }
    part weightedRuleReadAtTwoSamplesRefineGateR1 : TestResult { :>> id = "5b6998bc-92f8-4a4c-8dc3-c96f231a1c5f"; :>> outcome = VerdictKind::proposed; :>> judgedAgainst = "eda9647"; :>> judgedAt = "2026-09-13"; :>> judgedBy = "claudeFable5"; }
    verification weightedRuleReadAtTwoSamplesStandupGate : Test { :>> id = "0c9c9d16-f2c1-43e0-be7d-f482fe086034"; :>> title = "Sprint 694 standup gate"; :>> createdAt = "2026-09-13"; :>> createdBy = "claudeFable5"; :>> method = VerificationMethod::inspect; :>> procedureText = "Order: add the two SupersedeClause edges (textpatch insert-after the DependsOn lines); check-engine; sweep 0,1.1,1.25,1.5 on both arms at 50 cases; apply the weighted rule - it picks 1.1 (admissible: median 3 to 4, hits 46 held, rows 12 held, far +4; 24 against 23); that contradicts D0464's own prediction, so before touching the constant re-read at 100 cases; at 100 the rule refuses 1.1 (median 2 to 4) and keeps 1.25; read the hand set; write D0466 as a fork with COSTs; leave the constant; record the sprint; decision-surfacing."; }
    part weightedRuleReadAtTwoSamplesStandupGateR1 : TestResult { :>> id = "27373dc8-6091-4270-b0a6-50fad45f9068"; :>> outcome = VerdictKind::proposed; :>> judgedAgainst = "eda9647"; :>> judgedAt = "2026-09-13"; :>> judgedBy = "claudeFable5"; }
    verification weightedRuleReadAtTwoSamplesImplementGate : Test { :>> id = "499f5012-0cd1-4d3f-a11e-0fb903163ab9"; :>> title = "Sprint 694 implement gate"; :>> createdAt = "2026-09-13"; :>> createdBy = "claudeFable5"; :>> method = VerificationMethod::test; :>> procedureText = ".engine/decisions/0464-dominanceRuleOrDominanceBar.sysml: two #SupersedeClause edges added after the DependsOn lines with a dated comment; gate check-engine clean. RAN: python .engine/tools/recall_bench.py --sweep DOMINANCE=0,1.1,1.25,1.5 at 25e4c04 -> one-hop hits 46/46/46/46 median 3/4/3/3 top-3 30/20/27/30 rows 12, DISCRIMINATED median position moved; --hops 2 same sweep -> 20/24/23/20 median 5/3/4/5 top-3 2/15/8/2, DISCRIMINATED hits and median position moved; --cases 100 --sweep DOMINANCE=0,1.1,1.25 at eda9647 -> one-hop 89/90/90 median 2/4/3 top-3 57/39/51 rows 12; --hops 2 --cases 100 -> 39/53/48 median 5/3/4 top-3 3/31/18 (logs s692/sweep100_hop1.txt, sweep100_hop2.txt, tree sweep100_head.txt); plain runs of the rebuilt binary (25e4c04+dirty, knowledge.rs at HEAD) -> 46/50 median 3 top-3 27/46 and 23/50 median 4 top-3 8/23, the 1.25 rows; recall_ab.py -> 1.25 MET 7/7, KEEL_RECALL_DOMINANCE=1.1 MET 7/7, =0 NOT MET 6/7. keel record decision --from d_sample.md -> D0466 proposed, a FORK."; }
    // RAN: recall_bench.py --sweep DOMINANCE=0,1.1,1.25,1.5 at 25e4c04 one-hop 46/46/46/46 md 3/4/3/3 top-3 30/20/27/30, --hops 2 20/24/23/20 md 5/3/4/5; --cases 100 --sweep 0,1.1,1.25 at eda9647 one-hop 89/90/90 md 2/4/3 top-3 57/39/51, --hops 2 39/53/48 md 5/3/4 top-3 3/31/18 (s692/sweep100_hop*.txt); plain runs 46/50 md 3 27/46 and 23/50 md 4 8/23; recall_ab.py 1.25 MET 7/7, 1.1 MET 7/7, 0 NOT MET 6/7; keel record decision -> D0466 proposed FORK
    part weightedRuleReadAtTwoSamplesImplementGateR1 : TestResult { :>> id = "a647f4f6-0693-4f2e-bb25-384ca1304655"; :>> outcome = VerdictKind::pass; :>> judgedAgainst = "eda9647"; :>> judgedAt = "2026-09-13"; :>> judgedBy = "claudeFable5"; }
    verification weightedRuleReadAtTwoSamplesReviewGate : Test { :>> id = "b0484017-f1b8-4546-ac07-ad2162c908a8"; :>> title = "Sprint 694 review gate — three passes per D0172"; :>> createdAt = "2026-09-13"; :>> createdBy = "claudeFable5"; :>> method = VerificationMethod::inspect; :>> procedureText = "Three passes (D0172). Correctness: every number in D0466's research line is copied from a bench log written by the run that produced it; the 50-case rows are at one tree (25e4c04) and the 100-case rows at one tree (eda9647), named apart, and the two trees differ by four .tracking items only; every row sets the knob so the stale-stamp defect (issue516) cannot enter, and the plain runs printing the 1.25 rows exactly confirms the compiled constant. Honesty: the sprint claims a measurement and a fork, not a resolution - issue430 stays open, the DoD has no result, and D0466 says plainly that B and C are post hoc and that A chases a move that reverses between samples. Scope: D0364, D0365 and knowledge.rs unedited; the SupersedeClause edges are D0464's accepted consequence, not this sprint's judgment."; }
    part weightedRuleReadAtTwoSamplesReviewGateR1 : TestResult { :>> id = "c41e245a-c0e8-45d7-9aaa-63bf112430c5"; :>> outcome = VerdictKind::proposed; :>> judgedAgainst = "eda9647"; :>> judgedAt = "2026-09-13"; :>> judgedBy = "claudeFable5"; }
    verification weightedRuleReadAtTwoSamplesCloseOutGate : Test { :>> id = "efbe0b9d-eed0-4e05-b759-a49651f64275"; :>> title = "Sprint 694 closeOut gate (autonomous, D0049)"; :>> createdAt = "2026-09-13"; :>> createdBy = "claudeFable5"; :>> method = VerificationMethod::inspect; :>> procedureText = "Closes on gate validate, gate check-engine, gate guard --no-receipt ALL PASS over the tree holding D0466 and this sprint; no source change; D0466 in the authority queue and the brief republished with it (the pending set changed: d0460 and d0464 answered, d0463 rejected, d0465 and d0466 added)."; }
    part weightedRuleReadAtTwoSamplesCloseOutGateR1 : TestResult { :>> id = "0b210da3-a481-4034-9d60-11bbc055c955"; :>> outcome = VerdictKind::proposed; :>> judgedAgainst = "eda9647"; :>> judgedAt = "2026-09-13"; :>> judgedBy = "claudeFable5"; }
    verification weightedRuleReadAtTwoSamplesRetroGate : Test { :>> id = "c4890b6f-28d0-44ec-9b52-68bd1589431c"; :>> title = "Sprint 694 retro gate (autonomous, D0049)"; :>> createdAt = "2026-09-13"; :>> createdBy = "claudeFable5"; :>> method = VerificationMethod::analyze; :>> procedureText = "AVOIDABLE-ISSUE SCAN (D0131): one finding with empirical basis - D0464's text predicted its own option's outcome from a sweep at 33c398a, and the prediction did not survive one tree and one sample later; the human accepted the option with that prediction in front of them. That is not a defect in the rule but in what a fork brief promises: a predicted outcome of a rule is a measurement the brief should mark as taken at one SHA and one sample, or not carry. No new item - already tracked in d0466: D0466's context names the split and its consequences say the prediction is not repeated for the sample clause; the brief's falsifier field is where such a prediction belongs and the next brief carries it there. Sample-size dependence at n=50 is the retro's evidence for D0466 option B's cost line, not for a Decision of my own."; }
    part weightedRuleReadAtTwoSamplesRetroGateR1 : TestResult { :>> id = "d5a92bbb-c59a-4d28-83e0-363611c19e4e"; :>> outcome = VerdictKind::proposed; :>> judgedAgainst = "eda9647"; :>> judgedAt = "2026-09-13"; :>> judgedBy = "claudeFable5"; }
}
