// ProjectDeliveryS743 — Sprint 743: source citations on the living docs resolve - dcSourceCitationsOnTheLivingDocsResolve, chartered by D0471, resolving issue591 (the living doc surface cites source by path and line and nothing reads the citation against the tree). Before this sprint two docs - .engine/skills/project-migration/SKILL.md line 10 and .engine/processes/project-migration.sysml line 15 - cited migrate.rs lines 664-666 for check_preconditions, which D0479's move had carried to members/keel-process/src/migrate.rs line 804; tool-reference held a doc's script paths and cli-reference its keel verbs, and a .rs:N citation was read by nobody. This sprint a seventy-sixth hard guard, source-reference, reads every file.rs:N and file.rs:N-M citation on tool-reference's living surface, resolves the file through the manifest-driven corpus of every workspace member's src/ (a bare basename only when exactly one file bears it), holds the range to the file's lines, and holds the identifier cited beside it - the nearest identifier-shaped backtick span on the same line, else the last on the non-blank line above - to appear within the range; red names the doc line, the token and the line the identifier is at today. The two citations are repointed to members/keel-process/src/migrate.rs lines 804-807. D0514 is the guard's clause, recorded with the process-change marker and held proposed for the human.. EXECUTE. 3 pts.
package ProjectDeliveryS743 {
    private import EngineElement::*;
    private import EngineWork::*;
    private import EngineVerification::*;
    private import EngineRelationships::*;

    #CharteredBy dependency from sourceCitationsOnTheLivingDocsResolveStory to d0471;
    #Delivers dependency from sourceCitationsOnTheLivingDocsResolveStory to dcSourceCitationsOnTheLivingDocsResolve;

    part sourceCitationsOnTheLivingDocsResolveStory : Story {
        :>> id = "2df508d2-7aad-48a3-93ca-29eefa774541";
        :>> title = "Sprint 743: source citations on the living docs resolve - dcSourceCitationsOnTheLivingDocsResolve, chartered by D0471, resolving issue591 (the living doc surface cites source by path and line and nothing reads the citation against the tree). Before this sprint two docs - .engine/skills/project-migration/SKILL.md line 10 and .engine/processes/project-migration.sysml line 15 - cited migrate.rs lines 664-666 for check_preconditions, which D0479's move had carried to members/keel-process/src/migrate.rs line 804; tool-reference held a doc's script paths and cli-reference its keel verbs, and a .rs:N citation was read by nobody. This sprint a seventy-sixth hard guard, source-reference, reads every file.rs:N and file.rs:N-M citation on tool-reference's living surface, resolves the file through the manifest-driven corpus of every workspace member's src/ (a bare basename only when exactly one file bears it), holds the range to the file's lines, and holds the identifier cited beside it - the nearest identifier-shaped backtick span on the same line, else the last on the non-blank line above - to appear within the range; red names the doc line, the token and the line the identifier is at today. The two citations are repointed to members/keel-process/src/migrate.rs lines 804-807. D0514 is the guard's clause, recorded with the process-change marker and held proposed for the human. (3 pts)";
        :>> createdAt = "2026-09-18"; :>> createdBy = "claudeFable5"; :>> kind = WorkKind::code; :>> priority = WorkPriority::p0; :>> owner = "claudeFable5"; :>> estimatedPoints = 3;
    }

    action def DeliveryRunS743 {
        action storySourceCitationsOnTheLivingDocsResolve;
        verification storySourceCitationsOnTheLivingDocsResolveDoD : Test { :>> id = "c456fcf8-b9d6-4a20-95a2-9c9f45079ec6"; :>> method = VerificationMethod::test; :>> procedureText = "DELIVERED BACKLOG ITEMS: dcSourceCitationsOnTheLivingDocsResolve. DONE MEANS: members/keel-guards/src/surface.rs carries source_reference in FAMILY beside cli-reference with source_citations (the shapes, target/ and non-.rs excluded), cited_identifier (same line, else the line above), member_rust_sources (the corpus read from the root Cargo.toml through keel_model::corpus::workspace_members), resolve_citation (Path / Ambiguous / Missing) and source_citation_defect (the messages naming today's file, the files bearing a shared basename, a range past the end, and the identifier's line today); GUARD_NAMES in members/keel-schema/src/guard_names.rs is 76 with source-reference appended; guards.md, guard-constraints.sysml (sourceReference, guard 76) and control-map.sysml (gSourceReference) carry the row; the two issue591 citations read members/keel-process/src/migrate.rs:804-807; D0514 is recorded marked and held. cargo clippy --workspace --release --all-targets clean; cargo test -p keel-guards --release --lib 142 passed 0 failed (five new: a_stale_range_is_red_naming_todays_line_and_the_repointed_path_is_green, a_root_without_a_workspace_manifest_scans_nothing, a_moved_path_names_todays_file_a_shared_basename_asks_for_the_path_and_a_range_is_held_to_the_file, citations_are_read_in_their_shapes_and_the_identifier_is_the_nearest_in_reach, the_living_surface_cites_source_that_resolves over the real tree). Known-positive (pos743.py, chosen before the tree was read): the two claim-bearing lib tests pass and exactly two run; the guard run from the copy over the living surface extracted from HEAD - the tree before this sprint - exits red with exactly two violations, at SKILL.md:10 and project-migration.sysml:15, each saying check_preconditions is at line 804 today; over the working tree the guard passes with 3 scanned and keel version says guards: 76. Known-negative (neg743.py): a planted doc under .engine/docs carrying a target/ path, a .py:N citation and a digitless file.rs:N, and a planted .tracking file citing a stale migrate.rs:1-2, leave the scanned count at 3 and the guard green, both plants removed; the guard count rose by exactly one over the 75 GUARD_NAMES declared at HEAD. Read from the runs, not from this text: keel gate guard source-reference --no-receipt over the working tree - PASS, 3 scanned, 0 violations; keel gate guard --no-receipt - ALL PASS, exit 0; keel version - guards: 76 (67 hard-blocking, 9 warning-only)."; }
        // RAN: LADDER: keel verify . --probe-from pair743.txt -> outcome=pass stopped_at=none
        part storySourceCitationsOnTheLivingDocsResolveDoDR1 : TestResult { :>> id = "52cce430-7bfa-4e12-837b-4f4574a3d30d"; :>> outcome = VerdictKind::pass; :>> judgedAgainst = "66f74bd0"; :>> judgedAt = "2026-09-18"; :>> judgedBy = "claudeFable5"; }
    }

    verification sourceCitationsOnTheLivingDocsResolveRefineGate : Test { :>> id = "fdebe1bf-512b-4346-9be4-daf1f9e474f0"; :>> title = "Sprint 743 refine gate (DoR)"; :>> createdAt = "2026-09-18"; :>> createdBy = "claudeFable5"; :>> method = VerificationMethod::inspect; :>> procedureText = "DoR: dcSourceCitationsOnTheLivingDocsResolve was the third line of keel show whats-next at 66f74bd0 (sprint 742 landed, CI conclusion success) and the first unheld one - dcSittingReviewIsFinishedByAnalysis (D0510) and dcTheFourStayingModulesAreMembers (D0513) are held proposed on the published brief, a content gate the frontier is followed past (D0052). Chartered by D0471 through its #CharteredBy edge (backlog.sysml line 3468), whose accepted ProspectiveChange marker authorises the locked edits under D0465 - members/keel-guards/src/ (GUARD_SOURCE_DIRS), guard_names.rs (GUARD_SOURCE_FILES), the skill and the process file; #Resolves issue591; #DependsOn dcProcessIsAMember (landed, sprint 736). Sized 3 - one guard with five helpers and four lib tests in surface.rs, the GUARD_NAMES bump, three catalogue rows, two doc repoints, one held Decision; the enforcement lock is crossed and a Decision is owed, no schema change. Not split: the population, the resolution and the identifier check are one claim (a citation means the code it names) and issue591 states them as one. Blocking dependencies: none."; }
    // RAN: LADDER: keel verify . --probe-from pair743.txt -> outcome=pass stopped_at=none
    part sourceCitationsOnTheLivingDocsResolveRefineGateR1 : TestResult { :>> id = "09c5a3ea-69c1-4143-8984-ffcb0efe214e"; :>> outcome = VerdictKind::proposed; :>> judgedAgainst = "66f74bd0"; :>> judgedAt = "2026-09-18"; :>> judgedBy = "claudeFable5"; }
    verification sourceCitationsOnTheLivingDocsResolveStandupGate : Test { :>> id = "6b73b181-c68b-4be9-9d57-190c4313367f"; :>> title = "Sprint 743 standup gate"; :>> createdAt = "2026-09-18"; :>> createdBy = "claudeFable5"; :>> method = VerificationMethod::inspect; :>> procedureText = "Owner claudeFable5. Blocker: none - 66f74bd0 landed with CI conclusion success, no ladder or land running; the human's serve (pid 14600) runs from the pin cache, so the release image rebuilds freely. Order: (1) source_citations, cited_identifier, member_rust_sources, resolve_citation, source_citation_defect and the source_reference guard in surface.rs, FAMILY arm, four lib tests on a scratch workspace and the real tree; (2) GUARD_NAMES 76; (3) guards.md, guard-constraints.sysml, control-map.sysml rows; (4) the two repoints to members/keel-process/src/migrate.rs:804-807; (5) D0514 from a draft file with the marker, its #DependsOn hand lines to D0471 and D0209; (6) cargo build --release, keel-serve.exe refresh, clippy, cargo test -p keel-guards --lib, the four gate commands, keel sync-claude for the regenerated skill copy; (7) pos743.py, neg743.py, pair743.txt; (8) the sprint record with the retro filled, verifier with the pair file, recorder --owed 8, git diff --stat .tracking against the report's WROTE count (issue602), the detached commit with the CR: prefix, git status -sb, CI conclusion, then the decision-surfacing republish because the pending set gains d0514."; }
    // RAN: LADDER: keel verify . --probe-from pair743.txt -> outcome=pass stopped_at=none
    part sourceCitationsOnTheLivingDocsResolveStandupGateR1 : TestResult { :>> id = "c03a4772-39c1-4134-a2cc-6f69406df5ae"; :>> outcome = VerdictKind::proposed; :>> judgedAgainst = "66f74bd0"; :>> judgedAt = "2026-09-18"; :>> judgedBy = "claudeFable5"; }
    verification sourceCitationsOnTheLivingDocsResolveImplementGate : Test { :>> id = "8a4c2262-0816-412b-bf25-1f960fe686d9"; :>> title = "Sprint 743 implement gate"; :>> createdAt = "2026-09-18"; :>> createdBy = "claudeFable5"; :>> method = VerificationMethod::test; :>> procedureText = "The implement gate is the DoD's own probes plus the ladder: cargo build --release Finished and target/release/keel-serve.exe refreshed from it; keel version from the copy says guards: 76 (67 hard-blocking, 9 warning-only); cargo clippy --workspace --release --all-targets clean after three findings in the new code (two indexing-may-panic - the line above read through checked_sub and get, the basename match through a slice pattern - and one map_or_else); cargo test -p keel-guards --release --lib 142 passed 0 failed; cargo test -p keel-cli --release --lib 19 passed; keel gate validate 858 tracking files clean, gate check-engine clean, gate guard --no-receipt ALL PASS exit 0 with source-reference PASS 3 scanned, sync-claude --check green after keel sync-claude regenerated the project-migration skill copy under .claude/skills. The guard's first run over the real tree reddened its own catalogue row in guards.md: the row's history sentence quoted the stale token in citation shape and the guard read it as a citation of migrate.rs:664-666 beside check_preconditions, at line 804 today - the row now says lines 664-666 of a bare migrate.rs, and records that the guard caught it. The first ladder's touched rung was red - 880 passed, 23 failed, every failure an init-scaffolded project that must gate clean as its precondition: a scaffolded project receives the engine docs, which cite keel's source it does not hold, and source-reference read three Missing citations there (reproduced by keel init into a temp root and gate guard all before any claim). The guard now scans nothing under a root with no Cargo.toml, the fifth lib test a_root_without_a_workspace_manifest_scans_nothing holds both shapes, D0514's decision clause and the three catalogue rows state it, and keel init then gate guard all exits 0 with source-reference PASS 0 scanned. Two hook fires this sprint: the pre-bash hook denied two python heredocs carrying a backslash (D0309); each edit was made with the Edit or Write tool. pos743.py failed twice on its own scaffolding before its clauses were read - a git archive of HEAD extracted under the scratchpad ran past Windows MAX_PATH on a skills fixture name - and now extracts to %TEMP% directly, removed on exit; the guard's em-dash in the summary line was matched by a whitespace-bounded token after the cp1252 decode replaced it."; }
    // RAN: LADDER: keel verify . --probe-from pair743.txt -> outcome=pass stopped_at=none
    part sourceCitationsOnTheLivingDocsResolveImplementGateR1 : TestResult { :>> id = "518c6a0d-9003-4505-8910-0d5fc054ca36"; :>> outcome = VerdictKind::pass; :>> judgedAgainst = "66f74bd0"; :>> judgedAt = "2026-09-18"; :>> judgedBy = "claudeFable5"; }
    verification sourceCitationsOnTheLivingDocsResolveReviewGate : Test { :>> id = "414ec9f3-2ee1-4330-8a1f-f5f50e3daf0c"; :>> title = "Sprint 743 review gate — three passes per D0172"; :>> createdAt = "2026-09-18"; :>> createdBy = "claudeFable5"; :>> method = VerificationMethod::inspect; :>> procedureText = "Verifier receipt only: keel gate validate, check-engine, guard --no-receipt, sync-claude --check, the verify ladder with --probe-from naming pair743.txt (D0500), cargo clippy; the recorder writes this gate from the receipt. Three passes per D0172. Correctness: a stale range is red naming today's line and the repointed path is green, with a .tracking file and a target/ or .py citation uncounted (a_stale_range_is_red...); a moved path names today's file, a basename two files bear asks for the path naming both, a ghost file is missing without a today, and a range past the end names the file's length (a_moved_path_names_todays_file...); the citation shapes and the identifier reach - same line nearest, else the line above - are read as specified (citations_are_read_in_their_shapes...); the real living surface resolves (the_living_surface_cites_source_that_resolves). Honesty: the positive's red clause is read from the guard run over the tree as it stood at HEAD, extracted from git, not from a fixture built to be red; the negative plants real files in the real tree and reads the scanned count before and after; the guard count is read from keel version against the array HEAD declared. Scope: the diff crosses the enforcement lock - members/keel-guards/src/surface.rs (GUARD_SOURCE_DIRS) and members/keel-schema/src/guard_names.rs (GUARD_SOURCE_FILES) - and the process-def lock - the project-migration skill and process file - so the process-change guard needs the marked D0514 co-committed and the Story chartered by the accepted D0471 (D0465); D0514 is held proposed for the human and the sprint lands under D0471's acceptance, which is the path D0465 opened for exactly this shape."; }
    // RAN: LADDER: keel verify . --probe-from pair743.txt -> outcome=pass stopped_at=none
    part sourceCitationsOnTheLivingDocsResolveReviewGateR1 : TestResult { :>> id = "64e3faed-8bb7-43b2-a0ea-c3a649cc2f0a"; :>> outcome = VerdictKind::proposed; :>> judgedAgainst = "66f74bd0"; :>> judgedAt = "2026-09-18"; :>> judgedBy = "claudeFable5"; }
    verification sourceCitationsOnTheLivingDocsResolveCloseOutGate : Test { :>> id = "62e6c945-7946-4f3d-b76d-301ed8909afc"; :>> title = "Sprint 743 closeOut gate (autonomous, D0049)"; :>> createdAt = "2026-09-18"; :>> createdBy = "claudeFable5"; :>> method = VerificationMethod::inspect; :>> procedureText = "Landed when the verifier's receipt reads DISCREPANCIES: NONE and its probe rung row names pair743.txt, the recorder's report passes check_report.py --owed 8 and git diff --stat .tracking shows eight new TestResult parts for eight WROTE lines (issue602), git status -sb is clean after keel land and gh run list names the landing commit with conclusion success. The DoD result is recorded against dcSourceCitationsOnTheLivingDocsResolveDoD at that sha; issue591's resolution is computed from its #Resolves edge once that result lands. D0514 is recorded proposed with the process-change marker: the authority queue's pending set gains it, so decision-surfacing rebuilds the brief (facts.py, the page, check_templates.py --brief), republishes to the same URL and writes the new id set back to .keel/decision-page.toml; the link goes once at the top of the report. dcSprintNamesTheItemItDelivers is the next line of the frontier below the two held items."; }
    // RAN: LADDER: keel verify . --probe-from pair743.txt -> outcome=pass stopped_at=none
    part sourceCitationsOnTheLivingDocsResolveCloseOutGateR1 : TestResult { :>> id = "f2d38818-d169-4134-bdee-9ad51e56253f"; :>> outcome = VerdictKind::proposed; :>> judgedAgainst = "66f74bd0"; :>> judgedAt = "2026-09-18"; :>> judgedBy = "claudeFable5"; }
    verification sourceCitationsOnTheLivingDocsResolveRetroGate : Test { :>> id = "ac69123b-5add-45ea-8719-e68ab74ca93c"; :>> title = "Sprint 743 retro gate (autonomous, D0049)"; :>> createdAt = "2026-09-18"; :>> createdBy = "claudeFable5"; :>> method = VerificationMethod::analyze; :>> procedureText = "Written at close-out, before the verifier is dispatched; avoidable issues scanned (issue011), each finding a tracked item or the reason it is not. (1) The DoD said the two citations would be repointed to 805-807; line 804 is the one that names check_preconditions, and a range that excluded it would have been red under the guard it was cited to satisfy - the repoint is 804-807. No new item: the DoD's number was authored before the tree was read at HEAD, the guard is the control that caught the difference, and the record here says which line and why. (2) The DoD said the identifier must be on the same line as the citation; both real citations wrap the citation onto the line after the identifier, so a same-line rule would have made the known-positive green at HEAD - the guard reaches to the last identifier on the non-blank line above, and D0514's decision clause states that reach. No new item: the refinement is in the Decision and the catalogue row, and the test citations_are_read_in_their_shapes holds it. (3) The guard's first run over the real tree reddened its own catalogue row, which quoted the stale token in citation shape as history. Non-finding worth the sentence: the living surface is not allowed a stale citation even as history, and the row now says so - a doc that wants to quote a retired citation writes it in prose, not in the shape. (4) pos743.py failed twice on its own scaffolding (MAX_PATH under the scratchpad, an em-dash the cp1252 decode replaced) before any clause of the claim was read; neither run reached the tree. No new item: a probe that fails before its first assertion says so in its traceback and is fixed before the pair is handed to the verifier; the pair file holds the fixed probes. (5) A citation with no identifier in reach is counted and held to file and range only, a stated residual of D0514, and on this tree there is none (3 scanned, each with an identifier). Not tracked: an item that narrows the residual is owed when a citation of that shape appears and the scanned count against the violations will show it. (6) The process-change guard passed the working tree with D0514 co-present; the lock crossing is authorised twice - by the marker on D0514 and by the Story's charter to the accepted D0471 (D0465) - and the sprint lands under the second while the human holds the first. Non-finding: this is the shape D0465 was made for, recorded so the acceptance of D0514 is read as the guard's clause and not as a precondition of the landing. (7) The guard reddened 23 scaffold-and-gate tests on its first touched run: its population was defined on the self-build and nothing in the DoD or the four lib tests asked what a project that receives the engine docs but not the source would see. Tracked as the fifth test and a clause of D0514, not as a new item: the claim is now stated for both roots, and the touched set is the control that caught it. (8) The verifier's receipt called the ladder KILLED during touched with its pid dead while tasklist and keel verify --wait showed the pid alive, then restated the rung's red exit 101 as confirming the kill - the sprint 726 shape (issue575), whose control was a sentence. Tracked: issue603 with resolver dcVerifierReceiptIsCheckedAgainstTheLadder, a checker that reads the verifier's receipt against the ladder receipt and refuses one written before the ladder ended or disagreeing with its verdict; placed beside issue602's resolver."; }
    // RAN: LADDER: keel verify . --probe-from pair743.txt -> outcome=pass stopped_at=none
    part sourceCitationsOnTheLivingDocsResolveRetroGateR1 : TestResult { :>> id = "64685fef-aaae-4b0b-9587-f474adcd480e"; :>> outcome = VerdictKind::proposed; :>> judgedAgainst = "66f74bd0"; :>> judgedAt = "2026-09-18"; :>> judgedBy = "claudeFable5"; }
}
