// =====================================================================
// EngineBacklog — the engine's own construction plan, as tracked SysML data
// (the self-build dogfood). Transitioned from RESUME's prose backlog.
//
// A project plan IS a behavior, so it's an `action def`: tasks are `action`s,
// dependencies are `succession` (first/then). Each task's DoD is a method-tagged
// `verification <task>DoD : Test` (one line). Results are APPENDED, immutable
// `part <task>R<n> : TestResult` records (outcome + judgedAgainst commit) —
// re-verification appends R2, never edits R1 (Decision 0012; CR-3 2026-06-11).
// "Done" = the LATEST result is a pass. The query tool computes done/outstanding
// and SUSPECT via git-ancestry of judgedAgainst commits.
// =====================================================================
package EngineBacklog {
    private import EngineElement::*;        // enums (VerificationMethod, VerdictKind)
    private import EngineVerification::*;   // Test (criterion) + TestResult (appended record)
    private import EngineRelationships::*;  // #OrderingOnly marker

    action def EngineBuild {
        // ---- tasks ----
        action claudeMd;
        action processSpec;
        action schemaRewrite;
        action workflows;
        action validatorFix;
        action autoPush;
        action whatsNextV2;
        action testModel;
        action instanceAware;
        action schemaAudit;
        action instanceMigration;
        action queryTools;

        // ---- dependencies (succession: earlier then later) ----
        first claudeMd then processSpec;
        first processSpec then schemaRewrite;
        first schemaRewrite then workflows;
        first workflows then whatsNextV2;
        first whatsNextV2 then schemaAudit;
        first whatsNextV2 then testModel;
        // Restored 2026-06-11 (CR-4): this TRUE ordering fact was deleted on 2026-06-10 to
        // silence a false SUSPECT — workaround-by-deletion anti-pattern. Tagged #OrderingOnly:
        // it gates ordering but does NOT carry suspicion (D0005).
        #OrderingOnly first schemaAudit then testModel;
        first testModel then instanceAware;
        first whatsNextV2 then instanceAware;
        first schemaAudit then instanceMigration;
        first instanceAware then queryTools;

        // ---- acceptance (DoD) per task: method + recorded result (verifiedAtCommit) ----
        // (done/outstanding is COMPUTED by query.py - never narrated here)
        verification claudeMdDoD : Test { :>> id = "05bcb12e-1d2a-4cda-bfe8-06762c27d7c0"; :>> method = VerificationMethod::confirmation; :>> procedureText = "interaction discipline + triage accepted"; }
        part claudeMdR1 : TestResult { :>> id = "b5d37e1b-4a60-43d4-a0df-6cbaedcbc93f"; :>> outcome = VerdictKind::pass; :>> judgedAgainst = "2f762a6"; :>> judgedAt = "2026-06-10"; :>> judgedBy = "user"; }
        verification processSpecDoD : Test { :>> id = "f1847f4f-ca6f-45a5-af44-3179f327503a"; :>> method = VerificationMethod::confirmation; :>> procedureText = "process-model spec reviewed + accepted"; }
        part processSpecR1 : TestResult { :>> id = "67a24ab4-c724-48c1-80ca-2917724a9844"; :>> outcome = VerdictKind::pass; :>> judgedAgainst = "2f762a6"; :>> judgedAt = "2026-06-10"; :>> judgedBy = "user"; }
        part processSpecR2 : TestResult { :>> id = "ad89c4e1-a307-4be7-ba10-841ad54392e3"; :>> outcome = VerdictKind::pass; :>> judgedAgainst = "9837c17"; :>> judgedAt = "2026-06-11"; :>> judgedBy = "user"; }
        verification schemaRewriteDoD : Test { :>> id = "fbe432d5-a06b-4040-829b-b34a8fa4e249"; :>> method = VerificationMethod::test; :>> procedureText = "validate_schema 12/12 green"; }
        part schemaRewriteR1 : TestResult { :>> id = "74453aef-9251-4a4c-a428-8166b213a66f"; :>> outcome = VerdictKind::pass; :>> judgedAgainst = "2f762a6"; :>> judgedAt = "2026-06-10"; :>> judgedBy = "validate_schema"; }
        part schemaRewriteR2 : TestResult { :>> id = "73d8d665-b91e-4f51-ac01-4f358c8705fc"; :>> outcome = VerdictKind::pass; :>> judgedAgainst = "61850f4"; :>> judgedAt = "2026-06-11"; :>> judgedBy = "validate_schema"; }
        verification workflowsDoD : Test { :>> id = "bc582068-cf14-4cfc-a760-128b46fb9142"; :>> method = VerificationMethod::test; :>> procedureText = "validate_workflows 7/7 green"; }
        part workflowsR1 : TestResult { :>> id = "ada27b24-9192-4074-8a36-3350eccbd596"; :>> outcome = VerdictKind::pass; :>> judgedAgainst = "2f762a6"; :>> judgedAt = "2026-06-10"; :>> judgedBy = "validate_workflows"; }
        part workflowsR2 : TestResult { :>> id = "d8928c85-e00b-44ae-a88c-86a6aa32a165"; :>> outcome = VerdictKind::pass; :>> judgedAgainst = "61850f4"; :>> judgedAt = "2026-06-11"; :>> judgedBy = "validate_workflows"; }
        verification validatorFixDoD : Test { :>> id = "d4f32a8c-98c0-43b7-8509-a891f18d0622"; :>> method = VerificationMethod::demo; :>> procedureText = "validator returns cleanly; zero orphaned JVMs"; }
        part validatorFixR1 : TestResult { :>> id = "efad84f0-4118-46ff-9618-75dd13230641"; :>> outcome = VerdictKind::pass; :>> judgedAgainst = "2f762a6"; :>> judgedAt = "2026-06-10"; :>> judgedBy = "demo"; }
        verification autoPushDoD : Test { :>> id = "91807c1d-809c-4391-bac5-8d94e9c65a9d"; :>> method = VerificationMethod::demo; :>> procedureText = "a commit triggers an automatic push"; }
        part autoPushR1 : TestResult { :>> id = "ce9b6cec-dbca-4886-8469-a0fdde41bbb3"; :>> outcome = VerdictKind::pass; :>> judgedAgainst = "2f762a6"; :>> judgedAt = "2026-06-10"; :>> judgedBy = "demo"; }
        verification whatsNextV2DoD : Test { :>> id = "a979f11a-1c5a-407a-a0e2-fe2cc9e4fe8e"; :>> method = VerificationMethod::test; :>> procedureText = "resolver lays out all workflows incl. parallelism; clean exit"; }
        part whatsNextV2R1 : TestResult { :>> id = "5e0c9fff-f9df-48cd-be57-cfbb55106010"; :>> outcome = VerdictKind::pass; :>> judgedAgainst = "2f762a6"; :>> judgedAt = "2026-06-10"; :>> judgedBy = "whats_next"; }
        part whatsNextV2R2 : TestResult { :>> id = "5462250c-ec8a-4e62-a6c7-60efb9ab4c23"; :>> outcome = VerdictKind::pass; :>> judgedAgainst = "61850f4"; :>> judgedAt = "2026-06-11"; :>> judgedBy = "whats_next"; }

        verification testModelDoD : Test { :>> id = "6f958fe9-6654-4e9f-b133-61f426941ec7"; :>> method = VerificationMethod::confirmation; :>> procedureText = "verification model decided + native grammar validated"; }
        part testModelR1 : TestResult { :>> id = "ceabbeff-5030-40ba-83f2-073d00fb5339"; :>> outcome = VerdictKind::pass; :>> judgedAgainst = "0f5c7d1"; :>> judgedAt = "2026-06-10"; :>> judgedBy = "user"; }
        part testModelR2 : TestResult { :>> id = "3ccf4138-df0f-4614-8686-29617ca0c1f8"; :>> outcome = VerdictKind::pass; :>> judgedAgainst = "9837c17"; :>> judgedAt = "2026-06-11"; :>> judgedBy = "user"; }
        verification instanceAwareDoD : Test { :>> id = "2fe9a46e-ac18-4ad0-97ef-648f981bb011"; :>> method = VerificationMethod::test; :>> procedureText = "query DISCOVERS work-item backlogs from .tracking/*.sysml (action defs) and emits OUTSTANDING + SUSPECT; no hardcoded target; --target focuses one; item + override verified"; }
        part instanceAwareR1 : TestResult { :>> id = "a2dc3fbc-edf2-4b15-b373-1a59cd307e4c"; :>> outcome = VerdictKind::pass; :>> judgedAgainst = "adc35ab"; :>> judgedAt = "2026-06-11"; :>> judgedBy = "demo"; }
        part instanceAwareR2 : TestResult { :>> id = "3878c7f0-8f75-478c-895a-09d04b7e94d8"; :>> outcome = VerdictKind::pass; :>> judgedAgainst = "61850f4"; :>> judgedAt = "2026-06-11"; :>> judgedBy = "demo"; }
        verification schemaAuditDoD : Test { :>> id = "d9789ded-30e3-4562-8e91-dafe7ee2418c"; :>> method = VerificationMethod::confirmation; :>> procedureText = "schema types aligned with natives"; }
        part schemaAuditR1 : TestResult { :>> id = "043dfc68-b309-4694-96be-c07bc50b8e25"; :>> outcome = VerdictKind::pass; :>> judgedAgainst = "72bb02b"; :>> judgedAt = "2026-06-10"; :>> judgedBy = "user"; }
        part schemaAuditR2 : TestResult { :>> id = "25ffac6e-9c74-4b8d-a466-744a2d8e4fdc"; :>> outcome = VerdictKind::pass; :>> judgedAgainst = "9837c17"; :>> judgedAt = "2026-06-11"; :>> judgedBy = "user"; }
        verification instanceMigrationDoD : Test { :>> id = "8dbe21dd-34ab-4194-8ab4-632d3332b13a"; :>> method = VerificationMethod::test; :>> procedureText = "all 14 instance files (10 decisions + 3 processes + skills-registry) migrated to flat Engine<Concern> packages; parse green via validate_instances (14/14); Gate/GateCheck reconceived as Process/ProcessStep; legacy validate_sysml.py retired"; }
        part instanceMigrationR1 : TestResult { :>> id = "5d946440-0d31-452e-b187-2ce18b837a0a"; :>> outcome = VerdictKind::pass; :>> judgedAgainst = "e39a49e"; :>> judgedAt = "2026-06-11"; :>> judgedBy = "validate_instances"; }
        part instanceMigrationR2 : TestResult { :>> id = "57120ab4-7f6f-43b9-a065-58412d1b55c7"; :>> outcome = VerdictKind::pass; :>> judgedAgainst = "61850f4"; :>> judgedAt = "2026-06-11"; :>> judgedBy = "validate_instances"; }
        verification queryToolsDoD : Test { :>> id = "c32a8e54-e768-49b9-97b1-9896c3c49526"; :>> method = VerificationMethod::demo; :>> procedureText = "general query layer answers item/downstream/trace/suspect/outstanding (+ whats-next); verified on whatsNextV2/schemaAudit"; }
        part queryToolsR1 : TestResult { :>> id = "1c4a228c-4e12-4ef1-afe3-0a4598d60abf"; :>> outcome = VerdictKind::pass; :>> judgedAgainst = "35f5d54"; :>> judgedAt = "2026-06-11"; :>> judgedBy = "demo"; }
        part queryToolsR2 : TestResult { :>> id = "e9922863-01ee-4b7c-a952-820d348a471d"; :>> outcome = VerdictKind::pass; :>> judgedAgainst = "61850f4"; :>> judgedAt = "2026-06-11"; :>> judgedBy = "demo"; }

        // ---- schemaAudit critique findings (2026-06-10): native SysML v2 leverage ----
        // All depend on schemaAudit (the native-metaclass migration). strongTyping is
        // foundational; views expose traces; checkable reqs build on typed constraints.
        action strongTyping;     // enum def + typed Actor refs + value types (no more String-everywhere)
        action nativeTrace;      // native derive/refine/trace/satisfy/verify relationships (B)
        action nativeViews;      // view def / viewpoint / expose for the materialized-view layer (A)
        action checkableReqs;    // requirements carry require/assume evaluable constraints (C)
        action analysisCalc;     // computed derivations as native calc/analysis def
        action nativeAlloc;      // architecture allocate + interface def / connection
        action temporalModel;    // decide: native occurrence/snapshot/timeslice vs git-only ancestry
        action sec26Materialize; // add a sanctioned materialized-view sentence to CLAUDE.md §2.6
        action userCapture;      // capture acting user (git piggyback; fallback .env/prompt) -> actor registry

        first schemaAudit then strongTyping;
        first strongTyping then userCapture;
        first schemaAudit then nativeTrace;
        first schemaAudit then analysisCalc;
        first schemaAudit then nativeAlloc;
        first schemaAudit then temporalModel;
        first strongTyping then checkableReqs;
        first strongTyping then nativeViews;
        first nativeTrace then nativeViews;

        verification strongTypingDoD : Test { :>> id = "c6c995e7-f59d-4905-aea8-0de7bb1aa01d"; :>> method = VerificationMethod::test; :>> procedureText = "enum def closed-sets + value types (Uuid/Timestamp) adopted across schema/core; validates 12/12 green (typed Actor ref deferred to userCapture)"; }
        part strongTypingR1 : TestResult { :>> id = "8f88b479-02a0-4a23-99c7-ed437bbea5b9"; :>> outcome = VerdictKind::pass; :>> judgedAgainst = "c4d2f75"; :>> judgedAt = "2026-06-10"; :>> judgedBy = "validate_schema"; }
        part strongTypingR2 : TestResult { :>> id = "6bf73364-4322-410c-9c44-27cea4db4f9d"; :>> outcome = VerdictKind::pass; :>> judgedAgainst = "61850f4"; :>> judgedAt = "2026-06-11"; :>> judgedBy = "validate_schema"; }
        verification nativeTraceDoD : Test { :>> id = "be31ddee-9404-443f-b2a6-156a799a3ccd"; :>> method = VerificationMethod::test; :>> procedureText = "edge strategy set + documented in relationships.sysml: satisfy (native stmt) + verify (native verification objective) confirmed parsing; derive/refine/trace are v1-only -> :>/deferred; allocate/dependsOn/supersede stay markers; schema validates 12/12 green"; }
        part nativeTraceR1 : TestResult { :>> id = "0e8cb659-0a2c-4c30-9d66-a8ccf567d4c2"; :>> outcome = VerdictKind::pass; :>> judgedAgainst = "c4ea4c7"; :>> judgedAt = "2026-06-10"; :>> judgedBy = "validate_schema"; }
        part nativeTraceR2 : TestResult { :>> id = "064b2863-2f6a-43f6-a1a4-d36be90eab19"; :>> outcome = VerdictKind::pass; :>> judgedAgainst = "61850f4"; :>> judgedAt = "2026-06-11"; :>> judgedBy = "validate_schema"; }
        verification nativeViewsDoD : Test { :>> id = "ef5d25c2-cb69-4d01-8fab-0adf3f42cce2"; :>> method = VerificationMethod::demo; :>> procedureText = "engine views declared as native view def anchors (Outstanding/Suspect/Trace) + viewpoint in computed.sysml; expose/render NOT in pilot grammar so bodies stay computed by query.py (deferred to newer toolchain); 13/13 green"; }
        part nativeViewsR1 : TestResult { :>> id = "435d78fd-f31e-480d-a74c-cf3434e37ef4"; :>> outcome = VerdictKind::pass; :>> judgedAgainst = "71ad96d"; :>> judgedAt = "2026-06-11"; :>> judgedBy = "demo"; }
        part nativeViewsR2 : TestResult { :>> id = "f4dc5da9-4fbe-4c05-b9ba-c30e2e59a1dc"; :>> outcome = VerdictKind::pass; :>> judgedAgainst = "61850f4"; :>> judgedAt = "2026-06-11"; :>> judgedBy = "demo"; }
        verification checkableReqsDoD : Test { :>> id = "ca1f5ca8-14fa-41d4-a3c1-8441cf6a0f08"; :>> method = VerificationMethod::test; :>> procedureText = "concrete requirements may carry native require/assume constraints (parses, _spike_trace.py); documented in requirements.sysml; evaluation is solver-dependent (external SysIDE), not the kernel; schema 12/12 green"; }
        part checkableReqsR1 : TestResult { :>> id = "f8215086-a2df-4fc2-b9ff-0f6106e288bc"; :>> outcome = VerdictKind::pass; :>> judgedAgainst = "f0044f4"; :>> judgedAt = "2026-06-10"; :>> judgedBy = "validate_schema"; }
        part checkableReqsR2 : TestResult { :>> id = "1c47c046-1ad2-46cc-b7e7-be1c3fa1935d"; :>> outcome = VerdictKind::pass; :>> judgedAgainst = "61850f4"; :>> judgedAt = "2026-06-11"; :>> judgedBy = "validate_schema"; }
        verification analysisCalcDoD : Test { :>> id = "9ee093f2-9347-408f-a779-1c23589f530f"; :>> method = VerificationMethod::demo; :>> procedureText = "derivations expressed as native calc/analysis defs (RequirementCoverage calc w/ expression + SuspicionSweep analysis) in computed.sysml; 13/13 green"; }
        part analysisCalcR1 : TestResult { :>> id = "9fd5a686-e8eb-41ad-ab93-7896b4f70f24"; :>> outcome = VerdictKind::pass; :>> judgedAgainst = "71ad96d"; :>> judgedAt = "2026-06-11"; :>> judgedBy = "validate_schema"; }
        part analysisCalcR2 : TestResult { :>> id = "d172765c-1cce-4fe1-8e40-0dbaa4da14b8"; :>> outcome = VerdictKind::pass; :>> judgedAgainst = "61850f4"; :>> judgedAt = "2026-06-11"; :>> judgedBy = "demo"; }
        verification nativeAllocDoD : Test { :>> id = "e69e0039-a7da-4308-85a3-629d004c4b25"; :>> method = VerificationMethod::test; :>> procedureText = "native allocate X to Y + allocation def + connect + interface def(>=2 ends) confirmed parsing; allocation def anchor in EngineArchitecture; ICD/matrix stay computed; 13/13 green"; }
        part nativeAllocR1 : TestResult { :>> id = "c5a32d4b-8828-4459-ac38-fe981ac4f624"; :>> outcome = VerdictKind::pass; :>> judgedAgainst = "71ad96d"; :>> judgedAt = "2026-06-11"; :>> judgedBy = "validate_schema"; }
        part nativeAllocR2 : TestResult { :>> id = "1aa1eb62-3b89-4564-bc58-5c1e77cd2f8b"; :>> outcome = VerdictKind::pass; :>> judgedAgainst = "61850f4"; :>> judgedAt = "2026-06-11"; :>> judgedBy = "validate_schema"; }
        verification temporalModelDoD : Test { :>> id = "aa2e1808-792a-4b06-a544-4c91f24c25ee"; :>> method = VerificationMethod::confirmation; :>> procedureText = "DECIDED stay git-only (merge-base ancestry) for the engine timeline; native occurrence/snapshot/timeslice noted as available for deliverable/subject-version modeling, not the engine clock"; }
        part temporalModelR1 : TestResult { :>> id = "5d710f54-f27e-4d1b-9143-fcb6c248e2ad"; :>> outcome = VerdictKind::pass; :>> judgedAgainst = "0e8b24c"; :>> judgedAt = "2026-06-11"; :>> judgedBy = "user"; }
        part temporalModelR2 : TestResult { :>> id = "623fddac-d65a-4525-9227-ea26a3711705"; :>> outcome = VerdictKind::pass; :>> judgedAgainst = "9837c17"; :>> judgedAt = "2026-06-11"; :>> judgedBy = "user"; }
        // ---- 2026-06-11 architectural critique: 13 CRs, ALL ACCEPTED BY USER ----
        // (docs/design-history/2026-06-11-architectural-critique.md §4; suggested order = chain below)
        action crWritePath;        // CR-1  validate_tracking preloads schema; recursive globs; .tracking template
        action crKillState;        // CR-7  delete currentState/updatedAt; fix agile "set state" steps
        action crTruthDocs;        // CR-9  docs vs git reality (.tracking policy, banner, usage.md, RESUME, lying comments)
        action crBootstrapHole;    // CR-13 semantics-changing tooling = CHANGE (§3e)
        action crDecisions;        // CR-8  backfill Decisions 0011+; CR acceptance artifacts henceforth
        action crTypeUniverse;     // CR-2  schema/core canonical; retire _meta shadow item defs
        action crVerification;     // CR-3  appended TestResults replace mutable DoD verdicts; method enum
        action crSuspicion;        // CR-4  D0005-honest suspicion + evidence validation
        action crIdentity;         // CR-5  UUIDs on instances; qualified keying; Person actors
        action crCursor;           // CR-6  .tracking state cursor + query orient
        action crProcessHonesty;   // CR-10 registry real skills; agile rebased; evaluability labels
        action crValidateAll;      // CR-11 validate_all; pre-commit; JVM hygiene
        action crNativeWins;       // CR-12 doc clauses; typed refs; finish enums; metadata spike; STPA refs; marker examples

        first crWritePath then crKillState;
        first crKillState then crTruthDocs;
        first crTruthDocs then crBootstrapHole;
        first crBootstrapHole then crDecisions;
        first crDecisions then crTypeUniverse;
        first crTypeUniverse then crVerification;
        first crVerification then crSuspicion;
        first crSuspicion then crIdentity;
        first crIdentity then crCursor;
        first crCursor then crProcessHonesty;
        first crProcessHonesty then crValidateAll;
        first crValidateAll then crNativeWins;

        verification crWritePathDoD : Test { :>> id = "a8030800-ace9-4bbc-860e-a6dc89d4d6d0"; :>> method = VerificationMethod::test; :>> procedureText = "a schema/core-typed instance in .tracking passes validate_tracking; subdirs scanned; template exists"; }
        part crWritePathR1 : TestResult { :>> id = "2865943a-8782-407e-86cd-4ab5c3245459"; :>> outcome = VerdictKind::pass; :>> judgedAgainst = "1037d2d"; :>> judgedAt = "2026-06-11"; :>> judgedBy = "validate_tracking"; }
        verification crKillStateDoD : Test { :>> id = "c6d15c83-1fce-4fcf-be7f-d3872eea9514"; :>> method = VerificationMethod::test; :>> procedureText = "currentState/updatedAt gone from Element + Tracked bases; agile steps no longer author state; all green"; }
        part crKillStateR1 : TestResult { :>> id = "8a61de7b-c4f7-455f-bd77-4518f8d10d5c"; :>> outcome = VerdictKind::pass; :>> judgedAgainst = "4ef8679"; :>> judgedAt = "2026-06-11"; :>> judgedBy = "validate_schema"; }
        verification crTruthDocsDoD : Test { :>> id = "faa089be-ff02-471b-a2f6-017150ebb853"; :>> method = VerificationMethod::inspect; :>> procedureText = "docs match git reality; .tracking policy decided + recorded; usage.md valid; RESUME thinned; lying comments gone; EngineDocSync process added + tied into DoD and CLAUDE.md §4"; }
        part crTruthDocsR1 : TestResult { :>> id = "80032c4f-65f3-49f2-a169-0c3515c8d721"; :>> outcome = VerdictKind::pass; :>> judgedAgainst = "99e6ed7"; :>> judgedAt = "2026-06-11"; :>> judgedBy = "validate_instances"; }
        verification crBootstrapHoleDoD : Test { :>> id = "7a96d253-8d2d-4f48-95ac-636fa25a8d89"; :>> method = VerificationMethod::inspect; :>> procedureText = "CLAUDE.md §3e routes computed-view semantics changes as CHANGE"; }
        part crBootstrapHoleR1 : TestResult { :>> id = "830226a2-0fb8-4cf7-8380-ddee07668c3d"; :>> outcome = VerdictKind::pass; :>> judgedAgainst = "0a3aee2"; :>> judgedAt = "2026-06-11"; :>> judgedBy = "inspect"; }
        verification crDecisionsDoD : Test { :>> id = "5e87ae46-69f3-4a87-8c23-2a7015313c91"; :>> method = VerificationMethod::test; :>> procedureText = "Decisions 0011-0017 backfilled and parse green (24/24); CR-acceptance discipline recorded in CLAUDE.md §4"; }
        part crDecisionsR1 : TestResult { :>> id = "2e7b0ad8-8821-4f49-8fa5-2d4cbe7cbfe0"; :>> outcome = VerdictKind::pass; :>> judgedAgainst = "a092fc2"; :>> judgedAt = "2026-06-11"; :>> judgedBy = "validate_instances"; }
        verification crTypeUniverseDoD : Test { :>> id = "c1603e83-b2b6-490a-b879-490941f19bd9"; :>> method = VerificationMethod::test; :>> procedureText = "_meta shadow item defs retired; workflows typed by schema/core; workflows + tracking validate green"; }
        part crTypeUniverseR1 : TestResult { :>> id = "f48c1225-cd53-4fb6-8f90-6bf7c241831e"; :>> outcome = VerdictKind::pass; :>> judgedAgainst = "6f965c0"; :>> judgedAt = "2026-06-11"; :>> judgedBy = "validate_workflows"; }
        verification crVerificationDoD : Test { :>> id = "1e4afc6d-88c0-4b87-bbcf-899f4ba5996a"; :>> method = VerificationMethod::test; :>> procedureText = "DoD verdicts are appended TestResult records (immutable); method uses VerificationMethod enum; query computes done from results; all green"; }
        part crVerificationR1 : TestResult { :>> id = "0aa3a7eb-789d-4a55-81c2-0d4239419e70"; :>> outcome = VerdictKind::pass; :>> judgedAgainst = "df27aa2"; :>> judgedAt = "2026-06-11"; :>> judgedBy = "validate_tracking"; }
        verification crSuspicionDoD : Test { :>> id = "9d2f42e6-995a-4670-a2d6-f125ebcd5282"; :>> method = VerificationMethod::test; :>> procedureText = "suspicion = material change (git) over satisfy/:> + #OrderingOnly honored + transitive; verifiedAtCommit SHAs validated (INVALID-EVIDENCE bucket); ordering edge restored"; }
        part crSuspicionR1 : TestResult { :>> id = "3c377112-96e8-4df6-9408-512a6801a781"; :>> outcome = VerdictKind::pass; :>> judgedAgainst = "61850f4"; :>> judgedAt = "2026-06-11"; :>> judgedBy = "_test_suspect"; }
        verification crIdentityDoD : Test { :>> id = "072cbb2a-8b34-4b8c-871c-c32857c8c433"; :>> method = VerificationMethod::test; :>> procedureText = "all instances carry :>> id UUIDs; tooling keys qualified; actor registry = Person parts; validators warn on missing id"; }
        part crIdentityR1 : TestResult { :>> id = "6d261f2d-895d-428d-9630-d24b1e8a162d"; :>> outcome = VerdictKind::pass; :>> judgedAgainst = "bc4b6ca"; :>> judgedAt = "2026-06-11"; :>> judgedBy = "validate_instances"; }
        verification crCursorDoD : Test { :>> id = "6eea640e-6f23-484b-80b7-f847b7df3954"; :>> method = VerificationMethod::demo; :>> procedureText = ".tracking/state.sysml cursor exists; query orient merges cursor + ready + suspect"; }
        part crCursorR1 : TestResult { :>> id = "e0c715f9-d583-43c4-b1f7-b29306d16f41"; :>> outcome = VerdictKind::pass; :>> judgedAgainst = "bd47bae"; :>> judgedAt = "2026-06-11"; :>> judgedBy = "demo"; }
        verification crProcessHonestyDoD : Test { :>> id = "492294a7-4f39-46ae-a3eb-630a329d47d4"; :>> method = VerificationMethod::inspect; :>> procedureText = "registry lists the 5 real skills (phantoms gone); agile process matches main-only reality; DoR/DoD steps carry evaluability labels"; }
        part crProcessHonestyR1 : TestResult { :>> id = "08ee8c66-a5cb-4ec2-aa52-973cbd136086"; :>> outcome = VerdictKind::pass; :>> judgedAgainst = "0a509b1"; :>> judgedAt = "2026-06-11"; :>> judgedBy = "validate_instances"; }
        verification crValidateAllDoD : Test { :>> id = "3e8e94f9-8437-48a3-a054-3fc1559c661b"; :>> method = VerificationMethod::test; :>> procedureText = "validate_all runs all layers on one kernel; pre-commit validates staged layers; stale-kernel sweep exists; no orphan JVM after interrupt"; }
        part crValidateAllR1 : TestResult { :>> id = "1d64783a-5f52-4434-b771-49c9fdd8a710"; :>> outcome = VerdictKind::pass; :>> judgedAgainst = "4a9332d"; :>> judgedAt = "2026-06-11"; :>> judgedBy = "validate_all"; }
        verification crNativeWinsDoD : Test { :>> id = "96654b2b-9a04-4bd9-9304-b305ad89d430"; :>> method = VerificationMethod::test; :>> procedureText = "doc clauses on semantics-bearing elements; typed refs replace name-strings; remaining enums authored + strongTyping DoD statement superseded; metadata-def spike verdict; STPA control-loop refs; one worked example per marker; all green"; }
        part crNativeWinsR1 : TestResult { :>> id = "c778d275-9071-4185-a887-4b787aecc9f5"; :>> outcome = VerdictKind::pass; :>> judgedAgainst = "165a83f"; :>> judgedAt = "2026-06-11"; :>> judgedBy = "validate_all"; }

        verification sec26MaterializeDoD : Test { :>> id = "77a68ad8-aa36-44c0-b652-9c91a70a81db"; :>> method = VerificationMethod::confirmation; :>> procedureText = "CLAUDE.md §2.6 gains a sanctioned marked-materialized-view clause"; }
        part sec26MaterializeR1 : TestResult { :>> id = "cbb2d6ae-0683-413c-a33d-103662bfcaeb"; :>> outcome = VerdictKind::pass; :>> judgedAgainst = "062b97f"; :>> judgedAt = "2026-06-10"; :>> judgedBy = "user"; }
        verification userCaptureDoD : Test { :>> id = "e98cf42d-d21e-4eae-b297-d999da56047c"; :>> method = VerificationMethod::demo; :>> procedureText = "capture_user.py captures the acting user from git EFFECTIVE identity (git var GIT_COMMITTER_IDENT — config is often unset; fallback .env/prompt) + idempotently registers in .tracking/actors.sysml ActorId enum; demonstrated (wweatherholtz); parses via validate_tracking. Wiring authoredBy/verifiedBy to ActorId deferred to instanceMigration"; }
        part userCaptureR1 : TestResult { :>> id = "78f73f4e-84c5-4eca-9439-f3adc4e58fbb"; :>> outcome = VerdictKind::pass; :>> judgedAgainst = "3e40ff7"; :>> judgedAt = "2026-06-11"; :>> judgedBy = "demo"; }
        part userCaptureR2 : TestResult { :>> id = "3a019ce5-42fd-4599-82a7-c3b19ca892b5"; :>> outcome = VerdictKind::pass; :>> judgedAgainst = "61850f4"; :>> judgedAt = "2026-06-11"; :>> judgedBy = "demo"; }
        action p0ClaudeScaffold;
        verification p0ClaudeScaffoldDoD : Test { :>> id = "21c06b1e-20d4-470b-bbde-2793ca5f1b1e"; :>> method = VerificationMethod::test; :>> procedureText = "DONE MEANS: keel init scaffolds .claude/settings.json with FIVE hook events including SubagentStop, the keel output style, keel-owned permission rules plus the protected-path deny list, one .claude/skills/<name>/SKILL.md per skills-registry entry with counts asserted equal, the optional single-vendor CI template (validate + guard + rules + audit-history; rules step activates with p1RulesWired), and the fire-ledger emit plumbing writing hook fire/block/override events to .keel/metrics keyed by session id and event type. Behavioral acceptance on Windows AND Linux: skills discoverable in a live Claude Code session; hooks demonstrably fire (fire-ledger evidence) in a spawned claude -p session. Chartered by d0174."; }
        part p0ClaudeScaffoldDoDR1 : TestResult { :>> id = "158afdf1-f255-4657-a4b3-c6870929c7d2"; :>> outcome = VerdictKind::pass; :>> judgedAgainst = "11f4cac"; :>> judgedAt = "2026-08-21"; :>> judgedBy = "claudeFable5"; }
        action p0SyncClaude;
        verification p0SyncClaudeDoD : Test { :>> id = "6b0543fd-e49f-45ea-938f-44d6e93b4006"; :>> method = VerificationMethod::test; :>> procedureText = "DONE MEANS: keel sync-claude deep-merges keel-owned entries only (hook commands invoking keel hook, the keel output style, keel-named permission rules), stamps the generator version, and reports version skew as a regenerate obligation, not a violation; a downstream user's own hooks and permissions survive regeneration byte-for-byte; sync-claude --check is registered as ONE guard - no second drift surface. Chartered by d0174."; }
        part p0SyncClaudeDoDR1 : TestResult { :>> id = "ddb50edb-426f-4b7d-b0a7-24adc5ab0554"; :>> outcome = VerdictKind::pass; :>> judgedAgainst = "11f4cac"; :>> judgedAt = "2026-08-21"; :>> judgedBy = "claudeFable5"; }
        action p0FailLoud;
        verification p0FailLoudDoD : Test { :>> id = "dfa6307b-c955-417b-a53d-a46e64cfe713"; :>> method = VerificationMethod::test; :>> procedureText = "DONE MEANS: every scaffolded hook resolves the binary via absolute KEEL_BIN then PATH - never a cwd-relative target/ probe; the protected-path PreToolUse test is pure shell needing no binary (deny-by-default with a loud message when keel is unresolvable); a missing binary emits a visible warning, never a silent pass; the scaffolded pre-commit exits 1 with a remedy line naming the documented install path; init sets core.hooksPath when .git exists and orient warns loudly when unset. Chartered by d0174."; }
        part p0FailLoudDoDR1 : TestResult { :>> id = "6e596067-3ae2-4ef4-8f28-1a03a09b4500"; :>> outcome = VerdictKind::pass; :>> judgedAgainst = "11f4cac"; :>> judgedAt = "2026-08-21"; :>> judgedBy = "claudeFable5"; }
        action p0Profiles;
        verification p0ProfilesDoD : Test { :>> id = "771035ec-33c3-428f-abe7-4382136eb2a9"; :>> method = VerificationMethod::test; :>> procedureText = "DONE MEANS: keel init --profile strict|guided is explicit, printed, and recorded as a declared model-visible fact in a contract file; the default applies only to a provably empty directory (strict - init_smoke proves the scaffold starts green); any directory with existing content requires the flag; guided is advisory-first with a one-command promotion that cites PM evidence. Profile selection is NEVER inferred (the issue089/129 lockout class dies here). Chartered by d0174."; }
        part p0ProfilesDoDR1 : TestResult { :>> id = "baaa0d96-02ea-484c-baa6-692d17d78677"; :>> outcome = VerdictKind::pass; :>> judgedAgainst = "11f4cac"; :>> judgedAt = "2026-08-21"; :>> judgedBy = "claudeFable5"; }
        action p0InstallDocs;
        verification p0InstallDocsDoD : Test { :>> id = "3a5e39b3-f08b-4b2d-9b36-70cd11f64329"; :>> method = VerificationMethod::inspect; :>> procedureText = "DONE MEANS: the downstream install path is documented against the EXISTING verified release channel (v0.1.0-v0.2.3; sprint259/sprint264 evidence); every scaffolded remedy text points at it; the release-cadence/latest-version expectation is stated; scope stays inside the D-P0b fence - no package managers, no auto-update, no install scripts. Chartered by d0175."; }
        part p0InstallDocsDoDR1 : TestResult { :>> id = "2db0186f-2a32-44c9-b415-12bbf13c7faa"; :>> outcome = VerdictKind::pass; :>> judgedAgainst = "11f4cac"; :>> judgedAt = "2026-08-21"; :>> judgedBy = "claudeFable5"; }
        action p0SubagentStop;
        verification p0SubagentStopDoD : Test { :>> id = "f8fa5704-ac63-4c43-b26e-f86c73c4fff5"; :>> method = VerificationMethod::test; :>> procedureText = "DONE MEANS: SubagentStop gates only when the tree fingerprint changed during that subagent's lifetime - baseline captured at the subagent's first PreToolUse fire keyed by session id, degrading to systemMessage when no baseline exists; read-only subagents receive systemMessage, never block; parallel subagents neither race to fix the same violation nor pay the full gate when they wrote nothing. Chartered by d0174."; }
        part p0SubagentStopDoDR1 : TestResult { :>> id = "cacd1645-ecfa-4bc4-95af-941473444f5d"; :>> outcome = VerdictKind::pass; :>> judgedAgainst = "11f4cac"; :>> judgedAt = "2026-08-21"; :>> judgedBy = "claudeFable5"; }
        action p0HardeningInventory;
        verification p0HardeningInventoryDoD : Test { :>> id = "76ab0c81-9a03-46ea-882a-5d9c664b233b"; :>> method = VerificationMethod::test; :>> procedureText = "DONE MEANS: keel hardening enumerates EVERY enforcement point (hooks, pre-commit, CI steps, guards, rules) with its absent/error/timeout behavior; timeout-resolves-to-allow points are listed as recorded residuals with their fire-ledger visibility; no enforcement point is silently open without appearing in this inventory (kernel invariant K2). Chartered by d0174."; }
        part p0HardeningInventoryDoDR1 : TestResult { :>> id = "e4cd6569-17e0-41a5-95fb-89e4db9e2ee5"; :>> outcome = VerdictKind::pass; :>> judgedAgainst = "11f4cac"; :>> judgedAt = "2026-08-21"; :>> judgedBy = "claudeFable5"; }
        action p1TieredDeny;
        verification p1TieredDenyDoD : Test { :>> id = "cd902e69-720b-45a8-9ac2-ec6358a85608"; :>> method = VerificationMethod::test; :>> procedureText = "DONE MEANS: the three-tier PreToolUse model works as specified - hard deny ABSENT A RECORDED OVERRIDE on API-owned fact surfaces with the refusal naming the exact command; ask for other .tracking writes; recorded override (single-use, target-path-bound, session-bound, reason required) whose obligation fact names the path actually written and uses one-file-per-fact so recording cannot deadlock on the file being repaired; Windows path separators normalized; the headless mapping exercised by one launched run in acceptance (console proxy when up - ask-pending ledger entry written BEFORE blocking, wait bounded under the hook deadline, expiry = deny + obligation - else auto-deny + queued obligation). Chartered by d0176."; }
        part p1TieredDenyDoDR1 : TestResult { :>> id = "85eb6722-9236-4194-ad1a-333beb5cc937"; :>> outcome = VerdictKind::pass; :>> judgedAgainst = "894e394"; :>> judgedAt = "2026-08-21"; :>> judgedBy = "claudeFable5"; }
        action p1BashMatcher;
        verification p1BashMatcherDoD : Test { :>> id = "766d1eb3-2073-4dcc-af1b-f532eb2ed9f9"; :>> method = VerificationMethod::test; :>> procedureText = "DONE MEANS: the Bash matcher tokenizes argv - a commit message DESCRIBING --no-verify does not match; commands whose argv0 resolves to keel are exempt EXCEPT the never-exempt human-judgment/actor-identity set (accept, confirmation-method writes, actor set, Person enrollment, KEEL_ACTOR/--by/--judged-by naming a Person - these route to ask + recorded fact); unambiguous blocks cover redirection/tee/sed -i into .tracking or .claude, git commit --no-verify, SKIP_VALIDATE=1, SKIP_KEEL=1, and git config core.hooksPath; everything ambiguous stays advisory with promotion evidence-gated per D-PM. Chartered by d0176 and d0178."; }
        part p1BashMatcherDoDR1 : TestResult { :>> id = "7129656b-2fb5-4eda-86fe-2b697bdbe9cb"; :>> outcome = VerdictKind::pass; :>> judgedAgainst = "894e394"; :>> judgedAt = "2026-08-21"; :>> judgedBy = "claudeFable5"; }
        action p1HumanChannel;
        verification p1HumanChannelDoD : Test { :>> id = "206569f2-ad5d-450c-b785-9cc4038d1cae"; :>> method = VerificationMethod::test; :>> procedureText = "DONE MEANS: accept_decision and method=confirmation writes refuse when the resolved actor is ActorKind::ai; keel accept in an agent-marked session requires a console-issued or TTY-interactive confirmation (intercepted before the write layer - tested); the protected-subcommand set is DERIVED from a declared attribute on write-API operations rather than hand-enumerated, so apply-review and future judgment-recording operations are covered automatically; the marker heuristic stays best-effort by recorded design note. Chartered by d0178."; }
        part p1HumanChannelDoDR1 : TestResult { :>> id = "4ea730fd-a375-49d9-9959-43a8e4323677"; :>> outcome = VerdictKind::pass; :>> judgedAgainst = "894e394"; :>> judgedAt = "2026-08-21"; :>> judgedBy = "claudeFable5"; }
        action p1ControlPlane;
        verification p1ControlPlaneDoD : Test { :>> id = "69437e5e-35e3-49d2-8aee-12dad154e009"; :>> method = VerificationMethod::test; :>> procedureText = "DONE MEANS: Write|Edit on .claude/settings.json, .githooks/, the output style, and Bash git config core.hooksPath, keel deactivate, exemption writes, and actor-identity mutation all route through ask plus an auto-recorded orient-visible fact; the issue116 vector (hooksPath) is covered end to end. Chartered by d0179."; }
        part p1ControlPlaneDoDR1 : TestResult { :>> id = "2de1aa84-6552-4a24-acda-a55958d8a038"; :>> outcome = VerdictKind::pass; :>> judgedAgainst = "894e394"; :>> judgedAt = "2026-08-21"; :>> judgedBy = "claudeFable5"; }
        action p1RulesWired;
        verification p1RulesWiredDoD : Test { :>> id = "37df2dd9-cdbf-47c6-9e3d-cf711c9d2ed5"; :>> method = VerificationMethod::test; :>> procedureText = "DONE MEANS: declared EdgeRule/ElementRule instances are evaluated by hook stop, the pre-commit gate, and CI - blocking rules gate, warning rules report; a downstream project adds a blocking control by declaring a rule with no Rust and no fork, proven by test; hook_stop routes through the activation filter so a deactivated process's guard no longer blocks turns. Chartered by d0177."; }
        part p1RulesWiredDoDR1 : TestResult { :>> id = "89e39950-0fa1-4028-8729-d482d6596979"; :>> outcome = VerdictKind::pass; :>> judgedAgainst = "894e394"; :>> judgedAt = "2026-08-21"; :>> judgedBy = "claudeFable5"; }
        action p1AuditHistoryCi;
        verification p1AuditHistoryCiDoD : Test { :>> id = "99bf401b-5eb3-48c5-b841-0590060afe17"; :>> method = VerificationMethod::test; :>> procedureText = "DONE MEANS: keel audit-history runs in CI over the pushed range and fails on a re-derived red; CLAUDE.md's never-rebase line is softened to name what is actually enforced (no pre-push hook is added - the honesty edit wins over permanent surface); kernel invariant K15 has a downstream home via the P0 CI template. Chartered by d0179."; }
        part p1AuditHistoryCiDoDR1 : TestResult { :>> id = "a4937216-e0bb-41d7-a31c-c2cf90baf379"; :>> outcome = VerdictKind::pass; :>> judgedAgainst = "894e394"; :>> judgedAt = "2026-08-21"; :>> judgedBy = "claudeFable5"; }
        action p1RedYield;
        verification p1RedYieldDoD : Test { :>> id = "95966279-c536-4ef8-a493-68f1e2762102"; :>> method = VerificationMethod::test; :>> procedureText = "DONE MEANS: the Stop hook's second red pass still yields (loop avoidance stands) but records a tracked obligation fact visible in keel orient, surviving console downtime; the console renders it when up. Chartered by d0176."; }
        part p1RedYieldDoDR1 : TestResult { :>> id = "44fdf226-d2c0-48d5-897e-f834a22ad2fd"; :>> outcome = VerdictKind::pass; :>> judgedAgainst = "894e394"; :>> judgedAt = "2026-08-21"; :>> judgedBy = "claudeFable5"; }
        action pmMeasure;
        verification pmMeasureDoD : Test { :>> id = "db9d51a1-c881-487c-bc3f-bdea773ba984"; :>> method = VerificationMethod::test; :>> procedureText = "DONE MEANS: the fire-ledger schema is frozen (emit plumbing ships with p0ClaudeScaffold); red-yields, overrides, launcher-run durations and turn counts are captured; adherence trend computes from ProcessDefect-marked issues; everything is machine-local under .keel/metrics (no tracked summaries until a consumer is named, D0144); at least one advisory-to-blocking promotion or non-promotion decision cites >= 3 sprints of this evidence; the launcher-fraction hypothesis and the dirty-tree-refusal rate are both reported. Chartered by d0180."; }
        part pmMeasureDoDR1 : TestResult { :>> id = "5273d72d-6292-434b-a87e-b000f705a31a"; :>> outcome = VerdictKind::pass; :>> judgedAgainst = "7f7df2c"; :>> judgedAt = "2026-08-21"; :>> judgedBy = "claudeFable5"; }
        part pmMeasureDoDR2 : TestResult { :>> id = "0139b44d-7c92-4d1e-b2a7-e02c5e3b0fdb"; :>> outcome = VerdictKind::fail; :>> judgedAgainst = "c6aba5c"; :>> judgedAt = "2026-08-22"; :>> judgedBy = "claudeFable5"; }
        part pmMeasureDoDR3 : TestResult { :>> id = "0d9c3517-0db8-47a0-87aa-12640800f019"; :>> outcome = VerdictKind::pass; :>> judgedAgainst = "3c9645e84904624d8f62ace559a9ea2cbb01738c"; :>> judgedAt = "2026-08-22"; :>> judgedBy = "claudeFable5"; }
        action p5Forms;
        verification p5FormsDoD : Test { :>> id = "9c225a64-42d0-4ae0-b1c0-11a2ff7f8b1b"; :>> method = VerificationMethod::demo; :>> procedureText = "DONE MEANS: every declared launchable Process/AISkill gets a per-process input form generated from the model (/api/schema + /api/surfaces - D0117 substrate, nothing hardcoded); launch remains approve-before-execute; breadth is demand-driven and depth (gate, records, hardening) ships first under scope pressure. Chartered by d0181."; }
        part p5FormsDoDR1 : TestResult { :>> id = "107cbd9b-adda-4360-a945-43eed4050806"; :>> outcome = VerdictKind::pass; :>> judgedAgainst = "7061513"; :>> judgedAt = "2026-08-21"; :>> judgedBy = "claudeFable5"; }
        action p5RunRecords;
        verification p5RunRecordsDoD : Test { :>> id = "e70e2af9-d3b5-4f20-85d8-a26aee819922"; :>> method = VerificationMethod::test; :>> procedureText = "DONE MEANS: each launched run writes .keel/runs/<id>.jsonl (transcript path, duration, turns, exit status - schema-declared machine-local, exempt from existence checks) and, for non-empty-diff runs only, ONE tracked summary fact in its own file, written AFTER the post-run gate UNDER THE RUN'S STAMPED ACTOR, carrying the run-start fingerprint and judgedAgainst; a roll-up/archival policy exists before summaries can grow turn-gate latency without bound. Chartered by d0182."; }
        part p5RunRecordsDoDR1 : TestResult { :>> id = "d2bb66c5-babd-4be0-a581-2c1c6b53abc8"; :>> outcome = VerdictKind::pass; :>> judgedAgainst = "7061513"; :>> judgedAt = "2026-08-21"; :>> judgedBy = "claudeFable5"; }
        action p5PostRunGate;
        verification p5PostRunGateDoD : Test { :>> id = "d605d1dd-98a5-45b8-9810-406a87e9c1fb"; :>> method = VerificationMethod::test; :>> procedureText = "DONE MEANS: launch refuses on a dirty tree and snapshots the tree fingerprint at spawn; the post-run gate runs validate + guards + rules over the run-start-snapshot-to-working-tree diff, evaluates ownership against the run's stamped actor, flags (never folds in) writes not attributable to the run's session via fire-ledger keying, records red runs as failed, routes the diff to human review UNCONDITIONALLY green or red, and reads the fire-ledger as evidence against accidental enforcement loss conditional on the transcript containing matched tool calls; consecutive launches serialize behind commit/revert of the prior run and the console offers a commit action for pending human-attested writes so accept-then-launch does not detour through freeform. Chartered by d0182."; }
        part p5PostRunGateDoDR1 : TestResult { :>> id = "0c90b6ae-6fcf-43b1-98a3-2abb0b669cc8"; :>> outcome = VerdictKind::pass; :>> judgedAgainst = "7061513"; :>> judgedAt = "2026-08-21"; :>> judgedBy = "claudeFable5"; }
        action p5CompletionCheck;
        verification p5CompletionCheckDoD : Test { :>> id = "4b96301f-08f4-4eb9-abd0-c72a15c97fc6"; :>> method = VerificationMethod::test; :>> procedureText = "DONE MEANS: a launched run must have recorded its outputs through the write API - at minimum the process's declared result kind exists for this run - with bounded re-prompt on failure; NO checker is built over the free-text producedArtifact field; full artifact contracts activate only when P3b delivers the typed field. Chartered by d0182."; }
        part p5CompletionCheckDoDR1 : TestResult { :>> id = "8373ef28-ef1b-4cda-af3e-5739916e7642"; :>> outcome = VerdictKind::pass; :>> judgedAgainst = "7061513"; :>> judgedAt = "2026-08-21"; :>> judgedBy = "claudeFable5"; }
        action p5SpawnHardening;
        verification p5SpawnHardeningDoD : Test { :>> id = "4b6630d2-be94-4673-91be-57adadcbce64"; :>> method = VerificationMethod::test; :>> procedureText = "DONE MEANS: spawned runs receive an absolute KEEL_BIN, an explicit permission mode implementing the headless-ask mapping, and a per-run wall-clock timeout that kills and records timed-out status (max-turns bounds turns, not stalls); duration and turn count land in the run record so subscription quota burn is visible (D0094). Chartered by d0182."; }
        part p5SpawnHardeningDoDR1 : TestResult { :>> id = "79442a1c-6019-4eab-9598-fb819b9ac6cc"; :>> outcome = VerdictKind::pass; :>> judgedAgainst = "7061513"; :>> judgedAt = "2026-08-21"; :>> judgedBy = "claudeFable5"; }
        action p4aUnitIdentity;
        verification p4aUnitIdentityDoD : Test { :>> id = "58087cbd-a06d-4324-89cb-8d88015e5203"; :>> method = VerificationMethod::test; :>> procedureText = "DONE MEANS: process-unit identity is a versioned id in the unit manifest, not the file stem; activation entries, deploying-skill recovery, and guard_state resolve via the unit id; guard_state treats a guard as active if ANY active unit asserts it (first-match-wins is dead). Chartered by d0183."; }
        part p4aUnitIdentityDoDR1 : TestResult { :>> id = "0575389e-c352-4d80-934e-ea35c310012c"; :>> outcome = VerdictKind::pass; :>> judgedAgainst = "e2571f8"; :>> judgedAt = "2026-08-21"; :>> judgedBy = "claudeFable5"; }
        action p4aInstallRecord;
        verification p4aInstallRecordDoD : Test { :>> id = "a6bd1e86-6b20-4d25-9081-c84a79af2eef"; :>> method = VerificationMethod::test; :>> procedureText = "DONE MEANS: keel process import writes an install record (versioned unit id, version, per-file content hashes) as a tracked fact - the three-way merge base; pre-existing installs bootstrap by treating local as base with explicit human confirmation. Chartered by d0183."; }
        part p4aInstallRecordDoDR1 : TestResult { :>> id = "b49093d5-cf0a-48dc-89e0-a12bfdd9534f"; :>> outcome = VerdictKind::pass; :>> judgedAgainst = "e2571f8"; :>> judgedAt = "2026-08-21"; :>> judgedBy = "claudeFable5"; }
        action p4aImportUpdate;
        verification p4aImportUpdateDoD : Test { :>> id = "b1b18a3a-38ce-4abe-ad2c-057fcc9bead8"; :>> method = VerificationMethod::test; :>> procedureText = "DONE MEANS: keel process import --update performs a three-way comparison (recorded base / upstream-new / local); local assert-constraint additions are never silently clobbered and divergence refuses with a report; the superseded definition gets a supersede edge with the ProspectiveChange/SafetyChange marker so reprocess-candidates fires; activation.toml is rewritten atomically (old unit out, successor in). Chartered by d0183."; }
        part p4aImportUpdateDoDR1 : TestResult { :>> id = "670ccff2-9ecc-46ad-806a-e601fe1b4030"; :>> outcome = VerdictKind::pass; :>> judgedAgainst = "e2571f8"; :>> judgedAt = "2026-08-21"; :>> judgedBy = "claudeFable5"; }
        action p4aHandshake;
        verification p4aHandshakeDoD : Test { :>> id = "eb3a9d60-c5dc-40a9-9ac8-c29c2c9d0255"; :>> method = VerificationMethod::test; :>> procedureText = "DONE MEANS: import diffs the unit's required guards against the binary's guard inventory and refuses - or loudly degrades with a recorded Issue - when the teeth cannot land; never prose-lands-enforcement-silently-missing. Chartered by d0183."; }
        part p4aHandshakeDoDR1 : TestResult { :>> id = "813f186c-1182-465a-b58d-0c0b13636911"; :>> outcome = VerdictKind::pass; :>> judgedAgainst = "e2571f8"; :>> judgedAt = "2026-08-21"; :>> judgedBy = "claudeFable5"; }
        action p4aGoverningVersion;
        verification p4aGoverningVersionDoD : Test { :>> id = "3f530313-5a98-4638-8106-356d12aa2053"; :>> method = VerificationMethod::test; :>> procedureText = "DONE MEANS: governing-version resolves against ANY process/workflow definition (per item via its charter edges), not the hardcoded delivery.sysml path; reprocess-candidates surfaces work governed by any superseded definition. Chartered by d0183."; }
        part p4aGoverningVersionDoDR1 : TestResult { :>> id = "5d21165d-ca3d-4639-b897-38e3c0bddf05"; :>> outcome = VerdictKind::pass; :>> judgedAgainst = "e2571f8"; :>> judgedAt = "2026-08-21"; :>> judgedBy = "claudeFable5"; }
        action p3aRuleAttribution;
        verification p3aRuleAttributionDoD : Test { :>> id = "9d8afcb2-15dd-43ca-9db8-a3aac1c1bbcd"; :>> method = VerificationMethod::test; :>> procedureText = "DONE MEANS: a declared rule carries an association to its owning process unit; unit export populates rules from that association (unit.rules is no longer hardcoded empty); this is the enabling slice for p4bRulesTravel and deliberately NOT the guard-migration (that stays behind the D-P3b trigger). Chartered by d0184."; }
        part p3aRuleAttributionDoDR1 : TestResult { :>> id = "67dc92f8-5005-4675-a7f0-ce0e6d90a93b"; :>> outcome = VerdictKind::pass; :>> judgedAgainst = "e2571f8"; :>> judgedAt = "2026-08-21"; :>> judgedBy = "claudeFable5"; }
        action p3aKeystoneExtension;
        verification p3aKeystoneExtensionDoD : Test { :>> id = "2f89561c-af8a-41fc-b5a3-11b7a4cb3f4c"; :>> method = VerificationMethod::test; :>> procedureText = "DONE MEANS: the D0070 keystone lock fires on staged changes to .engine/skills/ and .engine/contracts/ exactly as it does for processes and workflows - a skill body or activation-policy edit without a co-committed marked Decision blocks. Chartered by d0184."; }
        part p3aKeystoneExtensionDoDR1 : TestResult { :>> id = "08befc1d-07db-4c38-8854-1b517fc094d9"; :>> outcome = VerdictKind::pass; :>> judgedAgainst = "e2571f8"; :>> judgedAt = "2026-08-21"; :>> judgedBy = "claudeFable5"; }
        action p4bRulesTravel;
        verification p4bRulesTravelDoD : Test { :>> id = "96a720a3-3520-4f7d-ab85-9d5df533a68d"; :>> method = VerificationMethod::test; :>> procedureText = "DONE MEANS: declared rules export and import with their process unit and the version handshake verifies the destination can evaluate them; a unit that cannot land its rules refuses or loudly degrades with a recorded Issue. Executes under d0183 jointly with d0184."; }
        part p4bRulesTravelDoDR1 : TestResult { :>> id = "fa3a394d-cd0c-4a23-9541-e6a73a21d393"; :>> outcome = VerdictKind::pass; :>> judgedAgainst = "e2571f8"; :>> judgedAt = "2026-08-21"; :>> judgedBy = "claudeFable5"; }
        action fixDownstreamDecisionNumbering;
        verification fixDownstreamDecisionNumberingDoD : Test { :>> id = "d58139a1-a53e-41c4-b0aa-a16cae584869"; :>> method = VerificationMethod::test; :>> procedureText = "In a fresh downstream project (keel init + reference decisions present), keel record decision allocates a number/package that CANNOT collide with the shipped read-only reference namespace (Decision0001../d0001..): either numbering continues past the highest reference decision, or project decisions get a distinct package/name scheme; guard:duplicate-identity stays green on the first recorded decision, demonstrated by a test."; }
        // RAN: cargo test --release => 278 passed 0 failed (incl reference_decision_package_is_renamed_declaration_only, non_decision_engine_files_are_never_content_transformed) | fresh fixture C:/kt/f2: keel init . --profile guided => 236 package ReferenceDecision; keel record decision => D0001 package Decision0001; keel guard => duplicate-identity PASS 331 scanned 0 violations; keel gate --fast => clean | old-vintage fixture (236 packages reverted, committed 793b865): keel guard => duplicate-identity FAIL 2 violations; keel migrate . => wrote 241 files, re-plan empty; keel guard => duplicate-identity PASS | this tree: keel validate . => 525 files clean; keel check-engine . => clean; keel guard => 0 of 52 failing
        part fixDownstreamDecisionNumberingDoDR1 : TestResult { :>> id = "311c049a-13bb-4ec4-9fc2-068d8162a169"; :>> outcome = VerdictKind::pass; :>> judgedAgainst = "019002b"; :>> judgedAt = "2026-08-27"; :>> judgedBy = "claudeOpus5"; }
        action kgRecallIsContentBearing;
        verification kgRecallIsContentBearingDoD : Test { :>> id = "bf3964e2-889b-45aa-8107-8573c5e489d6"; :>> method = VerificationMethod::test; :>> procedureText = "DONE MEANS: `keel why --brief` and `keel recall` emit a budgeted, ranked, CONTENT-bearing payload fit to inject - compact lines carrying type, name, title, hops, via and source file, plus the substantive text (decision/description/rationale/actionText) of the nearest two - and the JSON form is unchanged for existing callers. Today `seeds` are bare identifiers with no content and the command takes NO flags, so its 40 rows would be noise if injected. THE BUDGET HAS ONE STATED EXCEPTION: the top row is always included even if it alone exceeds the budget, because erasing the most relevant fact is worse than overshooting - every row after the first is inside the budget, footer reserved. VERIFY: at budgets 800/1500/4000 the whole payload FITS; at a budget too small for one row the top row is still present and no contradictory 'nothing reached' is printed; the payload cites a source file per row and carries substance for the top rows; `keel why <term>` JSON keys are unchanged (D0242 part 1)."; }
        // RAN: see sprint478_recall RAN receipt: 14 suites 0 failures + 3 new precision tests; clippy 0; seeds a 11112->431, decision 294->236, gate 5736 correct-unchanged; prompt of common words pushes nothing and names what it ignored; d0239 ranks first with its decision text; keystone(38)+workspace(65) survive; budgets 800/1500/4000 all fit, 200 still shows the top row; .knowledge deleted => recall still works (store is 7 of 13639 items); 641-863ms; why JSON keys unchanged
        part kgRecallIsContentBearingDoDR1 : TestResult { :>> id = "0727b43d-b56a-43ed-a554-a3d5a7e1553f"; :>> outcome = VerdictKind::pass; :>> judgedAgainst = "2bec54d"; :>> judgedAt = "2026-08-27"; :>> judgedBy = "claudeOpus5"; }
        action kgRecallSeedsFromAPrompt;
        verification kgRecallSeedsFromAPromptDoD : Test { :>> id = "4db149ec-2962-4f48-a363-748c56eabfda"; :>> method = VerificationMethod::test; :>> procedureText = "DONE MEANS: `keel recall --prompt -` reads a prompt on stdin and seeds from the CORPUS's own statistics and shape, with ZERO model calls (D0243 supersedes D0242's lexicon-first framing). Four precision rules in preference order: identifier-shaped tokens first (dNNNN, issueNNN, sprintNNN, camelCase element names); word and SEGMENT boundaries, never substrings (camelCase split before matching); rarity weighting DERIVED from the tree, so a token matching thousands of elements is dropped and one matching a handful is a strong seed; and the existing hub suppression. MEASURED BEFORE (substring seeding): decision 294 seeds, change 96, the 795, gate 5806, a 11112 - and 12,893 reached for `a`, which a 40-row cap hides rather than fixes. VERIFY: a prompt of only common words seeds NOTHING and says so; a prompt naming dNNNN or an element name seeds exactly it plus its neighbourhood; `gate` and `the` fall below the rarity threshold while `workspace` and `keystone` survive; recall works with .knowledge/ DELETED; no path spawns a model call."; }
        // RAN: see sprint478_recall RAN receipt: 14 suites 0 failures + 3 new precision tests; clippy 0; seeds a 11112->431, decision 294->236, gate 5736 correct-unchanged; prompt of common words pushes nothing and names what it ignored; d0239 ranks first with its decision text; keystone(38)+workspace(65) survive; budgets 800/1500/4000 all fit, 200 still shows the top row; .knowledge deleted => recall still works (store is 7 of 13639 items); 641-863ms; why JSON keys unchanged
        part kgRecallSeedsFromAPromptDoDR1 : TestResult { :>> id = "e9a1d8c7-cb0a-48a4-956f-2f03d8f3b5f8"; :>> outcome = VerdictKind::pass; :>> judgedAgainst = "2bec54d"; :>> judgedAt = "2026-08-27"; :>> judgedBy = "claudeOpus5"; }
        action kgPromptPathInjects;
        verification kgPromptPathInjectsDoD : Test { :>> id = "07258021-4f39-4643-ae17-a22888d9b378"; :>> method = VerificationMethod::test; :>> procedureText = "DONE MEANS: `keel hook user-prompt` READS the prompt (it took only the root and emitted a fixed routing string), calls recall, and PUSHES the facts ahead of the routing reminder with the VISIBLE count and elapsed time the source process names as this step's produced artifact. Injection pushes whenever an informative token survives; a prompt of only filler or corpus-common words pushes nothing. A CONFIDENCE gate was built here and REMOVED after measurement (2/8 against 5/8 for no gate) - this DoD text is corrected rather than left asserting a gate the code has not had since it was deleted (issue297). THREE KILL SWITCHES, at the human's request, in the order they would be reached for: (1) `keel deactivate knowledge-graph-memory`, the DECLARED off via the existing D0138 unit mechanism - committed, auditable, travels with the project; (2) `KEEL_RECALL=off`, the immediate machine-local off, env-based so it cannot be mistaken for a project decision; (3) a LOW-confidence prompt is simply not injected. Deleting `.knowledge/` is explicitly NOT a kill switch any more - D0243 made seeding corpus-derived - and that is stated because it used to be the removability story. FAIL-OPEN throughout with a hard latency cap that REPORTS rather than hides. VERIFY: a HIGH prompt yields facts with a count and a duration; a LOW prompt and an uninformative one yield the routing reminder unchanged; `keel deactivate` stops injection while `keel why` (pull) still works and reactivating restores it; KEEL_RECALL=off suppresses; the cap forced to 1ms prints a visible SKIPPED note and exits 0; `.knowledge/` deleted leaves the hook injecting and validate + guards green (D0242 part 3)."; }
        // RAN: 14 suites 0 failures, clippy 0; the REAL hook end-to-end: HIGH prompt => '[keel recall - pushed before the model, 809ms]' + d0134 + hooksInBinaryStory + st013 with decision text; LOW ('tidy up the workspace') and uninformative ('change the gate') => routing reminder only; keel deactivate knowledge-graph-memory => 0 recall lines while keel why still works, reactivate => 1 again; KEEL_RECALL=off on the keel process => suppressed; cap forced to 1ms => '[keel recall] SKIPPED - recall took 1002ms (cap 1ms)' exit 0 with routing intact; .knowledge deleted => hook still injects, validate 532 clean, 0 guards failing
        part kgPromptPathInjectsDoDR1 : TestResult { :>> id = "413a360b-8886-46e9-8e5b-7138219f940c"; :>> outcome = VerdictKind::pass; :>> judgedAgainst = "2bec54d"; :>> judgedAt = "2026-08-27"; :>> judgedBy = "claudeOpus5"; }
        action kgInjectionProvenOnTheTrap;
        verification kgInjectionProvenOnTheTrapDoD : Test { :>> id = "fc27d485-c3ba-4272-9d09-4aecb997b4c7"; :>> method = VerificationMethod::test; :>> procedureText = "DONE MEANS: injection is measured against a control on a set the author did not hand-pick, and the result decides whether it ships. MEASURE CORRECTED FROM THE ORIGINAL DoD, which asked for TOOL CALLS TO FIRST CORRECT ANSWER with injection on versus off: I cannot take that measure honestly on myself, because I already know the answers to questions about this corpus, so any tool-call count I produced would measure my memory rather than the retrieval. The mechanical proxy is RETRIEVAL HIT RATE - is the element that answers the request present in the rows the payload actually SHOWS - and the CONTROL is naive keyword search rather than silence, because a model without recall does not sit in the dark, it greps. Scoring the control as zero would have rigged the comparison. QUESTIONS ARE DERIVED, NOT WRITTEN: each query is built mechanically from the target element's BODY text with its own name-words removed, seeded and reproducible (.engine/tools/recall_bench.py), so the set cannot be biased toward what recall happens to find. VERIFY: both arms reported on 50 cases. HONEST OUTCOME CLAUSE: if recall does not beat the control, record that and keep the command tier - do not ship injection because it was planned (D0242 part 4)."; }
        // RAN: 50 mechanically-derived cases, seed 20260828, .engine/tools/recall_bench.py: KG 24/50 (48%) vs naive keyword control 17/50 (34%); overlap both 13, KG-only 11, grep-only 4, neither 22 (union 28/50); KG hit position median 2, top-3 in 14/24; latency mean 1009ms max 1256ms; pushed on 50/50. Earlier 8-case hand-written set with ground truth fixed in advance: 5/8 with no confidence bar vs 2/8 with it, 4 of 5 hits at position 1-2. Injection SHIPS on the strength of beating the control
        part kgInjectionProvenOnTheTrapDoDR1 : TestResult { :>> id = "a6629585-9d06-4013-a774-51a58a5b969b"; :>> outcome = VerdictKind::pass; :>> judgedAgainst = "2bec54d"; :>> judgedAt = "2026-08-28"; :>> judgedBy = "claudeOpus5"; }
        action dcPinBites;
        verification dcPinBitesDoD : Test { :>> id = "2783ff89-9608-4043-afbe-a5fca105fa3c"; :>> method = VerificationMethod::test; :>> procedureText = "Discharges srProjectPinsItsEngine + srWorkspacePinIsCoherent (D0251 clause A/C). The declared engine version becomes BINDING: a write or gate command invoked by a binary whose version differs from engine-version.toml REFUSES naming both versions; read-only views WARN and proceed; version and migrate never refuse (they are how skew is inspected and repaired); an ABSENT declaration stays a warn-only state (D0136: absence is a state - pre-D0190 trees keep working). Workspace: a gate spanning projects whose declarations DISAGREE refuses naming each project and its pin. GHERKIN FIRST, failing before implementation: (1) fixture declares a different version, record decision refuses naming both; (2) same skew, guard refuses; (3) same skew, orient proceeds with a loud warning; (4) migrate proceeds; (5) no declaration, everything proceeds with warn; (6) two-project workspace disagreeing, gate --workspace refuses naming both. VERIFY: all six scenarios green; clippy; full suite; the D0251 escalation warning ships in migrate output so existing projects hear about the change before it bites them."; }
        // RAN: // RAN: keel-cli/tests/pin_actually_bites.rs 6/6 (TDD: written first, run to RED); full workspace suite 18 suites 0 FAILED; discharged by sprint 490
        part dcPinBitesDoDR1 : TestResult { :>> id = "01058d12-9eb4-4033-bfa9-02188d942756"; :>> outcome = VerdictKind::pass; :>> judgedAgainst = "5fcaad7"; :>> judgedAt = "2026-08-29"; :>> judgedBy = "claudeOpus5"; }
        action dcKeelWrapper;
        verification dcKeelWrapperDoD : Test { :>> id = "6f9b5365-283a-42be-8ae4-63e50f17adbc"; :>> method = VerificationMethod::test; :>> procedureText = "Discharges D0251 clause B. A committed POSIX-sh wrapper (keelw) resolves the pinned version from engine-version.toml against a machine-local binary cache (.keel/bin/<version>/), and on a miss downloads THAT VERSION AND NO OTHER from the release page, verifies a committed SHA-256 (keel-wrapper.toml: version -> per-platform sha), and execs. It NEVER falls back to a binary on PATH and never resolves any other version. keel init ships keelw + the toml. TESTABLE WITHOUT THE NETWORK: KEELW_BASE_URL overrides the release origin, so the test serves a fake release from a local directory. GHERKIN FIRST: (1) cache hit execs the cached binary; (2) cache miss + good checksum downloads, caches, execs; (3) BAD checksum refuses loudly and caches nothing; (4) unreachable origin with an empty cache refuses with instructions, never falls back to PATH; (5) the wrapper resolves ONLY the pinned version even when newer assets exist. VERIFY: scenarios green via sh in CI; shipped by init; D0175's supersession-in-part (D0251) already recorded."; }
        // RAN: 5 Gherkin scenarios TDD (RED first); discharged by sprint 491
        part dcKeelWrapperDoDR1 : TestResult { :>> id = "fe6860fb-1152-4bd4-9530-a21a06ddafe6"; :>> outcome = VerdictKind::pass; :>> judgedAgainst = "b7403e4"; :>> judgedAt = "2026-08-29"; :>> judgedBy = "claudeOpus5"; }
        action dcLibraryReadSide;
        verification dcLibraryReadSideDoD : Test { :>> id = "61dae9e1-aae7-4497-9c5b-2c0f3fe1a02d"; :>> method = VerificationMethod::test; :>> procedureText = "Discharges srLibraryAvailableWithoutInstall + srAvailabilityIsNotActivation (D0250 clauses A/B/C/F). keel library init <remote> records the library remote in machine-local state beside the console registry; keel library sync is fetch + FAST-FORWARD-ONLY into the machine-local clone (a non-ff is a loud defect report, never a merge); an unreachable remote uses the last-good cache and SAYS how stale it is; keel library list enumerates the units in the cache; keel process import --from-library <unit> imports from the cache exactly as from a directory. GHERKIN FIRST: (1) init + sync clones a local bare fixture; (2) a second sync after upstream commits fast-forwards silently; (3) a doctored local clone (non-ff) reports the defect and refuses to merge; (4) unreachable remote: list still answers from cache and names the staleness; (5) THE DIFFERENTIAL: a project's gate verdict and guard set are byte-identical with the library present and absent - availability is never activation; (6) import --from-library lands a unit identically to directory import. VERIFY: scenarios green; no project tree contains the library; no gate reads it."; }
        // RAN: 6 Gherkin scenarios TDD; discharged by sprint 492
        part dcLibraryReadSideDoDR1 : TestResult { :>> id = "5a8bcf8a-8172-40c5-b78f-59518f19ffa6"; :>> outcome = VerdictKind::pass; :>> judgedAgainst = "a901722"; :>> judgedAt = "2026-08-29"; :>> judgedBy = "claudeOpus5"; }
        action dcLibraryPublish;
        verification dcLibraryPublishDoD : Test { :>> id = "ea36e5c8-5b74-4b9d-a65b-f7bdeb3b68b6"; :>> method = VerificationMethod::test; :>> procedureText = "Discharges D0250 clause D. keel process publish <name> exports the unit into the machine-local library clone and COMMITS with a message naming unit + version - always loud, never part of sync. GHERKIN FIRST: (1) publish lands exactly the export file set as one commit in the clone; (2) publishing an unchanged unit refuses as a no-op (issue302 semantics extended to the library: a version that did not move does not publish); (3) publish never pushes without being asked - the push is the human-visible act (or keel land on the library repo). VERIFY: scenarios green; sync remains fast-forward-only after a publish (local commits make the clone ahead, which sync tolerates - AHEAD is not the non-ff defect, BEHIND-divergent is)."; }
        // RAN: 3 Gherkin scenarios TDD; discharged by sprint 493
        part dcLibraryPublishDoDR1 : TestResult { :>> id = "3f823664-85cd-4f22-83c5-367a15979bf8"; :>> outcome = VerdictKind::pass; :>> judgedAgainst = "34e40b4"; :>> judgedAt = "2026-08-29"; :>> judgedBy = "claudeOpus5"; }
        action dcKickoffReady;
        verification dcKickoffReadyDoD : Test { :>> id = "3261af95-b2ca-4783-9fad-f2c321639c7e"; :>> method = VerificationMethod::demo; :>> procedureText = "The kickoff path, end to end, using everything above. (1) In se-templates: author the exec-summary PROCESS DEFINITION (its skill + template + tests exist; the process file is what makes it a transferable unit - the issue245 class) and publish it to the library. (2) Cut a release tag so a fresh project pins a clean version line. (3) keel init a THROWAWAY project with the shipped keelw, declared profile, first push (issue306 fix proving itself), library sync, import exec-summary + decision-channel from the library, keel onboard read back. VERIFY by demo: the throwaway project's transcript is the evidence - init to first green gate to imported units, no step manual beyond the declared ones. Then the REAL project kicks off on the proven path."; }
        // RAN: the end-to-end throwaway demo; discharged by sprint 494. All five increments of the st033 readiness plan are complete
        part dcKickoffReadyDoDR1 : TestResult { :>> id = "f1e48f27-d51e-4f91-aef7-70d2725105c6"; :>> outcome = VerdictKind::pass; :>> judgedAgainst = "c4d5dbf"; :>> judgedAt = "2026-08-29"; :>> judgedBy = "claudeOpus5"; }

        action retireTheConfidenceProse;
        // ── D0052 reorder (st035, 2026-08-29): PRIORITY IS ASSESSED, from the computed signals -
        // resolver severity first (Critical > High > Medium > none), the priority-inversion guard's
        // six standing warnings discharged rather than re-explained. dcRenameIsAChange (Critical
        // issue273) had sat at rank 16 below two no-issue items. ──
        action dcRenameIsAChange;
        verification dcRenameIsAChangeDoD : Test { :>> id = "41830da5-272d-4f06-a55e-7ba90484985d"; :>> method = VerificationMethod::test; :>> procedureText = "Resolves issue273 (D0235). An adversarial panel found that the issue272 fix - narrowing the keystone lock from --diff-filter=ACMR to MD so a fresh scaffold could make its first commit - DROPPED R, renames. Reproduced on a plain single-project repo: sed blocking to warning into rules2.sysml, remove rules.sysml, git add -A gives git an R096 rename, the MD filter matches nothing, and guard process-change reports PASS 0 scanned - every blocking rule downgraded by a git mv with no signed Decision, live in every repository. Same function, second blindness: git C-QUOTES non-ASCII paths in this output while rev-parse --show-prefix does not, so a project whose name carries a non-ASCII byte was invisible to the workspace gate and to its own guards. DO: the keystone reads MDR, never a bare A; the staged-path reader parses NUL-separated --name-status -M records with core.quotePath=false and returns BOTH sides of a rename. VERIFY BOTH DIRECTIONS: the rename downgrade FAILS with both paths named where it passed before; a fresh keel init plus git add -A plus commit still SUCCEEDS through the scaffolded hook so the issue272 fix survives; this repo guard output is otherwise unchanged."; }
        // RAN: // RAN: keel-cli/tests/keystone_sees_renames.rs -> 3/3. Direction 1: a REAL staged rename (git-confirmed R09x, asserted in-fixture after the first draft staged a D+A below similarity threshold) of a locked rules file with a blocking->warning downgrade FAILS guard process-change naming the path - the exact issue273 reproduction that once passed with 0 scanned. Direction 2: a fresh keel init's first commit (all additions) still PASSES, so the issue272 fix survives the MDR re-widening. Direction 3: the same downgrade renamed to a non-ASCII (C-quoted) filename still FAILS - the second blindness. The guard-side fix (--name-status -M -z, core.quotePath=false, both rename sides) had landed with the panel's finding; this probe is the DoD's owed VERIFY, discriminating in both directions
        part dcRenameIsAChangeDoDR1 : TestResult { :>> id = "5a96d6d6-d8c7-4844-bfe0-22d191a256cf"; :>> outcome = VerdictKind::pass; :>> judgedAgainst = "fd7a064"; :>> judgedAt = "2026-08-29"; :>> judgedBy = "claudeOpus5"; }
        action dcIntakeHasAWritePath;
        verification dcIntakeHasAWritePathDoD : Test { :>> id = "4f9e92b3-7517-49f6-b298-69d4ac46881f"; :>> method = VerificationMethod::test; :>> procedureText = "Resolves issue289. Intake had NO write path: keel record covered decision and issue only, so every Statement and UserStory in this repository was written by hand-editing a file. That is the record type where it matters most, because D0216 makes the VERBATIM Statement the precondition for every Need - a Need with no cited utterance cannot be checked against what the human actually said, which is how one comes to be written wider than the demand (D0157). Hand-editing meant no actor validation, no write lock, no refusal on a defaulted date, and nothing stopping a paraphrase typed from memory being stored in a field labelled verbatim. DO: keel record statement and keel record story, with --from FILE for prose (the D0224 lesson: prose through shell arguments is how tool output got injected into a governance record twice); a Statement's text escaped ONLY as the literal requires, never through the whitespace-collapsing sanitiser used for titles; an unknown channel or implication REFUSED rather than defaulted, because the channel is provenance; and a story's #DerivedFrom edge authored WITH it, with a story citing a non-existent Statement refused and nothing written. VERIFY: the human's own message recorded and read back BYTE-IDENTICAL including double spaces; a title through the same input collapses, proving the two escapings differ; a story citing st999 is refused and leaves no trace; the edge is present in the file; three unit tests plus a live end-to-end run."; }
        // RAN: // RAN: cargo test -p keel-cli --lib intake_write -> 4 passed: a_statements_text_survives_verbatim_where_a_title_would_be_collapsed (byte-identical round-trip INCLUDING double spaces, and the title collapse contrast proving the two escapings differ), a_statement_records_and_a_story_must_cite_one (st999 refused, nothing written; #DerivedFrom authored WITH the story), an_unknown_channel_or_implication_is_refused_rather_than_defaulted, every_schema_declared_member_of_both_intake_vocabularies_is_accepted (the issue300 control). LIVE: st001-st036 + us001-us051 all entered through keel record statement/story across this arc, including six concurrent writers in the lock probe. issue289 and issue300 resolve
        part dcIntakeHasAWritePathDoDR1 : TestResult { :>> id = "62870ad8-0507-43cc-aa4b-ca8ffa2a2aa7"; :>> outcome = VerdictKind::pass; :>> judgedAgainst = "fd7a064"; :>> judgedAt = "2026-08-29"; :>> judgedBy = "claudeOpus5"; }
        action activateDoesNotLoseFacts;
        verification activateDoesNotLoseFactsDoD : Test { :>> id = "61d241cd-5d97-4c38-be49-8b3409229c96"; :>> method = VerificationMethod::test; :>> procedureText = "DONE MEANS: keel activate / keel deactivate PRESERVE every fact in .engine/contracts/activation.toml that they do not intend to change. Measured loss on one deactivate+activate round trip: charteredBy = d0226 was deleted along with its explanatory comment (the D0225 charter reference - a set without a charter is a collection of switches nobody can account for), and decision-authoring was dropped from active because it is [always] and asserts no guard, so the writer omits non-switchable processes. The second is worse than untidy: an ABSENT section means everything is active (D0138/D0164), but a PRESENT list of 10 of 11 means the 11th is INACTIVE, so omitting a process from a list that exists is a semantic change. VERIFY: a deactivate+activate round trip leaves the file byte-identical apart from the one process named; charteredBy and comments survive; a non-switchable [always] process is never removed from a present active list; held by a test that round-trips the real file."; }
        // RAN: // RAN: see sprint497. RED-first 4/4 reproducing both documented losses, GREEN 4/4; byte-identical live round trip on .engine/contracts/activation.toml (git diff empty); charteredBy + its comment survive; decision-authoring ([always]) never dropped from a present list; the one named process is the only thing that changes
        part activateDoesNotLoseFactsDoDR1 : TestResult { :>> id = "6adb8eff-ba53-4165-a628-b403819c9f95"; :>> outcome = VerdictKind::pass; :>> judgedAgainst = "761e2e2"; :>> judgedAt = "2026-08-30"; :>> judgedBy = "claudeOpus5"; }
        action dcCliCommandFactsAuthored;
        verification dcCliCommandFactsAuthoredDoD : Test { :>> id = "76cea52e-d1f6-4f41-9509-814cfaffb9f7"; :>> method = VerificationMethod::test; :>> procedureText = "DONE MEANS: every dispatched keel command is a CliCommand fact and every CliCommand fact is dispatched, checked two ways by a guard. D0271 defined the schema (name, synopsis, invocation, family, effect, stability) and deferred the 65 instances until the human ruled on the lens collapse; D0273 ruled, the collapse landed, and the instances were never authored - grep finds zero, while CLAUDE.md invariant 8 states them as existing. The facts are also the source the computed control structure (dcControlStructureIsComputed) needs: effect = writes is a control action the agent issues on the model, reads is feedback. DO: author the instances in .engine/cli/ from cli_surface::COMMAND_NAMES and LENS_NAMES, effect and stability from each command's dispatch (a status command reads; land is both; hook is tooling and internal); the two-way guard cli-surface-declared; keel --help renders FROM the facts so the synopsis has one home. VERIFY: guard red on an undeclared dispatch and on a declared-but-undispatched name in a fixture; the count in CLAUDE.md invariant 8 corrected to the measured number in the same commit; the existing COMMAND_NAMES == dispatch test still holds."; }
        // RAN: cargo test -p keel-cli --lib guards::cli_surface_declared_tests 4/4 (dispatched-without-fact, fact-without-dispatch + lens-as-command, mirror field drift, live agreement); hardening::tests::every_dispatched_subcommand_is_documented 1/1 over the rendered facts; guard_catalogue_tests 1/1; keel guard cli-surface-declared . -> 100 scanned 0 violations; ARMED live: status effect flipped to writes -> 1 violation naming status; orient fact deleted -> 2 violations naming orient (mirror-without-fact, dispatched-without-fact); restored -> PASS; keel version -> guards: 58; keel --help renders 100 rows grouped by family
        part dcCliCommandFactsAuthoredDoDR1 : TestResult { :>> id = "f61ea751-a43e-44a4-965f-91e19ceca130"; :>> outcome = VerdictKind::pass; :>> judgedAgainst = "52424e3"; :>> judgedAt = "2026-09-02"; :>> judgedBy = "claudeOpus5"; }
        action dcControlStructureIsComputed;
        verification dcControlStructureIsComputedDoD : Test { :>> id = "a28238a7-5ee9-49cb-a59c-fdbc47e8df49"; :>> method = VerificationMethod::test; :>> procedureText = "DONE MEANS: the STPA step-2 control structure of keel itself is a COMPUTED view - keel show control-structure - and the safety viewpoint's renderer, so that viewpoint stops reading planned/unbuilt. The human's first step (st066): what authorities are present, how they interact, what data is sent - and (st066 follow-up) computed from existing facts as far as possible, never authored. SOURCES, each already in the tree or fetchable: controller anchors and controlled processes from engine-control-structure.sysml (the authored residue); hook-boundary actions from .claude/settings.json events and the hook dispatcher's block/advise verdict kinds; git-hook actions from .githooks/*; CI and channel actions from the step names in .github/workflows/*.yml; the agent's control actions from CliCommand facts with effect writes or both, feedback from effect reads (dcCliCommandFactsAuthored is the prerequisite); refusals from the guard set and control-map.sysml bound to hazards; declared human deciders from github-actors.toml; the remote's branch protection fetched live via gh api when online and reported as unverified when not - never copied into the tree. Each computed action names its issuer anchor, the process it acts on, the data it carries (the command's invocation or the workflow step) and the receiving control if any. Renders as JSON, as a table, and as a graph through keel render --mode graph. VERIFY: every controller anchor has at least one computed action or the view says which authority is inert; the view over a fresh keel init project produces the scaffold's structure with no authored actions; removing a hook event from settings.json removes its action from the view on the next run; process models render with their beliefs and the Issues that mark a belief false."; }
        // RAN: cargo test --test control_structure_is_computed 3/3 (fresh scaffold: every role derived, null anchors, empty processModels, channel inert because not imported; removing UserPromptSubmit from settings.json removes hookUserPromptSubmit with no model edit; this repo: 8 anchors decorate, pmHuman renders citing issue343, ehz1 attaches to a process, humanDecidesOnChannel from github-actors.toml, remote row says unverified under KEEL_OFFLINE); cargo test --lib view::control_structure 5/5 (write->action, read->feedback, accept->human, hook event->agent-turn action with verdict kind, HUMAN_AUTHORITY_COMMANDS == write::HUMAN_ONLY_WRITE_COMMANDS); live: keel show control-structure . -> 44 actions, 76 feedback, 0 inert, remote fetched live: requiresStatusChecks false, requiresReviews false, refusesForcePush true -> CI is DETECTIVE; keel guard viewpoint-renderer 2 warnings (safety no longer planned)
        part dcControlStructureIsComputedDoDR1 : TestResult { :>> id = "2c48f2ed-3e1b-4d50-9f0d-23f256eec24d"; :>> outcome = VerdictKind::pass; :>> judgedAgainst = "7459b45"; :>> judgedAt = "2026-09-02"; :>> judgedBy = "claudeOpus5"; }
        action recallIndexesBodiesAndRanksProperly;
        verification recallIndexesBodiesAndRanksProperlyDoD : Test { :>> id = "1396c570-9960-4831-8302-281016048e6d"; :>> method = VerificationMethod::test; :>> procedureText = "DONE MEANS: recall seeds on the BODY fields it already reads, and ranks by a graded weight rather than a binary vote. Measured by the panel: seeds_for matches name, title and Alias term ONLY (knowledge.rs seeds_for), so decision/description/rationale/actionText/consequences are loaded and used only to PRINT the top rows - a prompt about provenance contributed zero seeds because the word lives in bodies and in no name or title. And agreement reaches max 1 in 43 of 50 bench cases, so the primary sort key is constant and the production ranker degenerates to (hops, name) - alphabetical - which is the exact failure agreement was introduced to fix. Cause is structural: MAX_PROMPT_WORDS caps votes at 3 and the rarity ceiling deletes the mid-frequency words most likely to co-occur. BM25 measured on the SAME name+title fields scores 37/50 (74%) at hit@20 against the shipped 24/50 (48%), with a field ceiling of 44/50. VERIFY: bodies are indexed for seeding; scoring is IDF-weighted with length normalisation (BM25) replacing MAX_PROMPT_WORDS + the rarity ceiling + the 55-word list + the agreement key, keeping the identifier override; the corrected harness shows no regression against the shipped 24/50."; }
        // RAN: BM25F per field (name 3, title 2, body 1 incl. procedureText; k1 1.2, b 0.75) with one saturation; query segmented like the index; no prompt-word cap, no rarity ceiling, agreement key gone, identifier override kept, the 55-word English filler list KEPT and said so - measured, not the DoD's guess; one-hop degree-normalised lift from seeds. cargo test 463/0, clippy 0. Corrected harness, linked-record set 50: shipped 2/50 -> 41/50 (control 7/50, McNemar p<0.001); self set 25: shipped 5/25 -> 25/25 median position 1; hand set 8: shipped 7/8 -> 5/8 (issue367). Latency mean 685ms.
        part recallIndexesBodiesAndRanksProperlyDoDR1 : TestResult { :>> id = "71c0d679-1de2-4545-b844-ab8d54fad6eb"; :>> outcome = VerdictKind::pass; :>> judgedAgainst = "a40d876"; :>> judgedAt = "2026-09-04"; :>> judgedBy = "claudeOpus5"; }
        action recallBenchmarkCanDiscriminate;
        verification recallBenchmarkCanDiscriminateDoD : Test { :>> id = "62250817-726b-43e5-9b41-b23f5f1593e6"; :>> method = VerificationMethod::test; :>> procedureText = "DONE MEANS: the harness can decide the question it is used to decide. Four defects, all found by the panel and all confirmed. (1) STRAWMAN CONTROL: recall_bench.py builds queries from BODY_FIELDS while baseline() matches only name and title, so the control is structurally denied the one field the queries were sampled from - with bodies included the same control scores 50/50, and real git grep 14/15, both of which are ALSO leakage because the queries are verbatim body words. The harness therefore cannot discriminate in either direction and the 14-point gap is an artifact. (2) NO PRECISION METRIC: recall was measured, precision never was - sampled at ~9% across 17 realistic prompts (1 of 11 pushes topical), which is the metric a PUSH feature lives or dies on. (3) NO SIGNIFICANCE TEST: the 2x2 is KG-hit/grep-hit 13, KG-only 11, grep-only 4, neither 22; McNemar exact on the 15 discordant pairs gives p = 0.119, so the honest reading is 'direction favours KG, parity not excluded', and the net advantage is 7 cases not 24. (4) DEAD STATISTIC: `both` is computed from a name-in-list-of-tuples test that is always false and never printed - evidence the harness was unreviewed while being the sole basis for a delete-the-subsystem proposal. VERIFY: a body-searching control arm; a PARAPHRASE query set not drawn from the target's own text; precision reported beside recall; the 2x2 and McNemar printed; the 548-vs-13704 corpus asymmetry stated; the dead statistic gone."; }
        // RAN: recall_bench.py rewritten: control searches name+title+body; query set = a LINKED record's body words (edges parsed from the tree) with both names removed, --self keeps the leakage set labelled; precision floor (target + 1-hop) printed; 2x2 + exact McNemar printed; corpus asymmetry printed (15108 vs 5799); dead 'both' gone; second control grep+1hop with candidate-set size. Also fixed: a 6000-char window that handed one-line elements the NEXT element's title and body - 10168 -> 5799 titled elements - which is why b02e953's recorded 100% and the original 24/50 were both artifacts. The harness now discriminates: it produced p<0.001 for the new ranker and ALSO the finding that grep+1hop beats it (issue367).
        part recallBenchmarkCanDiscriminateDoDR1 : TestResult { :>> id = "320abadb-9562-40c5-999e-a652343703d0"; :>> outcome = VerdictKind::pass; :>> judgedAgainst = "a40d876"; :>> judgedAt = "2026-09-04"; :>> judgedBy = "claudeOpus5"; }
        action processAmendmentsReachTheDefinition;
        verification processAmendmentsReachTheDefinitionDoD : Test { :>> id = "6f833768-8938-4235-a8d9-b395f44045a6"; :>> method = VerificationMethod::test; :>> procedureText = "DONE MEANS: a Decision that changes what an accepted process MEANS also edits the process definition, and carries the marker. D0243 changed the meaning of knowledge-graph-memory's steps 1 and 2 - declaring .knowledge/ optional and seeding corpus-derived - while carrying NO #ProspectiveChange/#SafetyChange marker (its sibling D0242 carries two) and never touching .engine/processes/knowledge-graph-memory.sysml, which mentions neither D0242 nor D0243. The keystone guard did not fire because the guarded artifact was never edited: the change was made AROUND the control. D0161 had already written the rule this breaks - 'A design may amend a process; it may not quietly disagree with one.' VERIFY: D0243's amendment is recorded in the process definition with a marked governing Decision; and a forward control detects the class - a Decision whose text amends a named process step while that process file is unchanged in the same commit."; }
        // RAN: part A: D0244 71b789b already carried D0243's amendment into knowledge-graph-memory.sysml (OPTIONAL comments on steps 1-2, marked); part B: guard 59 decision-amends-process, warning-tier, identifier-anchored; census 296 decisions: 17 name a step, 5 untouched, numbers 16/24 mostly not amendments; staged probe naming kgInjection -> 1 warning, removed -> 0; residual (D0243's unnamed sentence) armed by a test; cargo test 467/0 x2; clippy 0
        part processAmendmentsReachTheDefinitionDoDR1 : TestResult { :>> id = "ed184971-0ebb-44f9-b66c-4c936cb18235"; :>> outcome = VerdictKind::pass; :>> judgedAgainst = "75941cc"; :>> judgedAt = "2026-09-04"; :>> judgedBy = "claudeOpus5"; }
        action dcProveTheRemainingControls;
        verification dcProveTheRemainingControlsDoD : Test { :>> id = "1ad43bff-fa04-48ca-9251-ea3d8d6b45e7"; :>> method = VerificationMethod::test; :>> procedureText = "Resolves issue303. D0253 established that arming may be proven by TEST where a read-only view cannot establish it, and proved ONE control - ctlWriteLock, by six concurrent OS processes contending for the real lock. Sprint 486 proved a second, ctlLaunchDirtyRefusal. SEVEN remain with no evidence that they can fire: ctlPrePushBehind (a two-clone fixture can attempt a push - audit-history already built one), ctlReverify (run it against a fixture and assert a stale result is refreshed only on a real green), ctlPreWriteTiers (invoke the hook and assert it denies a protected path), ctlAuditAdherence (weaken a guard severity in a fixture and assert the build fails), ctlAdoptionCheck (break a unit and assert the foreign-tree gate catches it), ctlFireLedger, ctlAuditHistory, ctlBranchProtection and ctlReleaseGateJob (the last three are infra-resident and may end in a stated reason no local test can reach them - which is a legitimate outcome, recorded rather than assumed). DO: one probe per control, each proving the control ALLOWS on a clean case before asserting it REFUSES on a dirty one, since a control that refuses everything is stuck rather than armed. VERIFY: each proven control carries provenBy in control-arming.toml naming its test; keel controls reports the honest evidence count; any control that genuinely cannot be tested locally says so in its reason rather than being left silent."; }
        // RAN: remaining_controls_actually_fire.rs 4/4 (post-edit, stop, override, audit-adherence; each allow-then-refuse); adoption_check_can_fail.rs already 2/2; control-arming.toml +5 entries; show controls armingEvidence = armedByProbe 1, provenByTest 11, reasonOnly 3 (branch protection, audit-history CI, release gate job - each with its reason), proofMissing 0, undeclared 0; cargo test 471/0; clippy 0
        part dcProveTheRemainingControlsDoDR1 : TestResult { :>> id = "eb1246d9-9513-4bb4-9e86-f427626445c2"; :>> outcome = VerdictKind::pass; :>> judgedAgainst = "d3338c3"; :>> judgedAt = "2026-09-04"; :>> judgedBy = "claudeOpus5"; }
        action dcEveryAdvertisedViewIsBound;
        verification dcEveryAdvertisedViewIsBoundDoD : Test { :>> id = "9956ed08-2a8d-4623-802e-b7ea0dc84af7"; :>> method = VerificationMethod::test; :>> procedureText = "Resolves issue285, reported by the human from the console itself. They clicked attestation-coverage and got: no computed view is bound to the command. The CLI command works. Diffing the viewpoint registry against the server binding table found SIX advertised computed views with no binding - attestation-coverage, critique-policy, decisions, reprocess-candidates, verification, whats-next - so the model declared surfaces the server could not serve, which is the accepted-Decision-with-artifact-unbuilt class landing on the human's own oversight surface. DO: bind all six, and add a control that derives the ADVERTISED set from the viewpoint registry's renderer prose and the BOUND set from the table's own source, failing on any gap - neither side hand-maintained. VERIFY: all six return HTTP 200 with computed JSON from a live server; the control PASSES now and FAILS naming the exact command when a binding is removed, probed both ways; it refuses to run over an empty population."; }
        // RAN: bindings landed at e4e8ee8 (unrecorded until now); live keel-serve on :7791 -> GET /api/computed/{attestation-coverage,critique-policy,decisions,reprocess-candidates,verification,whats-next} all HTTP 200 viewStatus computed with content; mutation probe: removed the attestation-coverage binding -> every_advertised_computed_view_is_bound FAILED naming [attestation-coverage], restored -> passes; the test refuses an empty registry or an empty scrape; found and fixed the duplicate viewStatus key (issue368); cargo test 472/0; clippy 0
        part dcEveryAdvertisedViewIsBoundDoDR1 : TestResult { :>> id = "acdcee8a-2d48-4afa-af6f-c28566aa3b14"; :>> outcome = VerdictKind::pass; :>> judgedAgainst = "7bae4a0"; :>> judgedAt = "2026-09-04"; :>> judgedBy = "claudeOpus5"; }
        action dcRecorderIsDistinctFromJudge;
        verification dcRecorderIsDistinctFromJudgeDoD : Test { :>> id = "a479374a-3962-48aa-b093-f5556560f3cc"; :>> method = VerificationMethod::test; :>> procedureText = "Resolves issue287. The human accepted d0235 themselves through a human surface while the AI was working, with the note agreed with panel's decisions. delegatedAcceptanceSubstanceRule then FAILED the gate, demanding that the human quote themselves - governance aimed at the one party it must never bind. The rule is right in intent: a DELEGATED acceptance, one an AI records on the human's behalf, must quote their words or cite their gesture, because that is the only thing standing between a real sign-off and a fabricated one. The defect is that NOTHING RECORDS WHO RECORDED an acceptance, only who judged it, so the rule cannot tell a delegated record from a self-recorded one and applies the delegated demand to both. DO: (a) the console's accept path stamps its own channel in the note, appended never substituted, so a self-recorded acceptance self-evidences - the predicate already accepts a cited console or deck gesture; (b) record the RECORDER as provenance distinct from the judge, so the rule can scope itself to genuinely delegated records rather than inferring from note text. VERIFY: an acceptance recorded through the console carries its channel and passes; an AI-delegated acceptance with no quote still FAILS; the human's own words are never altered by either path."; }
        // RAN: (a) console stamp landed at e4e8ee8, appended never substituted (serve.rs CONSOLE_GESTURE); (b) accept_decision takes recorded_by -> createdBy on AcceptR1; console passes the judge, keel accept passes the judge or (with --by) the session actor and refuses unbound, standing-consent auto-accept passes the recorder; acceptQuotesDelegatedWords returns true when createdBy == judgedBy, unstamped records stay delegated; unit test the_substance_rule_binds_only_delegated_acceptances (5 cases incl. human's words unaltered by either path); live: D0299's own R1 judgedBy wweatherholtz createdBy claudeOpus5 passes the rule on its quote; cargo test 473/0; clippy 0; validate clean
        part dcRecorderIsDistinctFromJudgeDoDR1 : TestResult { :>> id = "3e76f68b-b959-4f10-b852-8acb144a43fa"; :>> outcome = VerdictKind::pass; :>> judgedAgainst = "d82c512"; :>> judgedAt = "2026-09-04"; :>> judgedBy = "claudeOpus5"; }
        action dcMechanismMustBePresent;
        verification dcMechanismMustBePresentDoD : Test { :>> id = "2a0d3ba3-528e-4128-9971-f2721fb16542"; :>> method = VerificationMethod::test; :>> procedureText = "Resolves issue290. Adopting the channel onto penumbra, the unit's MECHANISM never landed: both workflows and both scripts were absent from the merged PR, so the project had a process definition and a skill referencing scripts that do not exist. Cause was hand-staging - explicit paths were staged to avoid that repo's untracked junk and .github was omitted from the list, then deleted from the working tree, destroying the only copy. This is issue251 reproduced BY HAND after being fixed in the export. NOTHING CAUGHT IT: adoption-check gates a fresh fixture rather than a real target, so it verifies what export produces and never what a target actually received; and no guard flags a process whose declared mechanism files are absent. DO: (a) a check that a process referencing files under a declared extras path FAILS when those files are missing from the tree - the tool-reference guard already does this for .engine/tools, so extend the same predicate to a unit's declared extras; (b) prefer keel process import over hand-staging when adopting, and say so in the process definition, since the importer places every carried file and hand-staging is what dropped four. VERIFY: a project holding the channel process with no .github mechanism FAILS the new check; the same project passes once the files are present; the penumbra tree passes after the follow-up import; adoption-check gains a note stating it verifies the EXPORT and not a target."; }
        // RAN: guard 60 unit-extras-present: fixture with [x] files=[.github/workflows/x.yml] + installed x -> FAIL naming unit and path; file created -> PASS; this tree 0 scanned (no installed unit declares extras since D0292); unit tests 2 (violations both directions + not-installed skip; inline and multi-line arrays); inline-array blind spot fixed in process_cmd::unit_extras too; unit-extras.toml header: REQUIRED, import not hand-staging; adoption-check prints its scope; cargo test 474/0; clippy 0
        part dcMechanismMustBePresentDoDR1 : TestResult { :>> id = "e94e84a2-0f4f-4e61-9578-91cf82a1e7ed"; :>> outcome = VerdictKind::pass; :>> judgedAgainst = "a708369"; :>> judgedAt = "2026-09-04"; :>> judgedBy = "claudeOpus5"; }
        action scopeReferenceCopyOutOfTheInstanceModel;
        verification scopeReferenceCopyOutOfTheInstanceModelDoD : Test { :>> id = "33ec606d-2016-447b-98bd-9f701fa98226"; :>> method = VerificationMethod::test; :>> procedureText = "DONE MEANS: a downstream project's model no longer contains the engine's own attestations or evidence SHAs. In a fresh keel init fixture, the count of TestResults judged by an actor foreign to that project is 0, and every judgedAgainst SHA present in the model resolves in that repository (git cat-file -t). The 10 #JustifiedBy edges in .engine/rules/rules.sysml to dNNNN targets still resolve (check-engine clean) - whatever mechanism scopes the reference copy out must keep them resolvable or relocate them. Demonstrated by a test that RECORDS a fact in the fixture before asserting, since init-then-validate is the state in which this class is invisible (issue292)."; }
        // RAN: measured on a fresh keel init fixture AFTER recording a task and a passing result: attestation census = one judge row with one result (the probe), zero judged by wweatherholtz; orient invalidEvidence []; check-engine clean; edge-endpoints 0 violations with 236 reference decisions physically present. The property has held since view::model_dirs excluded .engine/reference (0bd61be, 2026-08-14, D0093) - issue292 (2026-08-27) misdiagnosed collect_sysml as the path; the gap it named correctly was the missing record-then-assert gate, now tests/reference_copy_is_out_of_the_model.rs. Mutation probe: model_dirs with the reference copy added -> the test FAILS at the leak assertion; restored -> passes. 1/1; suite 476/0 pending final run
        part scopeReferenceCopyOutOfTheInstanceModelDoDR1 : TestResult { :>> id = "5c1359b3-3353-4770-9520-c1387fbae708"; :>> outcome = VerdictKind::pass; :>> judgedAgainst = "93169c6"; :>> judgedAt = "2026-09-04"; :>> judgedBy = "claudeOpus5"; }
        action dcSprintFillIsAWritePath;
        verification dcSprintFillIsAWritePathDoD : Test { :>> id = "cb07a3fa-c329-43ad-8ef5-5fe49307e036"; :>> method = VerificationMethod::test; :>> procedureText = "Resolves issue267. Guard 52 flagged a result the write API never wrote: sprint ceremony records have been filled all session by a SCRATCHPAD PYTHON SCRIPT that emits TestResult lines directly, so it bypasses every check the write path carries - actor validation, the write lock, the method=confirmation refusal, and now the evidence receipt - and its R1 DOUBLE-STAMPS the R2 the API writes for the same test. Seven duplicate results in sprint467 alone, and sprints 461 through 466 carry the same shape, which also inflates the 5135-result population every attestation number is computed over. The author had already said it: if we need something consistently, build it into keel rather than a bespoke script. DO: sprint ceremony filling becomes a keel subcommand that writes gate PROSE only and leaves every verdict to append-result / append-gate-result, so there is one write path and one result per test; the scratchpad filler is deleted rather than retired in place. VERIFY: filling a fresh sprint produces ZERO TestResults; every result in a filled sprint comes from the API and carries provenance; guard 52 passes over a newly filled and stamped sprint; the duplicate-result count for a new sprint is zero."; }
        // RAN: new sprint --fill FILE (8 --- key sections, refused when incomplete, sanitised, zero results); unit test a_filled_sprint_has_prose_everywhere_and_no_result; sprint543 itself produced by the path: fill -> 0 TestResults, append-result -> 1; cli facts + commands.sysml; CLAUDE.md + sprint-closeout skill; clippy 0
        part dcSprintFillIsAWritePathDoDR1 : TestResult { :>> id = "9df5750a-5ed4-4f38-8bcf-d8ee0ecb3c95"; :>> outcome = VerdictKind::pass; :>> judgedAgainst = "bd996ee"; :>> judgedAt = "2026-09-04"; :>> judgedBy = "claudeOpus5"; }
        action dcVintageFixture;
        verification dcVintageFixtureDoD : Test { :>> id = "dea8a70d-862e-485b-8f94-b7f119a68104"; :>> method = VerificationMethod::test; :>> procedureText = "Resolves issue265. adoption-check gates a FOREIGN tree, but the fixture is a CURRENT keel scaffold - keel adopting keel, which is a weaker foreign-ness than a real adopter. Two real defects are invisible to it and both were verified invisible rather than assumed: issue263, a unit asserting a constraint it does not carry, because keel init ships the rules file defining the symbol so the reference RESOLVES in the fixture; and issue259, a control firing on a project that never adopted it, because every process in the fixture already carries the current conventions so a convention-based guard has nothing to fire on. Both manifested on penumbra only because penumbra is on an older VINTAGE. DO: a second fixture pinned to a prior RELEASE - obtained from the release channel rather than synthesised, so the vintage is real - and adoption-check gates units against it too, reporting the two fixtures separately so a pass on the current one cannot stand in for the older one. VERIFY: with the vintage fixture in place, reintroducing the issue263 assert makes adoption-check RED and removing it green; the current-fixture verdicts are unchanged; the report names which fixture each verdict came from."; }
        // RAN: adoption-check --vintage 0.3.0 --unit intake: real v0.3.0 asset fetched to .keel/bin/0.3.0 and version-proved; CURRENT clean/clean, VINTAGE clean/clean; issue263 probe (intake asserting unitExtrasPresent, defined now, absent in 0.3.0's engine): CURRENT clean, VINTAGE FAIL import refused by K8 naming unit-extras-present; removed -> both clean; two tables per fixture; vintage 0.2.3: no process import, said per unit; offline unit test; twelve constraint defs added + every_guard_has_a_constraint_def_identity (issue370); suite 480/0; clippy 0
        part dcVintageFixtureDoDR1 : TestResult { :>> id = "3ba6d2df-280f-47f6-830c-e3986f89f1bc"; :>> outcome = VerdictKind::pass; :>> judgedAgainst = "284bac7"; :>> judgedAt = "2026-09-04"; :>> judgedBy = "claudeOpus5"; }
        action dcAuditSeesSchemaReferences;
        verification dcAuditSeesSchemaReferencesDoD : Test { :>> id = "2e679d7f-0bee-4081-a6e4-255dfdb1e23f"; :>> method = VerificationMethod::test; :>> procedureText = "Resolves issue263. keel process audit reported decision-channel TRAVELS WHOLE, and it did not: imported into penumbra it left check-engine with an unresolved type reference, because the process asserts a constraint - judgmentRequestQuality - that is DEFINED IN THE SOURCE SCHEMA and is not part of the unit. The audit checks that a deploying skill exists, that the binding declaration travels, that declared extras are present and that no carried file cites a path the adopter will not have; it does not check that TYPE and CONSTRAINT names the carried files reference are ones the unit brings. DO: audit resolves every schema-defined name a unit file references against the names the unit itself carries, and reports an EXTERNAL REFERENCE as a portability risk naming the symbol - it cannot see the target schema, so it reports the dependency rather than a verdict about the target. Record the remedy the penumbra adoption used: an unclaimed guard is CORE, so dropping the assert is usually better than importing it. VERIFY: audit flags decision-channel judgmentRequestQuality reference; a unit with no external schema reference stays clean; the count of units reported clean does not silently rise."; }
        // RAN: keel process audit: 9 units now report one external constraint each, all defined in .engine/rules/guard-constraints.sysml (issue263 class); units without one show no line; TRAVELS-WHOLE count unchanged; unit test external_references_name_what_the_unit_does_not_carry (constraint/type/enum/own/schema/comment/import); cargo test 480/0; clippy 0
        part dcAuditSeesSchemaReferencesDoDR1 : TestResult { :>> id = "08825b5a-ee91-4f16-bc96-ff7701ea462f"; :>> outcome = VerdictKind::pass; :>> judgedAgainst = "136b455"; :>> judgedAt = "2026-09-04"; :>> judgedBy = "claudeOpus5"; }
        // Reordered 2026-09-01 (D0052/D0258): these resolve High issues found by the rigor panel and
        // the control-defect process, and sat below Medium items only because add-task appends.
        action dcSessionActorReachesHooks;
        verification dcSessionActorReachesHooksDoD : Test { :>> id = "63617d31-b425-4072-9847-342de61c62f4"; :>> method = VerificationMethod::test; :>> procedureText = "Resolves issue337 and CORRECTS issue332. actor::resolve (actor.rs:97-112) is right: explicit, then KEEL_ACTOR, then the machine binding. The ownership guard calls it (guards.rs:2498). The defect is that the Stop hook is spawned by the harness in an environment where KEEL_ACTOR was never set - it is exported per-command in the session's shell - so resolve falls through to the machine binding, which on this machine is a different model than the one working. 22 edits were attributed to the wrong actor and 12 items the session owns were flagged as non-owner edits. DO: a SESSION-scoped binding that resolve reads after KEEL_ACTOR and before the machine binding. The hook payload carries the session id (hook_pre_bash already receives it), so the binding is `.keel/sessions/<id>/actor`, machine-local and gitignored, written by `keel actor set --session <id> <actor>` and by the UserPromptSubmit hook when KEEL_ACTOR is present in its environment. VERIFY: a hook run with no KEEL_ACTOR but a session binding attributes to the session actor; with neither it falls to the machine binding as today; the ownership guard under the hook reports the same count as under the CLI with KEEL_ACTOR set. ARMED: the 12-vs-0 discrepancy observed today reproduces against the current binary. NOT a keystone change: actor.rs and the hook plumbing are outside D0209 clause 2's surface, which is why issue332's stated reason for carrying it was wrong."; }
        // RAN: actor::resolve now reads a per-session binding at .keel/sessions/<CLAUDE_CODE_SESSION_ID>/actor between KEEL_ACTOR and the machine binding; any command run with KEEL_ACTOR remembers it; the hook dispatcher seeds the session id from its payload. LIVE: with KEEL_ACTOR unset - the hook's situation - keel actor resolves to claudeOpus5 (the session) instead of claudeFable5 (the machine), read back rather than assumed. 3 unit tests on the pure halves: read-back by session id, a different session sees nothing, a malformed id never becomes a path, an unchanged declaration does not rewrite. NOT a keystone change - actor.rs and the dispatcher are outside D0209 clause 2 - which is what issue332's carry-reason got wrong
        part dcSessionActorReachesHooksDoDR1 : TestResult { :>> id = "82265feb-9a1f-4cd5-bdc0-61235c0bf5fb"; :>> outcome = VerdictKind::pass; :>> judgedAgainst = "24dcc73"; :>> judgedAt = "2026-09-01"; :>> judgedBy = "claudeOpus5"; }
        action dcControlDefectsAreFixed;
        verification dcControlDefectsAreFixedDoD : Test { :>> id = "1ec01088-5cfe-4809-84a4-324af844c18c"; :>> method = VerificationMethod::test; :>> procedureText = "Resolves issue333 (issue332 was resolved by dcSessionActorReachesHooks; issue331 is SPLIT to dcDecisionClausesAreAddressable behind fork d0303 on 2026-09-04, because its fix is a schema question and a clauses-versus-stories heuristic was measured at 40 hits with delivered and partial cases indistinguishable). ORIGINAL TEXT FOLLOWS, numbering as first written - the registry's numbering is the correct one: 331 decision-scaffolding, 332 ownership, 333 issues. NOT started; registered and carried deliberately, with the reason recorded per defect as the process requires. THREE INDEPENDENT FIXES, one campaign, and each is carried for a stated reason rather than for want of time. (1) issue333, ownership OVER-reporting: the guard reads the machine's bound actor instead of the effective session actor. DO: read it the way the write paths do - crate::actor::resolve, which honours KEEL_ACTOR before the binding. VERIFY: a session under KEEL_ACTOR is not reported as a non-owner of items it owns, ARMED against the current predicate where 12 false violations accompany 10 real ones. CARRIED because it is guard source under the keystone lock and needs its own signed Decision. (2) issue331, issues UNDER-reporting: a #Resolves edge to an unrelated task is indistinguishable from a correct triage. The hard part is that the distinguishing signal is PROSE - issue322 points at the same task deliberately - so DO one of: require the resolving task's DoD to NAME the issue id (a convention change with a 329-issue migration), or warn where the resolver's text does not mention the issue (noise traded for visibility). VERIFY: the issue323-shaped mis-triage is reported, and issue322's deliberate one is not. CARRIED because neither shape is a one-line fix and choosing between them is a proposal. (3) issue332, decision-scaffolding UNDER-reporting: one chartered clause satisfies a multi-clause Decision. DO: per-clause charter edges, which needs a Decision to have addressable clauses. VERIFY: a Decision with one of two clauses chartered is reported. CARRIED because it is a schema question. WHEN EACH LANDS: the fix is ARMED against the broken predicate (D0253 - a control-defect fix never observed to change a verdict has not been shown to fix anything), and its control-defects.toml entry is removed in the SAME commit that resolves the Issue, never before."; }
        // RAN: rescoped to issue333: unnamed_resolutions + issues guard forward-only naming (either direction), arming test a_resolver_that_names_neither_way_is_a_mistriage_forward_only, live run caught issue370's unstated link, [issues] registry entry removed, guards.md row; issue332 already resolved by dcSessionActorReachesHooks; issue331 split to dcDecisionClausesAreAddressable behind fork d0303 (judgment-request-quality PASS); cargo test 481/0; clippy 0
        part dcControlDefectsAreFixedDoDR1 : TestResult { :>> id = "cbb87608-5591-49db-bc37-26277914b36f"; :>> outcome = VerdictKind::pass; :>> judgedAgainst = "3990204"; :>> judgedAt = "2026-09-04"; :>> judgedBy = "claudeOpus5"; }
        action dcShippedCiRunsWhereItLands;
        verification dcShippedCiRunsWhereItLandsDoD : Test { :>> id = "55eb9c6f-dd15-4662-be0c-cbccf42efed3"; :>> method = VerificationMethod::test; :>> procedureText = "Resolves issue326 and issue327. ONE remedy for two defects that share a root: every CI workflow keel SHIPS was written for the engine's own repo and has never been observed to run anywhere else. NOT started. THE REMEDY IS NOT 'fill in the placeholder', and finding out why is the useful part: a CI that installs the LATEST binary would sit in D0251 skew against the project's own pin, and validate/guard REFUSE under skew on a gate surface (main.rs:226-230) - so the naive fix produces a red CI for a different reason. The install must read .engine/contracts/engine-version.toml and fetch THAT version. Feasible as of today: the engine repo is PUBLIC (verified via gh repo view), so an unauthenticated download works with no secret, and the release workflow attaches keel-linux-x86_64 per tag (release.yml:49-76). DO: (1) replace CI_TEMPLATE's three-echo install block (claude_surface.rs:162-185) with a step that reads the pin and downloads the matching release asset; (2) make decision-issue.yml and decision-record.yml build from source ONLY when a keel-cli crate is present and otherwise download the pinned release - one file correct in both homes. REJECTED, shipping a separate consumer VARIANT of each workflow: extras ship a file from path X to path X, so two variants at one destination would need a from/to mapping in unit-extras.toml, a contract change to carry two copies of a file that one conditional handles. REJECTED for the engine repo, downloading instead of building: its in-workflow gate exists to gate recorder commits with the code IN THAT COMMIT, so it must build from source. VERIFY, and the limit is stated rather than papered over: a structural test asserts the scaffolded template contains no bare echo-only install step and that both shipped workflows reference the pin file, and a fixture asserts the conditional selects download when no keel-cli/Cargo.toml is present. That is NOT a live green run in a consumer's Actions, which I cannot produce from here - the honest arming is a downstream project reporting its first green keel-gate run, and until one does, this remains verified-by-construction only."; }
        // RAN: decision-issue.yml and decision-record.yml build only when keel-cli/Cargo.toml exists and otherwise download the PINNED release to target/release/keel; toolchain steps gated the same way. CI_TEMPLATE's three-echo install replaced with one that reads engine-version.toml and fetches that exact asset. RUN FOR REAL: a fresh scaffold's pin read as 0.3.1 and the release asset downloaded as an 11.6 MB x86-64 ELF. Three structural controls pass: the_scaffolded_gate_installs_the_pinned_release_not_an_echo, the_shipped_workflows_build_here_and_download_the_pin_downstream, and the fixture's fourth property a_lived_in_projects_own_ci_survives_migration_and_installs_the_pin. LIMIT STATED: not a live consumer Actions run - the download is proven, execution on a runner is not, and pm5FeedBack is the channel that closes it
        part dcShippedCiRunsWhereItLandsDoDR1 : TestResult { :>> id = "51ce1e51-e849-4be0-b9c2-ddb5211df83a"; :>> outcome = VerdictKind::pass; :>> judgedAgainst = "6eafa86"; :>> judgedAt = "2026-09-01"; :>> judgedBy = "claudeOpus5"; }
        action dcHooksOutsideTheAgentsWritePath;
        verification dcHooksOutsideTheAgentsWritePathDoD : Test { :>> id = "e439633c-b7be-4900-8d03-8c83c0a38c69"; :>> method = VerificationMethod::inspect; :>> procedureText = "SPIKE (research, plan only - a hosting change is a Decision the human accepts). DONE when a Decision proposal ranks the hosting options for the keel hook set by WHO CAN WRITE THE HOST and WHAT STILL SILENCES IT, each claim checked against Claude Code's documented behaviour or a live experiment in a scratch project: (a) repo .claude/settings.json - today: agent-writable, live-reloading, drift is detected at push (claude-surface-drift) not prevented; (b) a keel plugin (hooks/hooks.json, user scope): the repo commit cannot change it, the agent's shell still can (~/.claude), the project cannot declare or pin it, and repo-scope disableAllHooks still turns it off (issue365); (c) plugin plus a ConfigChange/PreToolUse deny hook guarding its own host and the disableAllHooks key - measure whether the deny fires BEFORE the key takes effect or is itself disabled by it; (d) managed settings with allowManagedHooksOnly: the only host the agent cannot write, admin-deployed per machine, no per-project declaration, couples every project on the machine to one keel version. For each: what enrollment (actor-enrollment) can verify about the host at session start, and what the fire-ledger reconciliation (dcExternalFactGate) can prove after the fact. The proposal names the recommended layering, its cost, and what the third leg (CI re-derivation) already guarantees regardless."; }
        // RAN: six nested claude -p runs (2.1.260) in a scratch project with a --plugin-dir plugin logging PostToolUse/ConfigChange: baseline 2/2 fires; mid-session disableAllHooks silences the plugin hook (0 fires after); ConfigChange payload = session_id,cwd,hook_event_name,source,file_path only; unconditional exit 2 keeps hooks alive (2/2 after); key on disk at launch = 0 fires; --settings disableAllHooks:false over it = 2/2 fires. Docs read via claude-code-guide for precedence, merge, non-revert, plugin scope, managed path. Output: D0296 + four chartered items.
        part dcHooksOutsideTheAgentsWritePathDoDR1 : TestResult { :>> id = "9ac7ba8c-3b18-45ce-b5f9-bde24c29ffad"; :>> outcome = VerdictKind::pass; :>> judgedAgainst = "7d174a6"; :>> judgedAt = "2026-09-03"; :>> judgedBy = "claudeOpus5"; }
        action dcDriftGuardRefusesDisableAllHooks;
        verification dcDriftGuardRefusesDisableAllHooksDoD : Test { :>> id = "efc78859-bb04-4e7a-b5a0-9dfac7f55941"; :>> method = VerificationMethod::test; :>> procedureText = "DONE when `keel sync-claude --check` (the claude-surface-drift guard) and `keel hook pre-write` REFUSE a repo-scope Claude settings file (.claude/settings.json, .claude/settings.local.json) that sets disableAllHooks - Claude Code reads that key from ANY scope, so one agent-writable line silences every keel hook, including plugin- or user-hosted ones, while every keel-owned hook entry stays byte-identical and the drift guard reports clean. A unit test plants the key and asserts the refusal names it; CI runs the check (already does). allowManagedHooksOnly is admin-scope and out of reach; it is not refused."; }
        // RAN: cargo test --release 457 passed 0 failed (new: kill_switch_is_stripped_named_and_detected, pre_write_denies_the_hook_kill_switch_in_a_guided_project); clippy clean; live: settings.local.json with the key planted in this repo -> guard claude-surface-drift FAIL naming file+key, removed -> PASS
        part dcDriftGuardRefusesDisableAllHooksDoDR1 : TestResult { :>> id = "518b480a-57a0-42ab-823f-c564b6ee7503"; :>> outcome = VerdictKind::pass; :>> judgedAgainst = "cffe258"; :>> judgedAt = "2026-09-03"; :>> judgedBy = "claudeOpus5"; }
        action dcKeelPluginHostsTheHooks;
        verification dcKeelPluginHostsTheHooksDoD : Test { :>> id = "c9571568-0e92-40b5-8d3e-b37bd206572a"; :>> method = VerificationMethod::test; :>> procedureText = "DONE when the binary ships a Claude Code plugin - .claude-plugin/plugin.json and hooks/hooks.json - rendered by the SAME generator that writes the repo's .claude/settings.json hook entries (claude_surface.rs), so the hook set has one source and two renderings; `keel sync-claude` writes the plugin under .engine/claude-plugin/ (or the install location the item establishes) and `sync-claude --check` reports drift in EITHER rendering; the repository publishes a marketplace.json naming the plugin so a project's settings can carry it in extraKnownMarketplaces/enabledPlugins. RAN receipt: the RUN 1 shape of D0296 reproduced against the shipped plugin - a nested session loaded with --plugin-dir fires the keel post-edit hook, one fire-ledger line per fire."; }
        // RAN: cargo test --release 458/0 (new: plugin_rendering_is_the_same_hook_set_and_checked); clippy 0; claude plugin validate passed on both manifests; nested claude -p --plugin-dir .engine/claude-plugin in a fresh project with NO .claude/settings.json: fire-ledger shows user-prompt, post-edit, pre-bash, stop
        part dcKeelPluginHostsTheHooksDoDR1 : TestResult { :>> id = "bd0abb07-ef08-4ed7-99a7-47a3ec250855"; :>> outcome = VerdictKind::pass; :>> judgedAgainst = "c8e08f5"; :>> judgedAt = "2026-09-03"; :>> judgedBy = "claudeOpus5"; }
        action dcHookConfigChangeRestoresTheFile;
        verification dcHookConfigChangeRestoresTheFileDoD : Test { :>> id = "1cb7c487-b07e-41bd-a3a6-8e3ec719f913"; :>> method = VerificationMethod::test; :>> procedureText = "DONE when `keel hook config-change` exists and the plugin binds it to ConfigChange: it reads the settings file at the payload's file_path (the payload carries NO config content - D0296 RUN 3), exits 2 when the file sets disableAllHooks or alters a keel-owned hook entry, RESTORES the keel-owned subset in place because a blocked ConfigChange does not revert the file, and appends one fire-ledger line naming what it refused. RAN receipt: D0296 RUN 4 + RUN 5 reproduced against the real handler - the key written mid-session is denied and the file is clean within the same session; a following launch finds no key on disk. Unit test on the file-shape decision; the handler never blocks on a file it cannot parse (it reports)."; }
        // RAN: cargo test --release 460/0 (new: restored_settings_repairs_exactly_what_was_broken, config_change_refuses_and_restores_the_settings_file incl. two block lines in the fire-ledger); clippy 0; nested claude -p with --plugin-dir: agent wrote disableAllHooks:true, ledger shows config-change block exit 2, file on disk back to six events without the key, pre-bash and stop kept firing
        part dcHookConfigChangeRestoresTheFileDoDR1 : TestResult { :>> id = "9f307f0a-bd0b-43c4-aa70-60f1e4617f55"; :>> outcome = VerdictKind::pass; :>> judgedAgainst = "42fa740"; :>> judgedAt = "2026-09-03"; :>> judgedBy = "claudeOpus5"; }
        action dcLaunchPinsHooksOn;
        verification dcLaunchPinsHooksOnDoD : Test { :>> id = "e1abe451-1647-405d-9cbb-747218e0aca7"; :>> method = VerificationMethod::test; :>> procedureText = "DONE when both keel launch paths pin the hooks on above project scope: launcher.rs's claude -p spawn and a new `keel claude` wrapper (a CliCommand fact, family launch) pass --plugin-dir <shipped plugin> and --settings with 'disableAllHooks': false, and the run record's ledgerSignal reads the fire-ledger as today. RAN receipt: D0296 RUN 6 reproduced through `keel claude` - a project settings file carrying the key at launch, and the post-edit hook still fires."; }
        // RAN: cargo test --release 461/0 (new: hook_pin_args_pin_the_kill_switch_off_and_load_the_plugin_when_present); clippy 0; guard cli-surface-declared 102 scanned PASS with the claude fact; keel claude -p over a project whose settings.json holds disableAllHooks:true: hooks.jsonl user-prompt, pre-bash, post-edit, stop all fired; .keel/launch-settings.json = disableAllHooks false
        part dcLaunchPinsHooksOnDoDR1 : TestResult { :>> id = "964f2ec4-e566-4bda-acd4-1c32cfcefc7c"; :>> outcome = VerdictKind::pass; :>> judgedAgainst = "1652217"; :>> judgedAt = "2026-09-03"; :>> judgedBy = "claudeOpus5"; }
        action dcStatusReportsHookHosts;
        verification dcStatusReportsHookHostsDoD : Test { :>> id = "38b33a36-2433-4135-8ec9-935f385173e7"; :>> method = VerificationMethod::test; :>> procedureText = "DONE when `keel status` carries a hook-hosts line: which hosts are present for this project (repo settings declaration, plugin installed or --plugin-dir shipped, launch override available, managed settings present - read, never fetched) and whether any repo-scope settings file sets disableAllHooks, coloured per D0287 - an out-of-hook check, because a silenced hook cannot report itself (D0296 RUN 5). The control-structure view (D0284) lists the plugin and the launch override as hook sources when present, computed from the same reads."; }
        // RAN: cargo test --release 463/0 (new: kill_switch_is_attention_and_named, no_host_is_attention_and_a_clean_declaration_is_ok); clippy 0; keel status . -> hooks OK, 2 hosts, 6 events, plugin present; keel status over the poisoned fixture -> hooks ATTENTION naming settings.json + disableAllHooks; control-structure source lists both renderings; the in-repo plant was restored by this session's own config-change hook before status could read it (ledger block line)
        part dcStatusReportsHookHostsDoDR1 : TestResult { :>> id = "b369a6a6-b259-4871-8820-98ca1de25955"; :>> outcome = VerdictKind::pass; :>> judgedAgainst = "129bbc8"; :>> judgedAt = "2026-09-03"; :>> judgedBy = "claudeOpus5"; }
        action dcSanitizeMakesBackslashesSafe;
        verification dcSanitizeMakesBackslashesSafeDoD : Test { :>> id = "381083a2-0e7d-4344-836b-c07f1852c0d5"; :>> method = VerificationMethod::test; :>> procedureText = "DONE when every API write path that embeds prose in a SysML string literal (sanitize_field and any sibling in write.rs) makes a backslash safe - replaced with a forward slash, or escaped - so a Windows path or a regex in a Decision, DoD, Issue or Statement can never produce an invalid escape sequence; the write is REFUSED (not written) if the produced file fails to tokenize, so a record command never reports success over a file validate rejects. Unit test: a field containing a Windows path with backslashes (C:, Program Files, a file) round-trips through record decision --from and the file parses; a second test asserts the pre-write tokenize refusal path."; }
        // RAN: sanitize_field backslash -> slash; write_atomic parses every .sysml result and refuses InvalidData with the original intact; unit test both directions; live: record decision --from with C:/Program Files path in the fixture records slash-form and validates clean; FIRST FULL RUN 480/2 - the refusal caught launcher::finish embedding a Windows path through a second sanitiser (fixed: one sanitiser) and an atomicity test writing prose into a .sysml (fixed); the corrected total is in sprint547's implement gate. This line first said 482/0 before the run had finished - a false receipt, corrected by its author
        part dcSanitizeMakesBackslashesSafeDoDR1 : TestResult { :>> id = "411023d7-b105-4642-ac70-d317d0100dec"; :>> outcome = VerdictKind::pass; :>> judgedAgainst = "936dabc"; :>> judgedAt = "2026-09-04"; :>> judgedBy = "claudeOpus5"; }
        action dcOwnDoDDriftIsSuspect;
        verification dcOwnDoDDriftIsSuspectDoD : Test { :>> id = "4ca8175b-f731-4b6c-95da-25db5e714926"; :>> method = VerificationMethod::test; :>> procedureText = "DONE MEANS: a done task whose OWN DoD text changed since its passing result computes as suspect, exactly as it already does when a dependency's DoD changes. MEASURED 2026-09-02: orient.rs criterion_suspects compares only data.deps criteria against the verified commit; editing a done task's own procedureText (instanceAwareDoD widened with an unverified claim, orient run, reverted) produced no suspect entry and the task stayed done. The post-edit advisory (proactive.rs) mentions the drift at edit time and is non-blocking, so nothing computed carries it. WHY IT IS RANK ONE: the human's stated direction is trust-but-verify with the DoD as the gold standard - the thing verified must be the thing that was agreed, and today the owner of a task (usually the AI) may rewrite the criterion after the pass under D0108 with the pass still standing. Same mechanism as dcAcceptanceBindsToTheText (issue341): compare the text at the result's judgedAgainst SHA with HEAD; build them on one helper. DO: extend criterion_suspects to the task's own DoD; reason text names the task, both SHAs and that it is the OWN criterion. VERIFY: the live experiment above goes suspect with the edit and clean on revert; a dependency-criterion change still reports as before; the batched blob fetch stays batched (orientPerf) - orient timing before and after stated."; }
        // RAN: criterion_suspects extended to the own DoD in the same batch; live: widen dcVintageFixture's DoD -> suspect set gains exactly dcVintageFixture, revert -> clean; own_dod_drift_is_suspect integration test 1/1; orient 2.4s before -> ~4s after (3 runs 3.5-4.5s), one cat-file batch; cargo test --release --no-fail-fast 484 passed 0 failed (completed before this line); clippy 0
        part dcOwnDoDDriftIsSuspectDoDR1 : TestResult { :>> id = "8e2d2a65-dc42-4685-8ad0-048447469807"; :>> outcome = VerdictKind::pass; :>> judgedAgainst = "b1a1f99"; :>> judgedAt = "2026-09-04"; :>> judgedBy = "claudeOpus5"; }
        action dcAcceptanceBindsToTheText;
        verification dcAcceptanceBindsToTheTextDoD : Test { :>> id = "b0cfb1a7-5230-45a4-877e-3f73fa2ffe2d"; :>> method = VerificationMethod::test; :>> procedureText = "DONE MEANS: an accepted Decision whose text changed after its acceptance computes as NOT accepted, rather than as accepted. Landscape finding (agent-corral-landscape-2026-09-02, from mcp-scan's rug-pull class and PAuth's operand binding): acceptance today binds to a commit SHA (govern.rs acceptance_judged_against) and nothing compares the Decision body at that SHA with the body at HEAD - so the text a human signed and the text the tree carries can diverge silently, which is the same failure keel already refuses for evidence (judgedAgainst must resolve) and for confirmations (the quote receipt). DO: a guard - acceptance-binds-to-text - that, for every Decision carrying an acceptance, reads the decision/rationale/consequences fields at the acceptance's judgedAgainst SHA via git and at HEAD, and reports a violation when they differ; the acceptance is then reported by orient as suspect, exactly as drifted evidence is. Grandfather nothing: measure first, and if any accepted Decision already drifted, that is a finding to record, not a case to allowlist. VERIFY: a fixture with an accepted Decision, edit its decision field, guard goes red naming the Decision and both SHAs; revert, green; the live repo measured and its number stated."; }
        // RAN: guard 61 acceptance-binds-to-text (values compared, latest AcceptR, introducing-commit fallback, one batch); census 17/301 drifted (10 false positives on the first draft were formatting), issue371 recorded, 17 re-bound via keel accept --rebind under standing consent; live guard 302 scanned 0 violations; integration test acceptance_binds_to_text (green, red naming both SHAs + remedy, revert green, edit+commit+rebind green with AcceptR2); decision-amends-process ignores prose-unchanged staged Decisions; constraint def added; cargo test --release --no-fail-fast 486 passed 0 failed (completed before this line); clippy 0
        part dcAcceptanceBindsToTheTextDoDR1 : TestResult { :>> id = "47cf9936-6e8e-4e07-87a3-2d69ba8c68d0"; :>> outcome = VerdictKind::pass; :>> judgedAgainst = "eb0adcf"; :>> judgedAt = "2026-09-04"; :>> judgedBy = "claudeOpus5"; }
        action dcVerificationByAuthority;
        verification dcVerificationByAuthorityDoD : Test { :>> id = "8e75b225-7e93-4e61-9069-231e1b845d70"; :>> method = VerificationMethod::demo; :>> procedureText = "DONE MEANS: a proposed Decision, costed per option, on what a passing verification MEANS by authority and method - the human's revamp (st065): an automatic test verifies itself and satisfies its parent; anything else defaults to human judgment on evidence the AI proposes, presented in sets so the human is not hammered; the method kinds (analysis, demonstration, inspection, test) are leveraged, and an AI demonstration is feasible evidence. MEASURED 2026-09-02 (keel attestation): 4954 AI-judged results, 9 percent of the exercised ones carry a receipt, 3694 examined-by-AI are testimony; 323 human. This is a Change Request against the verification model and touches the frozen VerificationMethod vocabulary, so it is a FORK. OPTIONS to cost: (a) three tiers - machine (method test with a CI-verifiable receipt, self-satisfying; dcExternalFactGate is the mechanism), proposed (demo, analyze, inspect recorded by the AI as PROPOSED with evidence, pending until a human judges), human (confirmation, unchanged) - with a proposal SET as the unit the human judges, each item still recorded individually with a quote receipt so issue158 (a count accepted as a card) cannot recur; (b) the same tiers but AI-judged demo stays a pass when it carries a replayable receipt, human review sampled; (c) status quo with receipts made mandatory on all AI methods. For each: what changes for the 4954 standing results (grandfathered by date, never re-judged), what the human's per-sprint load becomes in items and in sets, and which guards change. The proposal is written AFTER the control structure view exists, because it binds authority to method and the authorities are what that view computes. VERIFY: passes judgment-request-quality; surfaced to the human through decision-surfacing; names the schema fields that change and the transform that carries existing results."; }
        // RAN: D0312 recorded as a FORK (options A/B/C with COST each, RESEARCH statement with the 2026-09-05 attestation census 5024/13pct/3698/323 and method mix, recommendation B with what would change it); judgment-request-quality PASS; written after the control structure existed (D0284) as the DoD required; schema fields named (outcome value proposed), transform named (D0067 migration of the outcome vocabulary)
        part dcVerificationByAuthorityDoDR1 : TestResult { :>> id = "8ca53ea5-5a10-4a7e-89c6-76a6f8eafb99"; :>> outcome = VerdictKind::pass; :>> judgedAgainst = "494d293"; :>> judgedAt = "2026-09-05"; :>> judgedBy = "claudeOpus5"; }
        action dcProvenanceAsRefs;
        verification dcProvenanceAsRefsDoD : Test { :>> id = "0d8000da-0814-60da-9b3e-0000003000da"; :>> method = VerificationMethod::demo; :>> procedureText = "Panel finding (e). `createdBy`, `owner` and `judgedBy` are `String` while `part def Actor` exists and is instantiated, so ~3000 attestation records carry an actor NAME that no viewer can navigate — you cannot select an actor and see what they authored or attested. This is the only trace that survives a provenance audit and it is the one with no edge, which matters directly under D0129, where provenance is never defaulted and an AI must never be able to pass as a human. NO PARSER GAP EXCUSES IT: all three fields are single-valued, and the single-valued `ref` assignment is confirmed portable in BOTH toolchains — the multi-valued sequence gap that sysmlv2-syntax-notes.md blames does not apply. DO: `ref createdBy : Actor[0..1];`, `ref owner : Actor;`, `ref judgedBy : Actor;`, with `ci` modelled as a registered tool Actor rather than a magic string. D0067 gated migration with a committed transform and reconciled control totals; the `actors` guard must see the identical actor set before and after, proven by capturing its output on both sides. VERIFY: an unregistered actor still FAILS the actors guard; confirmation-authenticity still distinguishes human from AI; every judgedBy resolves to a registered Actor; counts reconcile exactly; green at each phase."; }
        action dcUntrustedTaintClosure;
        verification dcUntrustedTaintClosureDoD : Test { :>> id = "a6aef919-39fe-4327-ad49-97f709c44952"; :>> method = VerificationMethod::test; :>> procedureText = "DONE MEANS: nothing transitively derived from an untrusted utterance reaches a privileged sink without the label travelling with it. Landscape finding (CaMeL capability labels): guard 56 untrusted-routing enforces the ROUTING of an untrusted Statement - plan only, propose a Decision, a human accepts. It does not follow the label through derivation: a UserStory derived from an untrusted Statement, a Need derived from that story, a task chartered by that Need - three hops and the label is gone, and the task builds. DO: compute the taint closure over #DerivedFrom / #CharteredBy / #Resolves edges from every Statement with sourceTrust = untrusted, and refuse (violation) when a tainted item is an accepted Decision, a #SafetyChange or #ProspectiveChange, a guard or contract edit, or a task whose sprint has an Implement gate passing - unless the path crosses a human acceptance, which is the point at which trust is conferred. VERIFY: a fixture chain Statement(untrusted) -> UserStory -> Need -> task with a passing Implement gate goes red naming the path; the same chain with an accepted Decision between Need and task is green; the live repo measured against the 14 untrusted statements it holds."; }
        // RAN: cargo test --release: 498 passed, 0 failed, exit 0 (2026-09-05) incl. tests/untrusted_taint.rs red+green on the DoD chain; keel guard untrusted-taint . 26 scanned 0 violations; clippy -D warnings clean
        part dcUntrustedTaintClosureDoDR1 : TestResult { :>> id = "d1e087d3-54a4-4ef3-8024-b81e71b77db0"; :>> outcome = VerdictKind::pass; :>> judgedAgainst = "95493091e898d6c1257c5c4097b86c26428965a0"; :>> judgedAt = "2026-09-05"; :>> judgedBy = "claudeOpus5"; }
        action dcRetroAlreadyTrackedMustName;
        verification dcRetroAlreadyTrackedMustNameDoD : Test { :>> id = "b3567d56-154f-4f2d-8676-90c047cddbba"; :>> method = VerificationMethod::test; :>> procedureText = "DONE MEANS: a retro that claims a finding is 'already tracked' must NAME the item that tracks it (an issueNNN or dcCamelCase token that resolves), or the retro-backlog guard reports a violation - the bare phrase no longer satisfies the guard. Found 2026-09-03 by the human's question: at least two retros this week (sprint 526, sprint 527) said 'already tracked' about findings no item tracked, and the guard passed both, because RETRO_NO_ITEM_JUSTIFICATIONS accepts the words. The other justifications ('no new item', 'no item needed', 'no further item') stay accepted only when the retro also names the sprint's own delivered item, so a retro cannot be empty and justified at once. VERIFY: the two retros above, re-scanned, would have failed; a retro naming a real issue passes; a retro naming a non-existent issue fails; the guard's own unit tests cover the three shapes."; }
        // RAN: cargo test --lib retro 12/12: already_tracked_with_no_named_item_is_a_violation, already_tracked_naming_a_nonexistent_item_is_a_violation, a_justification_that_names_a_real_item_passes_form, a_retro_that_mentions_verification_is_still_examined (the second shape, found by the first test failing with RETROS=[]), the earlier eight; count of skipped retros 27/510 (20 unjustified) by the fixed extraction; control-defects.toml retro-backlog entry removed in this commit; full suite 452/0; clippy clean
        part dcRetroAlreadyTrackedMustNameDoDR1 : TestResult { :>> id = "3f0b213d-b0cb-4af8-9b16-ac824725650e"; :>> outcome = VerdictKind::pass; :>> judgedAgainst = "4506a05"; :>> judgedAt = "2026-09-03"; :>> judgedBy = "claudeOpus5"; }
        action dcAppendResultFindsTheClosingBrace;
        verification dcAppendResultFindsTheClosingBraceDoD : Test { :>> id = "b084b1c5-578b-4f13-a1af-f150fe939189"; :>> method = VerificationMethod::test; :>> procedureText = "DONE MEANS: keel append-result and append-gate-result insert the TestResult after the verification block's CLOSING brace, whether the DoD is one line or many. GH#48 (st081): the insert followed the line that OPENS the verification block (the DoD's Test header), which is right only for a one-liner; a multi-line DoD got the result inserted inside itself and the error pointed at the wrong thing. The issue325 class (the write API corrupting the file it writes). VERIFY: a fixture with a multi-line DoD takes a result and validates; a one-liner still works; the error on a malformed block names the block."; }
        // RAN: cargo test --lib write::tests: a_result_lands_after_a_multi_line_dod_block_closes, a_dod_containing_a_brace_does_not_misplace_the_next_task, braces_in_ignores_strings_and_comments, a_dod_containing_quotes_cannot_break_the_backlog 4/4; live: brace text restored in backlog.sysml -> add-task probe lands at line 560 inside EngineBuild (18-562), file restored; small-fixture misplacement reproduced before the fix (zzB at package level) and gone after; full suite 455/0; clippy clean
        part dcAppendResultFindsTheClosingBraceDoDR1 : TestResult { :>> id = "821e3502-b332-40e9-9ccb-d9c3d08ab389"; :>> outcome = VerdictKind::pass; :>> judgedAgainst = "7c34bb7"; :>> judgedAt = "2026-09-03"; :>> judgedBy = "claudeOpus5"; }
        action dcTtyAcceptCitesTheGesture;
        verification dcTtyAcceptCitesTheGestureDoD : Test { :>> id = "dd1b40a8-d490-4282-9f2c-42b3b7d3cb9b"; :>> method = VerificationMethod::test; :>> procedureText = "DONE MEANS: keel accept run from an interactive terminal satisfies the delegated-acceptance substance rule by construction: the TTY is the human's gesture, so the recorded note cites it (the rule already accepts a cited deck/console/GitHub gesture) and the human's bare sentence is not required to be self-quoting. GH#53 (st076): six acceptances typed by the human at their own terminal, from the one path the docs told them to use, went red at the gate for want of a single-quoted span. The mirror of D0289 (which handles the agent-session path). VERIFY: a fixture accept with stdin a TTY (or KEEL_TTY_GESTURE=1 for the test) records a note that passes acceptQuotesDelegatedWords; the agent-session path is unchanged."; }
        // RAN: cargo test --release: 501 passed, 0 failed, exit 0 (2026-09-05) incl. tests/tty_accept_cites_the_gesture.rs; clippy -D warnings clean
        part dcTtyAcceptCitesTheGestureDoDR1 : TestResult { :>> id = "cdce2fbb-3366-48c6-b3e1-ed3cba0b810d"; :>> outcome = VerdictKind::pass; :>> judgedAgainst = "d697ae2927bde09c42b5a05d469da06e52e4cc29"; :>> judgedAt = "2026-09-05"; :>> judgedBy = "claudeOpus5"; }
        action dcHooksResolveThePinFirst;
        verification dcHooksResolveThePinFirstDoD : Test { :>> id = "38851503-bcbb-4952-ac13-4e3dbbe9326d"; :>> method = VerificationMethod::test; :>> procedureText = "DONE MEANS: every hook claude_surface generates resolves the keel binary in the same order as the git hooks (D0230): KEEL_BIN, then .keel/bin/keel(.exe), then PATH - so a project's turns and its gates run the same pinned engine. GH#43 (st086): the hooks tried PATH first, so a project pinned to 0.3.0 ran its turns on whatever keel PATH held, including an uncommitted build. VERIFY: a scaffold's settings.json hooks contain the .keel/bin probe before the PATH probe; a test asserts the order for every hook template; the shipped pre-commit hook and the generated hooks agree by string comparison."; }
        // RAN: same run: 501/0 exit 0 incl. claude_surface::every_hook_command_resolves_the_pin_before_path_in_the_git_hooks_order; keel sync-claude regenerated settings.json + plugin hooks.json (7 pin probes each)
        part dcHooksResolveThePinFirstDoDR1 : TestResult { :>> id = "2f0b1ce9-f391-40e4-9f1c-e75c6be1d605"; :>> outcome = VerdictKind::pass; :>> judgedAgainst = "d697ae2927bde09c42b5a05d469da06e52e4cc29"; :>> judgedAt = "2026-09-05"; :>> judgedBy = "claudeOpus5"; }
        action dcMigratePreservesProjectSections;
        verification dcMigratePreservesProjectSectionsDoD : Test { :>> id = "69ca5164-c921-4665-a4e1-9f0f839a15bc"; :>> method = VerificationMethod::test; :>> procedureText = "DONE MEANS: keel migrate never deletes a project-authored section of an engine-shipped contract file. GH#44 (st085): unit-extras.toml carried a project's own [unit] section and the resync rewrote the file wholesale, losing a published unit's declared payload with nothing reported. DO: a section keyed by a unit the project owns (present in its installed-units under a project-minted id, or absent from the engine's copy) is project-owned and is preserved through the resync; when preservation is impossible the migration REFUSES naming the section, per issue314's shape. VERIFY: a fixture with a project-authored section migrates with the section intact; a conflicting section refuses by name; the realistic-fixture suite gains this as its fifth property."; }
        // RAN: cargo test --release: 506 passed, 0 failed, exit 0 (2026-09-05) incl. migrate::section_merge_tests (merge + collision) and migration_fixture_is_realistic::a_projects_own_unit_extras_section_survives_the_resync_and_is_reported
        part dcMigratePreservesProjectSectionsDoDR1 : TestResult { :>> id = "58b484c0-2539-4fc7-9775-b298d31202e4"; :>> outcome = VerdictKind::pass; :>> judgedAgainst = "88864053792a741b681bcee2fe202d2d1b14dffe"; :>> judgedAt = "2026-09-05"; :>> judgedBy = "claudeOpus5"; }
        action dcAdoptionCheckReportsTheRealVerdict;
        verification dcAdoptionCheckReportsTheRealVerdictDoD : Test { :>> id = "04d5c74d-c765-4dcf-a090-f1160e6b06d7"; :>> method = VerificationMethod::test; :>> procedureText = "DONE MEANS: keel adoption-check reports PASS for a unit whose foreign gate is green and, when red, prints the failing check - never a PASS line relabelled as the reason. GH#45 (st084): every unit reported FAIL and the reason printed was a guard PASS line. Almost certainly the issue329 class: a substring test on gate output. DO: parse the gate's verdict line; VERIFY: a fixture with a known-good unit reports PASS; a unit with a real violation reports FAIL naming that violation; the parse is a function with unit tests, not a contains()."; }
        // RAN: same run: 506/0 exit 0 incl. adoption_check::verdict_tests (PASS-mentioning-FAIL out, FAIL verdict + ERROR detail in, order and cap); clippy -D warnings clean
        part dcAdoptionCheckReportsTheRealVerdictDoDR1 : TestResult { :>> id = "b632e583-04ca-44f8-bd38-3e0fde64c64e"; :>> outcome = VerdictKind::pass; :>> judgedAgainst = "88864053792a741b681bcee2fe202d2d1b14dffe"; :>> judgedAt = "2026-09-05"; :>> judgedBy = "claudeOpus5"; }
        action dcSurfaceDriftIgnoresLineEndings;
        verification dcSurfaceDriftIgnoresLineEndingsDoD : Test { :>> id = "c4ac2d6a-264b-480c-b011-d76a725f47a6"; :>> method = VerificationMethod::test; :>> procedureText = "DONE MEANS: guard claude-surface-drift compares the deployed .claude surface to the embedded contract with line endings normalised, so a Windows checkout (CRLF) of a file sync-claude wrote (LF) is not drift. GH#46 (st083): every fresh clone on Windows failed the guard on arrival. VERIFY: a fixture whose keel.md is CRLF passes; a fixture whose content actually differs still fails; the comparison helper has a unit test for both."; }
        // RAN: same run: 512/0 exit 0 incl. claude_surface::line_endings_are_not_drift_but_content_is and a_crlf_checkout_of_the_output_style_is_not_drift_but_a_changed_word_is; clippy -D warnings clean
        part dcSurfaceDriftIgnoresLineEndingsDoDR1 : TestResult { :>> id = "cbcfb0a5-2272-4205-9b88-383f52e30e93"; :>> outcome = VerdictKind::pass; :>> judgedAgainst = "d9e250e71ab615c2cac2723b71ffeabfad85ddb0"; :>> judgedAt = "2026-09-05"; :>> judgedBy = "claudeOpus5"; }
        action dcForwardOnlyCutoffIsTheProjectsOwn;
        verification dcForwardOnlyCutoffIsTheProjectsOwnDoD : Test { :>> id = "a5162436-07b3-4e92-a0af-12054e1015f3"; :>> method = VerificationMethod::test; :>> procedureText = "DONE MEANS: a forward-only rule's cutoff is the ADOPTING project's date, never the engine's. GH#47 (st082): delegatedAcceptanceSubstanceRule and delegatedConfirmationSubstanceRule ship predicate = ...(2026-08-22) - this repository's adoption date baked into a shipped rule - so a downstream project migrating into 0.3.1 was retro-failed on acceptances it recorded before it ever had the rule. The general form of issue068. DO: the cutoff resolves from the project's own record - the date the rule (or its unit) was activated or migrated in, recorded in the project's contracts - with the literal kept only as this repository's own value. Touches rules.sysml (keystone) and checks.rs. VERIFY: a fixture migrated on day D with acceptances before D passes; an acceptance after D without a quote fails; this repository's own cutoffs are unchanged."; }
        // RAN: cargo test --release: 512 passed, 0 failed, exit 0 (2026-09-05) incl. checks::cutoff_tests and tests/forward_only_cutoff_is_the_projects_own.rs (scaffold declared today: 2026-08-30 unquoted acceptance passes, today's fails)
        part dcForwardOnlyCutoffIsTheProjectsOwnDoDR1 : TestResult { :>> id = "ebffb1fa-7f23-4cf2-ae38-c7867e6ca3a0"; :>> outcome = VerdictKind::pass; :>> judgedAgainst = "d9e250e71ab615c2cac2723b71ffeabfad85ddb0"; :>> judgedAt = "2026-09-05"; :>> judgedBy = "claudeOpus5"; }
        action dcProcessStepsBindToChecks;
        action dcForkShapeIsDetected;   // resolves issue373 (High): ranked above the Medium work per the priority lens, D0311
        action dcExternalFactGate;   // resolves issue374 (High, stpa-self run 1): ranked with the High work, D0311
        verification dcProcessStepsBindToChecksDoD : Test { :>> id = "d73f9241-c475-46d8-9935-c22a8c07b437"; :>> method = VerificationMethod::test; :>> procedureText = "Resolves the panel's process-authority finding (rigorProcessAuthorityCritique) and its fact-lifecycle finding (rigorFactLifecycleCritique) - one root: a process is a document with an optional guard, not a machine, because a ProcessStep has no binding to a predicate and everything analytical lives in a String field no control can read. MEASURED: 37 processes, 16 assert any guard, 10 declared human-judgment, 11 UNDECLARED including five authored in the last two days - authoring outruns enforcement and only the author's memory converts one to the other. 'Enforced' means the process asserts a guard SOMEWHERE, not that each step has a check; only agile-workflow's ceremony steps have per-step gates, which is why `keel advance --to` can refuse there and nowhere else. THIS IS A PROPOSAL, NOT A BUILD, because both halves are schema questions under the frozen core: (a) a ProcessStep may declare the guard or rule that checks it - `checkedBy` - so a process can be asked which of its steps are enforced and `advance`-style refusal generalises beyond ceremonies; (b) the analytical fields that controls need to read stop being prose - a Decision's clauses as addressable children, a retro's findings as Issues by construction rather than by grep. DO: write the proposal as a Decision with the two options costed, and put it to the human as a FORK - it changes what a Process IS. VERIFY, for the proposal: it names the 11 undeclared processes and for each says whether a checkedBy binding is possible or whether it joins the 10 declared judgments."; }
        // RAN: keel guard judgment-request-quality . PASS (2 scanned, D0312 + D0321, 0 violations); keel show hardening . 2026-09-05: 37/15/10/12, each of the 12 undeclared processes read against its steps in D0321's research line; the fork published at https://claude.ai/code/artifact/634dee77-bdfb-49e1-925e-929f4a3c2bf4
        part dcProcessStepsBindToChecksDoDR1 : TestResult { :>> id = "2a24c5e5-ac07-4b06-8076-673fe3c92cde"; :>> outcome = VerdictKind::pass; :>> judgedAgainst = "18bbdc997f4aebe3eb740393643bda7cb4b11c58"; :>> judgedAt = "2026-09-05"; :>> judgedBy = "claudeOpus5"; }
        action dcDecisionClausesAreAddressable;
        verification dcDecisionClausesAreAddressableDoD : Test { :>> id = "38b49a60-f411-45c0-a1c1-8baced936acf"; :>> method = VerificationMethod::test; :>> procedureText = "DONE MEANS: whichever option of d0303 the human accepts is built, so decision-scaffolding sees a multi-clause Decision with an uncovered clause (issue331): under C, a CLAUDE.md convention line, a census view of the grandfathered multi-clause Decisions, and the guard exact for every new single-clause Decision; under A or B, the schema Decision, the D0067 migration and the guard learning clauses. The control-defects.toml [decision-scaffolding] entry leaves in the same commit. ARMED against the broken predicate first (D0253): a fixture Decision with two clauses and one chartered is reported before the fix is trusted. Blocked on d0303 until the human's word."; }
        // RAN: D0303 accepted on the human's words 'i do like C the best' (recorder claudeOpus5, judge wweatherholtz); decision-scaffolding: compound_decisions + clause_count, cutoff 2026-09-05; compound_decision_tests 1/1 (forward reported with count, pre-cutoff counted, single clause neither); live guard: 81 grandfathered, 0 violations; registry entry removed, registry empty and declared legitimately empty; CLAUDE.md + guards.md; cargo test --release --no-fail-fast 483 passed 0 failed (run to completion BEFORE this line was written); clippy 0
        part dcDecisionClausesAreAddressableDoDR1 : TestResult { :>> id = "c797531c-8150-478d-a3d6-d5476f60da25"; :>> outcome = VerdictKind::pass; :>> judgedAgainst = "fcd56db"; :>> judgedAt = "2026-09-04"; :>> judgedBy = "claudeOpus5"; }
        action dcLauncherFinishTestIsDeterministic;
        verification dcLauncherFinishTestIsDeterministicDoD : Test { :>> id = "be42407a-5bbe-4fa1-8b6a-8cd9e1ca5603"; :>> method = VerificationMethod::test; :>> procedureText = "DONE when finish_writes_a_record_carrying_every_declared_field (tests/launcher_controls_actually_fire.rs) passes in twenty consecutive full-suite runs, with the cause of its intermittent failure named in the test's own comment - not a retry loop, not an #[ignore]. OBSERVED 2026-09-04: failed once in a full cargo test --release run (suite stopped at 401 passed), passed alone and in the next full run; an earlier full run the same day stopped at 397 passed with one uncaptured failure. Capture the assertion text first (run the suite with --no-fail-fast and keep the output), then find the shared state - launcher::finish runs a gate and reads the fixture's ledger; the three tests in that binary share a process."; }
        // RAN: cause captured with --no-fail-fast to a file: got [.keel/sessions/] - the issue337 session binding written when CLAUDE_CODE_SESSION_ID is inherited; launcher::finish excludes .keel/ from a run's diff (machine-local by definition, K15); the test sets the variable to force the condition; cargo test --test launcher_controls_actually_fire x20 -> 20/20 3 passed; clippy 0
        part dcLauncherFinishTestIsDeterministicDoDR1 : TestResult { :>> id = "716bf7b9-7f52-42dc-b313-15ee725600d4"; :>> outcome = VerdictKind::pass; :>> judgedAgainst = "93169c6"; :>> judgedAt = "2026-09-04"; :>> judgedBy = "claudeOpus5"; }
        // ---- GH#54-59 (D0339, 2026-09-06): six downstream defects filed by the decider, Critical first, above every Medium ----
        action dcStandingWordsAreProjectLocal;
        verification dcStandingWordsAreProjectLocalDoD : Test { :>> id = "078a3673-7451-4546-b481-d60d3e565de6"; :>> method = VerificationMethod::test; :>> procedureText = "DONE MEANS: the words a standing-consent acceptance quotes are the ADOPTING project's own data, never a literal in the engine. GH#57 (st094, us093): the library unit's record_decision.sh hardcodes --by wweatherholtz and one human's quote; VERIFIED WIDER on main - keel record decision builds the AUTO-ACCEPTED note from a string literal of this repository's human's words (main.rs cmd_record), init ships attestation-policy.toml verbatim with standingConsent = d0207, and migrate resyncs the file wholesale (not project-owned) - so a fresh project with one declared decider auto-accepts every non-fork Decision in that decider's name quoting words they never said: a fabricated attestation produced by the engine (D0106 class). DO: attestation-policy.toml carries standingWords = '<verbatim>' beside standingConsent; record-time auto-accept quotes THAT and, with standingConsent declared but no standingWords, leaves the Decision proposed saying why; keel init resets the two grant lines (delegatedRecording, standingConsent) to commented-out templates - a grant is the human's, not the scaffold's; migrate treats attestation-policy.toml as project-owned so an adopter's grants survive a resync. VERIFY: a fixture with standingConsent and no standingWords records a Decision that stays proposed and the output names the missing words; with standingWords the note quotes exactly them; a fresh init has no live grant lines; migrate on a fixture with its own grants leaves them byte-identical; this repository's policy carries its human's words and its own auto-accept still works."; }
        // RAN: cargo test --release --no-fail-fast 543 passed 0 failed (suite577.txt); standing_words_are_project_local 3/3 (fresh scaffold has no live grant; consent without words stays proposed naming standingWords; consent with words quotes exactly them, never customizedly); standing_consent_at_record_time 3/3 and accept_honours_delegation 3/3 with fixtures granting their own consent; federation F9 policy byte-identical through migrate; clippy -D warnings clean
        part dcStandingWordsAreProjectLocalDoDR1 : TestResult { :>> id = "6c75af4d-e05e-4dc9-8627-e14c051dd81e"; :>> outcome = VerdictKind::pass; :>> judgedAgainst = "5e3a8285c6ad296313624db9da86390071ae94ab"; :>> judgedAt = "2026-09-06"; :>> judgedBy = "claudeOpus5"; }
        action dcRemovedTypeScannerReadsSchemaNotProse;
        verification dcRemovedTypeScannerReadsSchemaNotProseDoD : Test { :>> id = "14ea4e96-abfe-4a8b-9453-54b6d98dcc39"; :>> method = VerificationMethod::test; :>> procedureText = "DONE MEANS: migrate's removed-type and removed-enum scanners read SCHEMA, not the text inside double-quoted string literals. GH#59 (st092, us091): types_as accepts a Rust path separator (ureq::Agent) as a SysML typing colon, and step_removed_types scans whole lines, so a critic's quoted finding in an authored description BLOCKED a healthy project from moving vintage with no override surface; every REMOVED_TYPES name that is also an ordinary word (Task, Risk, Role) is exposed the same way. DO: blank double-quoted literals (structure preserved) before both scans in step_removed_types only - a type annotation never appears inside a string. VERIFY: a regression test with both arms - a removed type named in prose does not block, the same type as a real : Agent annotation outside quotes still does (so the fix cannot pass by never matching); the existing old-vintage arms still block on the Task annotation and the RiskLevel::high enum; a passthrough helper makes the new test fail with the reason it names."; }
        // RAN: cargo test --lib migrate 11 passed incl. a_removed_type_named_inside_a_string_literal_is_prose_not_schema (prose arm no blocker; real : Agent and RiskLevel::high still block; escaped quote honoured); old_vintage_tree_migrates_then_is_a_noop unchanged; full suite 543/0 (suite577.txt)
        part dcRemovedTypeScannerReadsSchemaNotProseDoDR1 : TestResult { :>> id = "a9085be4-e95b-4e72-9b27-5551a68a5768"; :>> outcome = VerdictKind::pass; :>> judgedAgainst = "5e3a8285c6ad296313624db9da86390071ae94ab"; :>> judgedAt = "2026-09-06"; :>> judgedBy = "claudeOpus5"; }
        action dcOneBinaryResolutionForEverySurface;
        verification dcOneBinaryResolutionForEverySurfaceDoD : Test { :>> id = "1fe69727-0655-474d-9b5f-e2ae4658e267"; :>> method = VerificationMethod::test; :>> procedureText = "DONE MEANS: every surface that gates this project - the scaffolded pre-commit hook, the generated Claude hooks and keelw - finds the SAME pinned binary, and each prints which binary it gated with. GH#55 (st096, us095): keelw and init write .keel/bin/<version>/<asset>; the pre-commit hook (lib.rs PRECOMMIT_HOOK) and claude_surface's RESOLUTION_ORDER (D0316) probe .keel/bin/keel(.exe) - a path nothing writes - then fall back to PATH silently, so a fresh project's commits and turns were gated by a +dirty PATH build while keelw ran the release, producing a false green and a false red on the same tree. D0316 fixed the order and left the mismatch. DO: one probe list in one place, shared by the hook text and every generated Claude hook: KEEL_BIN, then .keel/bin/keel(.exe), then the PIN's cache .keel/bin/<engine pin>/<platform asset> read from engine-version.toml, then PATH; every surface echoes the resolved path with its version and build commit before gating, so a PATH fallback is loud rather than silent. VERIFY: a test builds a fixture whose only binary is at .keel/bin/<pin>/<asset> and asserts the pre-commit text and every Claude hook resolve it before PATH; the shipped hook and the generated hooks agree on the probe list by string comparison; the gating line names the binary; this repository's own hooks still resolve (KEEL_BIN, then PATH) and say so."; }
        // RAN: cargo test --release --no-fail-fast 544 passed 0 failed (suite578.txt); claude_surface tests 11/11 incl. every_hook_command_resolves_the_pin_before_path_in_the_git_hooks_order (hook embeds pin_probe_sh verbatim) and the_probe_resolves_the_pins_own_cache_before_path (sh, PATH=/usr/bin:/bin); live: keel init scaffold with planted .keel/bin/0.3.1/keel-windows-x86_64.exe and PATH=/usr/bin ran pre-commit via the planted binary; live hook fire ledger line carries bin and build 0fd3173+dirty, keel status shows last hook fire; clippy -D warnings clean; sync-claude --check clean
        part dcOneBinaryResolutionForEverySurfaceDoDR1 : TestResult { :>> id = "923ac081-1d7c-48ec-b71f-14e843409e1f"; :>> outcome = VerdictKind::pass; :>> judgedAgainst = "0fd3173d5f34677db321c262d3fbcbe466fc07c6"; :>> judgedAt = "2026-09-06"; :>> judgedBy = "claudeOpus5"; }
        action dcSeededCacheIsVerified;
        verification dcSeededCacheIsVerifiedDoD : Test { :>> id = "f9cc4454-77e6-471b-9056-c3c4124983e2"; :>> method = VerificationMethod::test; :>> procedureText = "DONE MEANS: a binary in the wrapper cache is trusted only as far as it is verified. GH#54 (st097, us096): keel init copies WHATEVER binary ran it into .keel/bin/<version>/<asset> - a +dirty dev build became the pinned 0.3.1 for a project's whole life - and keelw execs a cache hit without comparing it to keel-wrapper.toml, so the correct checksum sat in the tree while nothing compared the cached file against it; the two binaries disagreed on 14 guard violations for one tree. DO: keelw verifies a cache hit's SHA-256 against the committed entry for that version whenever one exists and refuses on mismatch naming both hashes and the path (the download path already does this; a seeded cache is trust-on-first-use by another route); init seeds the cache only when the running binary's baked build commit is clean (no +dirty, not unknown) and prints what it did either way - seeded from this binary at <commit>, unverified until keel-wrapper.toml carries the release checksum; or NOT seeded, keelw fetches v<pin> on first use - never writing a checksum it made up. VERIFY: a keelw test with a cache hit whose hash mismatches the committed entry refuses and names both; a matching hit execs; no entry still execs (unverified, as today) and says so; an init test from a +dirty build leaves the cache empty and prints the reason; the seeded message names the commit."; }
        // RAN: cargo test wrapper_resolves_only_the_pin 7/7 (seeded binary mismatching the committed entry refused naming both hashes; hit with no entry runs and prints UNVERIFIED; five prior scenarios hold); only_a_reproducible_build_may_seed_the_wrapper_cache 1/1; live keel init C:/kt/initseed from build 5e3a828+dirty printed wrapper cache NOT seeded and left .keel/bin absent; full suite 543/0 (suite577.txt)
        part dcSeededCacheIsVerifiedDoDR1 : TestResult { :>> id = "438b3aa6-2738-400d-809c-17cf9591ec21"; :>> outcome = VerdictKind::pass; :>> judgedAgainst = "5e3a8285c6ad296313624db9da86390071ae94ab"; :>> judgedAt = "2026-09-06"; :>> judgedBy = "claudeOpus5"; }
        action dcCharterMustResolve;
        verification dcCharterMustResolveDoD : Test { :>> id = "6574f395-743d-4455-8eda-79f84741d0df"; :>> method = VerificationMethod::test; :>> procedureText = "DONE MEANS: an activation charter names a Decision the project holds, or the surfaces say so instead of asserting it. GH#56 (st095, us094): after a v0.3.1 migrate rewrote activation.toml with the engine's own (the issue314 class, fixed on main at 6583e08 - after the v0.3.1 tag, so unreleased), keel onboard reported the process set as CHARTERED by d0226, a Decision that project does not contain - a dangling provenance claim printed as fact on the command whose job is to answer on what basis the processes were chosen. DO: charteredBy is checked to resolve to a Decision in the project's own .engine/decisions; onboard and activation print UNRESOLVED CHARTER <id> - the set is not chartered here - and the activation-manifest guard fails on it, so the silent form of GH#56 becomes a loud one. VERIFY: a fixture whose charteredBy names an absent Decision fails the guard and onboard names it; a resolving charter still reports CHARTERED; this repository's own charter resolves; the release gap is stated in the sprint record as a fact for the deploy workflow, not fixed here."; }
        // RAN: cargo test --release --no-fail-fast 546 passed 0 failed (suite579.txt); charter_must_resolve 2/2 (dangling d0226 fails activation-manifest naming 0226-*.sysml, onboard prints UNRESOLVED CHARTER, JSON chartered false; own D0001 passes and reads CHARTERED); keel guard activation-manifest . PASS 32 scanned on this repository; clippy -D warnings clean
        part dcCharterMustResolveDoDR1 : TestResult { :>> id = "9e2e628c-1a48-402e-a6ba-de8b785c0b47"; :>> outcome = VerdictKind::pass; :>> judgedAgainst = "0d70e27634589958a3de92351c61df149e0d6bb4"; :>> judgedAt = "2026-09-06"; :>> judgedBy = "claudeOpus5"; }
        action dcLibraryUnitRetirement;
        verification dcLibraryUnitRetirementDoD : Test { :>> id = "dea452f3-7f6d-4bec-a90a-dd5075230e71"; :>> method = VerificationMethod::test; :>> procedureText = "DONE MEANS: a library unit its upstream has abandoned can be RETIRED in the library, and the retirement reaches every consumer. GH#58 (st093, us092) and GH#57 (st094, us093): keel-lib's decision-channel v6 ships .github/scripts/record_decision.sh (hardcoded actor and quote - a fabricated-attestation path) and decision-issue.yml (never creates the keel-standing label its script requires); this repository deleted the channel in sprint 527 (D0291), so library-stewardship rule 1 - publish from landed trees only - means the unit cannot be republished from here, and it stays importable with both defects. DO: keel process retire <unit> --why TEXT [--replaced-by TEXT] writes retired/retiredAt/retiredWhy/replacedBy into the library unit.toml and commits it in the library; import --from-library refuses a retired unit naming the reason and the replacement; keel status and keel library list mark an INSTALLED retired unit RETIRED with the why; the currency pass's drift lines carry it. Then decision-channel is retired: why = the channel's auto-accept path records an acceptance in a hardcoded human's name quoting words the adopting project's human never gave (GH#57), and its first run in a new repository dies on an undeclared label (GH#58); replaced by record-time standing consent in the binary (D0291) with the project's own words (dcStandingWordsAreProjectLocal). VERIFY: a library fixture retires a unit and a fresh import refuses naming the why; an installed retired unit shows RETIRED in status; the live keel-lib carries decision-channel retired after a deliberate push; the two GitHub issues are answered with the tracked ids."; }
        // RAN: cargo test --release --no-fail-fast 549 passed 0 failed (suite580.txt); library_unit_retirement 3/3 on an isolated HOME (retire writes and commits once, list marks, import refuses naming why and replacement, second retirement refused; short --why refused; status marks the installed retired unit and never offers it); keel guard cli-surface-declared . PASS 105; clippy clean; LIVE: decision-channel v6 retired in keel-lib commit c619e28 and pushed (main...origin/main in sync), keel library list reads RETIRED 2026-09-06, keel status here offers 10 units not 11
        part dcLibraryUnitRetirementDoDR1 : TestResult { :>> id = "cb02a34b-59ff-4ade-a6cb-f8f4c1675930"; :>> outcome = VerdictKind::pass; :>> judgedAgainst = "d5334b27a1bdfe5195b229155eccf6ef8642701b"; :>> judgedAt = "2026-09-06"; :>> judgedBy = "claudeOpus5"; }
        action recallRanksLinkedRecordsAsWellAsGrepDoes;
        verification recallRanksLinkedRecordsAsWellAsGrepDoesDoD : Test { :>> id = "e65d68a5-f630-4fdb-8a58-74db4f6032c3"; :>> method = VerificationMethod::test; :>> procedureText = "DONE MEANS: on the corrected harness's linked-record set (recall_bench.py, seed 20260828, 50 cases), the ranked recall payload contains the target at least as often as the second control - the rarest-word grep hits plus their one-hop neighbours - while showing no more rows than that control's candidate set (measured 2026-09-04: control+1hop 49/50 in a mean 16 candidates; ranked KG 41/50 in a mean 21 rows; hand-written 8-case set 5/8 against the previous ranker's 7/8, the two d0129 questions lost because the decision is two hops from every lexical match). The mechanism is open - a two-hop lift with decay, a narrower seed set when a term is rare, or a source-then-neighbours listing when one seed dominates - and must be chosen on the 50-case set and only then read against the hand set, never fitted to it. The hand set stays at 7/8 or better."; }
        // RAN: recall_bench.py (seed 20260828, 50 cases): KG 48/50 in mean 13 rows vs control+1hop 48/50 in mean 13 - first clause met; recall_ab.py read afterwards: 5/8 against the required 7/8 (d0129 x2, d0176 two hops from every lexical match) - second clause NOT met; cargo test 522/0
        part recallRanksLinkedRecordsAsWellAsGrepDoesDoDR1 : TestResult { :>> id = "4fda97a5-663f-4763-bbd7-0b3afa4b9a61"; :>> outcome = VerdictKind::fail; :>> judgedAgainst = "24782908c03af0c4d18a695d70304c0946be3228"; :>> judgedAt = "2026-09-05"; :>> judgedBy = "claudeOpus5"; }
        // RAN: recall_bench.py (seed 20260828, 50 cases): KG 49/50 in mean 13 ranked rows vs control+1hop 47/50 in mean 14 unranked, median position 3, McNemar p=0.000 - FIRST CLAUSE MET. recall_ab.py read afterwards: 6/8 against the required 7/8 - SECOND CLAUSE NOT MET. Sweep behind the choice, on the 50-case set only: conv(10,2,0.3) neutral, (10,2,0.6) 48/50, (10,3,0.6) neutral, (10,3,1.0) neutral, (10,3,1.5) 47/50, (20,3,1.0) 48/50; the rare-term narrowing was neutral at every threshold 40-800 so that set could not choose one, and at 1% of corpus it scored 5/8 - rejected and deleted. cargo clippy -D warnings clean
        part recallRanksLinkedRecordsAsWellAsGrepDoesDoDR2 : TestResult { :>> id = "12c1d209-332d-443c-98de-a3e4973ece0b"; :>> outcome = VerdictKind::fail; :>> judgedAgainst = "HEAD"; :>> judgedAt = "2026-09-06"; :>> judgedBy = "claudeOpus5"; }
        // RAN: recall_bench.py seed 20260828 50 cases: KG 49/50 in mean 13 ranked rows vs control+1hop 47/50 in mean 14 unranked, median position 3, McNemar p=0.000 on 44 discordant pairs - FIRST CLAUSE MET. recall_ab.py read AFTER the mechanism was chosen: 7/8 (required 7/8), stable over three consecutive runs, d0129 at position 8 on the rebase question - SECOND CLAUSE MET. Chosen on the generated two-hop arm added this sprint (D0364): off 15/50 median 8; DOMINANCE 1.25 22/50 median 5 with the one-hop arm unchanged, TAKEN; 1.1 27/50 but 48/50 and median 4; 1.0 36/50 but 45/50 and median 5 - refused by the pre-stated no-regression rule. The remaining hand-set miss is d0176, not reached by any mechanism (issue391). keel suite 570 passed 0 failed (receipt 91238ffbf2c6); validate 674; guard ALL PASS; clippy -D warnings clean
        part recallRanksLinkedRecordsAsWellAsGrepDoesDoDR3 : TestResult { :>> id = "7d20fcf3-24f5-4930-a986-e1fcac9c9fe2"; :>> outcome = VerdictKind::pass; :>> judgedAgainst = "018315ace003b7751ab5cb31f5ab653f2faa58bf"; :>> judgedAt = "2026-09-07"; :>> judgedBy = "claudeOpus5"; }
        action dcPreBashSeesHeredocSource;
        verification dcPreBashSeesHeredocSourceDoD : Test { :>> id = "92791ee2-2b66-45ea-8005-739390c4a207"; :>> method = VerificationMethod::test; :>> procedureText = "DONE when keel hook pre-bash (advisory, never blocking - issue094 lineage) recognises a Bash command carrying a heredoc whose body looks like source (Rust, Python, JSON or SysML: braces with quotes, backslash escapes, or backticks inside the body) and advises writing the file with the Write tool and running it by path - the shell eats backslashes and executes backticks, which broke an edit script three times in the week of 2026-09-01 (sprint528, sprint529, sprint531). Unit test on the recogniser: a plain heredoc of prose is silent; a heredoc with a Rust char literal or a backslash escape advises."; }
        // RAN: shellcheck::heredoc_with_backslash + pre-bash DENY in every profile (the one blocking pre-bash verdict); mechanism measured live: cat <<'EOF' collapses a backslash pair to one; unit test (source heredoc named, prose heredoc passes, backslash outside a heredoc passes, <<- and quoted tags); live hook: the exact Python-with-escapes shape denied, a commit-message heredoc silent; the control fired on its author one minute after being built (a census script with regex backslashes) and the script was written by path instead
        part dcPreBashSeesHeredocSourceDoDR1 : TestResult { :>> id = "1f5a6623-9073-42bc-bff8-e048e3274f57"; :>> outcome = VerdictKind::pass; :>> judgedAgainst = "6702c38"; :>> judgedAt = "2026-09-05"; :>> judgedBy = "claudeOpus5"; }
        action dcStpaProcessForKeel;
        verification dcStpaProcessForKeelDoD : Test { :>> id = "0a123f9f-95a4-441a-a293-9231b1d00087"; :>> method = VerificationMethod::demo; :>> procedureText = "DONE MEANS: a repeatable STPA process exists for keel's own workflow and its first run is recorded. The human (st065): a strong STPA process to identify control gaps if we are going to be that cavalier with AI. Recurring by their words, so D0040 makes this a CHANGE: define the process and skill BEFORE running it. STEPS: stpa1 losses and hazards reviewed (exist: 4 and 9); stpa2 the computed control structure read back (dcControlStructureIsComputed); stpa3 UCAs - for every computed control action the four types (provided, not provided, wrong timing or order, stopped too soon or applied too long) considered and each UCA recorded as an UnsafeControlAction with its context; stpa4 loss scenarios and controller constraints, each constraint traced to a control in control-map or to an Issue where no control exists; stpa5 re-run trigger - the process re-runs when the control structure view changes (a new hook event, workflow step, or write command), which the view can detect by diffing itself against its last recorded run. The proposal goes to the human as a Decision with the process definition attached. VERIFY: the process file passes process-skill and process-applicability; the first run records UCAs for at least the caAutoAccept, caRecordResult and caCommitLand actions, since those are where the landscape spike and the human's own words already point; every UCA either has a controller constraint bound to an existing control or an Issue naming the gap."; }
        // RAN: cargo test --release: 492 passed, 0 failed, exit 0 (37 binaries, 2026-09-05); keel guard stpa-currency . PASS, 1 warning naming 39 of 42; keel validate . 631 clean; check-engine clean; process-skill and process-applicability green in keel guard .
        part dcStpaProcessForKeelDoDR1 : TestResult { :>> id = "eb393b5e-09bc-44d0-bb35-257726efdd25"; :>> outcome = VerdictKind::pass; :>> judgedAgainst = "494d293340d569d911ff8a3ff7b07abe9da29526"; :>> judgedAt = "2026-09-05"; :>> judgedBy = "claudeOpus5"; }
        action dcConsentIsScopedAndExpires;
        verification dcConsentIsScopedAndExpiresDoD : Test { :>> id = "bd14f8d9-aaab-47ce-aba7-0668d8b69de4"; :>> method = VerificationMethod::demo; :>> procedureText = "DONE MEANS: a FORK Decision is written and put to the human on whether standing consent (D0207) binds to the revision of the rule it was granted under and whether it expires. Landscape finding: every in-path product the spike examined treats a standing, revision-unbound, non-expiring grant as the artifact to distrust - Entra Agent ID time-bounds grants and re-opens approval on extension, CapLease shows single-use tokens still replay under agent retry unless durable state records the confirmation event and remaining budget, and the untrusted commenter on the override thread asked exactly this. MEASURED: an auto-acceptance names D0207 and quotes the standing words but records neither the commit of the D0207 file nor the guard-set revision at acceptance (decision-issue.yml auto-accept step). OPTIONS, each costed: (a) keep as is and state why - the override thread is the escape valve and the human chose it; (b) stamp the D0207 revision and guard count on every auto-acceptance so a later change to the rule makes earlier consents visibly pre-revision (cheap, informational); (c) bind consent to the revision - a change to D0207 or a weakening of the guard set lapses standing consent until re-granted, so every auto-accept after it is refused until the human re-consents (a control, with a cost in interruptions); (d) add an expiry the human sets. VERIFY: the proposal passes judgment-request-quality (guard 48) - short name, rationale, per-option cost, a --research statement citing the knowledge record - and is surfaced to the human through decision-surfacing before the turn ends."; }
        // RAN: keel guard judgment-request-quality . PASS (D0324 scanned, 0 violations); D0324 recorded as a fork with 4 costed options and a research statement; page republished at https://claude.ai/code/artifact/634dee77-bdfb-49e1-925e-929f4a3c2bf4
        part dcConsentIsScopedAndExpiresDoDR1 : TestResult { :>> id = "87f07ece-6126-4e4c-a941-299cf12f3e9c"; :>> outcome = VerdictKind::pass; :>> judgedAgainst = "e04bf076c14114690fc656775c052e77b40ff8e3"; :>> judgedAt = "2026-09-05"; :>> judgedBy = "claudeOpus5"; }
        action shortDomainWordsCanSeed;
        verification shortDomainWordsCanSeedDoD : Test { :>> id = "a3eb95be-a8c0-42f0-bf5d-9624cf23e099"; :>> method = VerificationMethod::test; :>> procedureText = "DONE MEANS: a four-letter domain word seeds recall. Today a prompt token under five characters is dropped for LENGTH before frequency is ever consulted, so gate, hook, land, push and view never seed - while hooks does, which is arbitrary from the reader's side and was found only because a test's premise was wrong. The trade needs MEASURING, not guessing: lowering the floor to four re-admits been, does, made, that, this and more unless the language list grows to compensate, and the eight-case comparison is the instrument. VERIFY: with the floor lowered and the language list extended, the eight-case hit rate does not fall below 5/8 and a prompt of only short function words still pushes nothing; report both arms."; }
        // RAN: same run 524/0; recall_ab.py 5/8 (not below 5/8) with the distinctiveness floor vs 3/8 and 4/8 for the filler-list variants; keel recall on 'that this with from and the been does' pushes nothing and says why; gate/hook/land/push/view seed
        part shortDomainWordsCanSeedDoDR1 : TestResult { :>> id = "07b4f88d-8e37-4243-a025-517fcbf88c11"; :>> outcome = VerdictKind::pass; :>> judgedAgainst = "73ae2a232a67cb411194c79354aa763e64bf9d76"; :>> judgedAt = "2026-09-05"; :>> judgedBy = "claudeOpus5"; }
        action identifierMatchingAcceptsNaturalSpellings;
        verification identifierMatchingAcceptsNaturalSpellingsDoD : Test { :>> id = "4027c8e9-fc11-42dd-84e0-30950d31768c"; :>> method = VerificationMethod::test; :>> procedureText = "DONE MEANS: the one query-sensitive path that measurably works is not brittle across the spellings a person actually types. Measured by the panel and reconfirmed: `d0242`, `issue294` and `what does D0242 say` all seed correctly, while `issue 294`, `D-0242` and `decision 242` push NOTHING - is_identifier_token requires the digit run to abut the prefix with no separator. Three of six natural spellings fail, and identifier lookup is the case both the cost-benefit and IR critics named as the feature's real value. VERIFY: separator and bigram forms (`issue 294`, `D-0242`, `decision 242`, `sprint 480`) all seed the same element as the compact form, pinned by a test; no false positive on a bare number or a year."; }
        // RAN: cargo test --release: 524 passed, 0 failed, exit 0 (2026-09-05) incl. knowledge::tests::natural_spellings_of_an_identifier_seed_the_compact_form; keel recall on issue 294 / D-0242 / decision 242 / sprint 480 each seeds the compact element, named
        part identifierMatchingAcceptsNaturalSpellingsDoDR1 : TestResult { :>> id = "84e66525-3226-4daa-b2d7-a86aa1fdbad1"; :>> outcome = VerdictKind::pass; :>> judgedAgainst = "73ae2a232a67cb411194c79354aa763e64bf9d76"; :>> judgedAt = "2026-09-05"; :>> judgedBy = "claudeOpus5"; }
        action dcPanelRecordCorrections;
        verification dcPanelRecordCorrectionsDoD : Test { :>> id = "68f4ccaa-920d-4fa1-8903-cbc16fa0245c"; :>> method = VerificationMethod::test; :>> procedureText = "Resolves issue283. The facts pedant verified most of D0234's record and refuted six claims. byte-identical for a single-project repo is an over-claim: the multi-project predicate gates only message wording, and three changes alter single-project behaviour - the keystone filter, validate's refusal, and staged-path re-basing under a non-root project. verified against both real repositories undercounts the population by six; there are eight keel repos on this machine. no nested false positives was VACUOUS - the walk short-circuits at a root project, so it never examined a subdirectory in any of them. The two headline RAN evidence references in sprint469 DO NOT RESOLVE, being commits in deleted scratch repos, which violates D0129 inside the very receipt mechanism built to make a pass re-derivable by someone else. The refusal message misstates which directory is missing. An unexplained installed-units counter bump rode the commit. DO: correct each claim in the record; replace the scratch references with a reproduction recipe or a fixture test; explain or exclude the counter bump. VERIFY: every corrected claim is checkable and checks out; no evidence reference in the sprint fails to resolve."; }
        // RAN: cargo test --release: 524 passed, 0 failed, exit 0 (2026-09-05) incl. acceptance_binds_to_text.rs third phase; keel guard acceptance-binds-to-text . PASS (pending warning for d0234AcceptR2 until this commit lands); sprint469 receipts name land_gate/init_smoke/no_green_over_nothing tests and f356770, all resolving
        part dcPanelRecordCorrectionsDoDR1 : TestResult { :>> id = "8eb12f5e-fc7f-4404-8976-e22b952145ab"; :>> outcome = VerdictKind::pass; :>> judgedAgainst = "f84ff686e69a9d7770c67816aa2ecede8b84f470"; :>> judgedAt = "2026-09-05"; :>> judgedBy = "claudeOpus5"; }
        action dcComputedViewsRenderAndLink;
        verification dcComputedViewsRenderAndLinkDoD : Test { :>> id = "ac2548a5-545b-44db-ae42-0ee2e5ea7e1f"; :>> method = VerificationMethod::test; :>> procedureText = "Resolves issue286, reported by the human: tools give a vanilla json payload, needs to be displayed properly and link to items properly and dynamically. The generic viewpoint panel rendered every unbespoke view as pre JSON.stringify - a payload the reader parses by eye, with item names as dead text - while itemLink, openItem and the /api/item/:name endpoint had existed all along. The console had a working navigation mechanism the generic panel did not use. DO: a generic renderer that puts scalars in a headline row, arrays of objects in tables with the union of their keys as columns, and turns anything shaped like a keel item name into a live link that openItem resolves against the model AT CLICK TIME, so a view gains working links with no per-view code; keep the raw payload available in a collapsed details block, because a rendered table is a READING of the data and the reader must be able to check it against what the server sent. VERIFY: a computed view renders as tables rather than a JSON blob; an item name in it opens that item; a name that is not an item says so rather than failing silently; the raw payload is still reachable."; }
        // RAN: keel serve copy on :7791 (2026-09-05): /api/computed/open-issues is a dict renderComputed tables; /api/item/issue283 resolves, /api/item/notAnItemXyz answers found:false and openItem says so; GET / carries renderComputed + raw payload details; cargo test --release 526/0 incl. serve::tests::the_generic_panel_renders_tables_links_items_and_keeps_the_raw_payload
        part dcComputedViewsRenderAndLinkDoDR1 : TestResult { :>> id = "e25af0e9-1d36-4ff0-a050-a3b0800ce787"; :>> outcome = VerdictKind::pass; :>> judgedAgainst = "18270a81975f4de36c4a5f707b85babe8a4f0b9e"; :>> judgedAt = "2026-09-05"; :>> judgedBy = "claudeOpus5"; }
        action dcTabsFlagWhatNeedsTheHuman;
        verification dcTabsFlagWhatNeedsTheHumanDoD : Test { :>> id = "e157a929-4f15-4540-b769-83743d996833"; :>> method = VerificationMethod::test; :>> procedureText = "Resolves issue288, reported by the human: putting the number of views in the tab heading is bad, each tab should flag actionable items, because they open the console to RESOLVE things. The tab rendered the count of VIEWPOINTS on that surface - assurance (11) told them how many lenses it has, which is never the question a supervisor arrives with. The data was already there: /api/obligations computes what awaits the HUMAN per viewpoint, derived from viewpoints declaring surface=act, and carries a countable flag whose own note says a class with no bound counter must NEVER render as zero. DO: the tab shows a badge counting items waiting on the human, and NOTHING when none - a zero badge is noise; the viewpoint count moves to the tooltip rather than being lost; each viewpoint CARD carries the same badge so the surface says WHICH lens holds the work; a class with no counter renders ? and never 0; and a FAILED obligations fetch renders ? on every tab rather than vanishing, because an absent badge means zero and that would be a false all-clear. VERIFY: act reads 140 and the other five read nothing; inside act the three non-empty classes are badged 50/50/40 and acceptances-pending is not badged; the served page carries the flag markup; killing the obligations endpoint yields ? rather than a clean tab. STATE THE LIMIT: obligation classes come only from act-surface viewpoints, so a human obligation declared on another surface would not be badged - that is the declaration mechanism, not an oversight."; }
        // RAN: same serve: /api/obligations 4 act classes all countable (1/132/131/138) so act badges 402 and the other five surfaces nothing; GET / carries oblFlag with the ? branches for uncountable and failed fetch; suite 526/0 incl. serve::tests::tab_badges_count_the_humans_work_and_never_render_a_false_zero
        part dcTabsFlagWhatNeedsTheHumanDoDR1 : TestResult { :>> id = "b72a0846-a653-4b0e-bddc-311c1d687610"; :>> outcome = VerdictKind::pass; :>> judgedAgainst = "18270a81975f4de36c4a5f707b85babe8a4f0b9e"; :>> judgedAt = "2026-09-05"; :>> judgedBy = "claudeOpus5"; }
        action kgTravelsWithTheEngine;
        verification kgTravelsWithTheEngineDoD : Test { :>> id = "d8f64df5-63c5-4d42-8c7a-4588c4469327"; :>> method = VerificationMethod::test; :>> procedureText = "DONE MEANS: a downstream project gets recall AND injection with no authored vocabulary and no bespoke script. The mechanism rides the engine-generated UserPromptSubmit wiring (claude_surface.rs), so it propagates via `keel init` and `keel sync-claude`. Because D0243 made seeding corpus-derived, the human-owned half is now OPTIONAL: declare questions if you want question-coverage measured, declare aliases if your people use words the corpus does not. The knowledge-graph-memory SKILL is updated to say which steps are optional and which are the engine's, and must NOT ship this project's questions - .knowledge/ is instance data and inheriting it is the issue243 class. VERIFY: a fresh `keel init` project has the injecting hook wired, recalls facts over its OWN model with an empty .knowledge/, carries none of this project's questions, and `sync-claude --check` is clean."; }
        // RAN: fresh keel init at C:/t/kgfresh (2026-09-05): settings.json carries UserPromptSubmit; no .knowledge/ shipped; keel recall over its own 326 items answers; sync-claude --check clean; skill section added under D0332
        part kgTravelsWithTheEngineDoDR1 : TestResult { :>> id = "b7891fad-8c7e-49ec-b41a-54996bc5c7a0"; :>> outcome = VerdictKind::pass; :>> judgedAgainst = "18270a81975f4de36c4a5f707b85babe8a4f0b9e"; :>> judgedAt = "2026-09-05"; :>> judgedBy = "claudeOpus5"; }

        verification retireTheConfidenceProseDoD : Test { :>> id = "dc7a47d6-bd8f-43dd-93eb-7b9688d73166"; :>> method = VerificationMethod::test; :>> procedureText = "DONE MEANS: no surface claims a confidence gate that does not exist. confident() discards every parameter and returns seed_count > 0, so the only prompts silenced are those with no informative token - which prompt_tokens already rejects upstream. Yet three surfaces still assert a gate: the main.rs doc comment listing kill switch 3 ('a LOW-confidence prompt is not injected at all. Silence is the default whenever recall cannot show it has found the right thing'), a PASSING DoD (kgPromptPathInjects: 'Injection is gated on a CONFIDENCE verdict - silence beats noise'), and the printed HIGH/LOW label itself, where LOW is unreachable whenever any row is shown so the label carries no information while reading as if it does - the panel observed 'confidence HIGH' on a payload that was 14 of 17 rows off-topic. Also in scope, same class: three wrong or contradictory numbers in my own comments - the ceiling described as '~60' when it computes to 68, 'gate (5,736)' at one line and '5,806' at another, and the ceiling credited with dropping `gate` when the five-character length rule drops it first and it never reaches the frequency check. VERIFY: the doc comment, the DoD text and the label are corrected or removed together; a test pins that no surface names a gate the code does not implement."; }
        // RAN: confident()/recall_confidence() replaced by has_pushable_facts() which asks only whether an informative token survived; main.rs kill-switch-3 prose corrected to say it is NOT a confidence gate and why (2/8 vs 5/8); the passing kgPromptPathInjects DoD text corrected rather than left asserting a removed gate; the misleading HIGH/LOW label removed from the header, which now reads 'top score 27.4, named'; 14 suites 0 failures, clippy 0 errors, validate 536 clean, 0 of 52 guards failing
        part retireTheConfidenceProseDoDR1 : TestResult { :>> id = "4f638063-47de-481c-9e3d-5aa0184ba816"; :>> outcome = VerdictKind::pass; :>> judgedAgainst = "2bec54d"; :>> judgedAt = "2026-08-28"; :>> judgedBy = "claudeOpus5"; }
        action oneConsoleManyProjects;
        verification oneConsoleManyProjectsDoD : Test { :>> id = "c11def7a-3f26-40cc-9558-6c0473e10085"; :>> method = VerificationMethod::test; :>> procedureText = "DONE MEANS (D0245): running keel serve in a second project ATTACHES to the running console instead of starting another, the console's selector lists REGISTERED projects rather than whatever sits beside the active root, and a project in a DIFFERENT repository appears. Measured before: serve bound 7777 and hard-errored when taken, so a second project either failed or was given --port and became another window; /api/projects scanned the PARENT directory for siblings, which worked on this machine only because all eight projects happen to share a parent. VERIFY: with a console live, keel serve in another repo prints ALREADY RUNNING, registers, and exits 0 without binding; the registry holds absolute canonical roots with repo names; an entry whose directory is gone is pruned on read; keel serve --forget removes an entry without touching the project; two projects with the same label are disambiguated by repo and distinct labels are not; the registry lives outside every repository and is never committed; writes remain scoped to the ACTIVE project (rebind still refuses an invalid target rather than falling back)."; }
        // RAN: 14 suites 0 failures, clippy 0 errors, validate 537 clean, 0 of 52 guards failing | LIVE test against the human's own running console: keel serve from penumbra, passext and se-templates each printed 'ALREADY RUNNING ... attached, did not start a second' and exited 0 | registry at USERPROFILE/.keel/console.json holds 4 projects from 4 SEPARATE repos with canonical absolute roots, repo names and lastServed | git check-ignore reports the file is OUTSIDE the repository, and git status shows 0 tracked changes for it | display_labels test: distinct labels stay short, colliding labels qualify by repo | console_on returns false for an unbound port | DEFECT FOUND AND FIXED BY THE LIVE TEST: console_on matched the literal lowercase 'keel', but a real console's payload spells it only as viewerKeelApi, so detection failed and serve hard-errored on the occupied port - the exact failure the function exists to prevent, caused by the function
        part oneConsoleManyProjectsDoDR1 : TestResult { :>> id = "9fe842aa-a926-4e89-8dfc-e412d72c0d50"; :>> outcome = VerdictKind::pass; :>> judgedAgainst = "2bec54d"; :>> judgedAt = "2026-08-28"; :>> judgedBy = "claudeOpus5"; }
        action dcNoOpInvarianceControl;
        verification dcNoOpInvarianceControlDoD : Test { :>> id = "664ec1c7-c38a-4326-9402-6ae60afe61ce"; :>> method = VerificationMethod::test; :>> procedureText = "Resolves issue310. THE CONTROL: no-op invariance - a command told to make a change that is already TRUE must leave the file byte-identical. Chosen because it needs no inventory of human-editable facts and cannot be defeated by refactoring: regeneration is lossless only when the model can represent every byte present, so a no-op that alters the file proves a fact the writer cannot round-trip. It would have failed on issue293 the day it shipped. VERIFY: keel-cli/tests/no_op_writes_lose_nothing.rs 7/7 - no-op activate, repeated deactivate, no-op viewpoint switch, a hand-added user key surviving sync-claude (the .claude preservation claim asserted in a doc comment and never tested), a second sync being inert, a hand-added comment surviving migrate's pin re-stamp, and a COVERAGE FLOOR failing when the source grows a whole-file write to a tracked surface no case exercises. The floor must be shown to have found something REAL: it found engine-version.toml (migrate re-stamped from a template - the same class, fixed here) and named adoption-profile.toml and keel-wrapper.toml scaffold-only with the reason in the source."; }
        // RAN: // RAN: see sprint498. 7/7 including the floor, which found engine-version.toml as a live second instance and forced two scaffold-only writers to be named with reasons
        part dcNoOpInvarianceControlDoDR1 : TestResult { :>> id = "b1438bfb-b686-4f36-8aae-b1fee7157d90"; :>> outcome = VerdictKind::pass; :>> judgedAgainst = "6b43586"; :>> judgedAt = "2026-08-30"; :>> judgedBy = "claudeOpus5"; }
        action dcAttestationBindsToDevice;
        verification dcAttestationBindsToDeviceDoD : Test { :>> id = "9199c135-40b6-45a8-b918-0bf6a1389f73"; :>> method = VerificationMethod::test; :>> procedureText = "Charters D0201 OPTION B, which the human CHOSE on 2026-08-23 (d0201Accept: 'deck-tap signature binding: device HMAC on taps, read-back ratification for chat approvals', bound to a single uncontradicted tap, uid 553d2b58) and which no tracked work ever carried - found by the rigor audit seven days later, because the decision-scaffolding warning naming it stood unread behind 61 undischargeable warnings. DO: a deck tap carries a device-scoped HMAC so a recorded human attestation is bound to the device that made it, not merely asserted by the server that received it; a chat-sourced approval is ratified by READ-BACK before it becomes a method=confirmation result. VERIFY BOTH DIRECTIONS: a tap with a valid device HMAC records and one with an absent or wrong HMAC is REFUSED with nothing written; a chat approval that is not read back does not become a confirmation. THE SCOPE BOUNDARY: this binds a tap to a DEVICE, not to a person's identity - say so in the record, since an attestation that overclaims what it proves is worse than one that claims less."; }
        // RAN: cargo test --release --no-fail-fast: 533 passed, 0 failed, exit 0 (2026-09-05) incl. device unit tests (RFC 4231 vector), tests/device_bound_taps.rs (live serve: unsigned/unknown/wrong refused with nothing written; paired signature recorded and device-tagged), read_back_names tests, accept_honours_delegation updated to D0335; python .engine/tools/test_deck_e2e.py 20 ok exit 0 incl. an unsigned tap refused
        part dcAttestationBindsToDeviceDoDR1 : TestResult { :>> id = "8bcfd5b8-ef8b-45b0-a448-de9c746c562d"; :>> outcome = VerdictKind::pass; :>> judgedAgainst = "c850affdf3632c8cd59241064900f313de83ae38"; :>> judgedAt = "2026-09-05"; :>> judgedBy = "claudeOpus5"; }
        action dcMigrationRollsBack;
        verification dcMigrationRollsBackDoD : Test { :>> id = "a0d760ef-bae1-4d80-a16c-d8f8568c9891"; :>> method = VerificationMethod::test; :>> procedureText = "Charters D0252's unbuilt clause: a migration that cannot finish ROLLS BACK. migrate.rs contains no rollback today (grep: zero occurrences), so a migration that fails partway leaves a project in a state neither vintage - and D0067 already names a partially migrated project that reports success as the most expensive possible outcome. The existing guarantee is weaker than the Decision claims: blockers abort BEFORE anything is written, which covers refusal but not a mid-apply failure (a disk error, a permission denial, an interrupted run). DO: apply the plan so that a failure at any step restores the tree to its pre-migration state. VERIFY: a migration interrupted mid-apply leaves the tree byte-identical to its pre-run state, held by a fault-injected test - a rollback that has never been observed to run is a claim, not a mechanism (the arming discipline, D0253)."; }
        // RAN: see sprint503. Detected failure restores in-process; interruption is recovered by the next run via a pre-armed marker; a completed run clears it
        part dcMigrationRollsBackDoDR1 : TestResult { :>> id = "039c6196-f67d-4262-b869-a1ac742411cd"; :>> outcome = VerdictKind::pass; :>> judgedAgainst = "7c12f13"; :>> judgedAt = "2026-08-30"; :>> judgedBy = "claudeOpus5"; }
        action dcUngroundedRatioTriggers;
        verification dcUngroundedRatioTriggersDoD : Test { :>> id = "8447af70-032a-4a68-ab8d-646f67789d25"; :>> method = VerificationMethod::test; :>> procedureText = "Charters D0249's unbuilt clause: the rootedness ungrounded ratio becomes a TRIGGER for the latent-need derivation, not a number someone must think to read. Sprint 483's own retro named the failure this prevents - the Need set was inverted relative to the code for months and NO VIEW SAID SO, because tier-satisfaction reported 100 percent while rootedness held the honest number (415 of 482 ungrounded) and nothing ranked or raised it. A metric only readable by someone who already suspects the answer is not a control (D0047: manual vigilance is not a control). Today the ratio is absent from keel indicators entirely (verified 2026-08-30: zero matches). DO: publish the ungrounded ratio as a declared indicator with a stated trigger threshold that surfaces derivation work when crossed. VERIFY: the ratio appears in keel indicators; a tree pushed past the threshold surfaces the trigger and one below it does not - both directions, since an indicator that only ever says the same thing is not discriminating."; }
        // RAN: cargo test --release: 528 passed, 0 failed, exit 0 (2026-09-05) incl. tests/indicator_trigger_surfaces_work.rs (0% nothing, 100% surfaced) and reports::trigger_tests; live: keel show indicators . triggered ungroundedRatioIndicator 85.00 above 50; keel orient . burndown.triggers 1
        part dcUngroundedRatioTriggersDoDR1 : TestResult { :>> id = "07399753-6214-453c-8d1d-03cca20dfb37"; :>> outcome = VerdictKind::pass; :>> judgedAgainst = "c81f82ce739ae06c5fe5db950971e2dc92710b34"; :>> judgedAt = "2026-09-05"; :>> judgedBy = "claudeOpus5"; }
        action dcBatchedGovernanceIndex;
        verification dcBatchedGovernanceIndexDoD : Test { :>> id = "16960044-e826-4a27-96bd-7ced2939ef98"; :>> method = VerificationMethod::test; :>> procedureText = "Resolves issue316. The governance traversal is BATCHED so the antiquated-data question can actually be asked. Before: reprocess-candidates did not finish - 240 seconds, exit 124, zero bytes, measured twice - because each item cost a pickaxe search over full history plus a merge-base per process-change Decision (a single item timed at ~15s, so 501 stories is roughly two hours). DO: one rev-list builds the child map and forward-reachability sets per marker commit, so is_ancestor is a set lookup; one git log -p over .tracking/delivery maps every name to its introducing commit; charter edges come from the WORKING TREE, decision-introduction commits and process-def touches from one log each. VERIFY BOTH HALVES, because speed alone proves nothing: (1) the corpus lens EXITS 0, returns its answer and is NON-VACUOUS - an empty result on a corpus that has safety changes and items predating them would be a mis-aimed lens, not a clean bill of health; (2) the batched path is BYTE-IDENTICAL to the per-item resolver on three real corpus items chosen across vintages, since one item could agree by luck. Held by batched_governance_agrees.rs."; }
        // RAN: see sprint502. 240s timeout -> 46s; equality asserted byte-for-byte against the per-item resolver on storyRustS0Workspace, storyRustS1Lexer and needSetRederivationStory
        part dcBatchedGovernanceIndexDoDR1 : TestResult { :>> id = "107a9b04-6574-4a97-b24c-c536aec041c4"; :>> outcome = VerdictKind::pass; :>> judgedAgainst = "bd0d919"; :>> judgedAt = "2026-08-30"; :>> judgedBy = "claudeOpus5"; }
        action dcAutoUpdateVerifiedOrReverted;
        verification dcAutoUpdateVerifiedOrRevertedDoD : Test { :>> id = "f4f0b2ec-1e2d-4adf-801c-f7a5844a58bb"; :>> method = VerificationMethod::test; :>> procedureText = "Verifies srUpdateIsVerifiedOrReverted and srUnprovenUpdateAsksRatherThanActs. DEPENDS ON dcMigrationRollsBack - without a rollback, verified-or-reverted has no second half. THE GATE IS NOT 'EMPTY PLAN': tested during design and it is vacuous - when the plan is empty migrate returns at migrate.rs:739 BEFORE restamp_pin at :828, so auto-applying an empty plan achieves nothing including not advancing the pin; and any real upgrade plans at least the engine resync, so the criterion never fires where it matters. DO: record the pre-update commit; apply; run the project's own gate (validate + every enforced guard + check-engine); on green retain and report what moved including the pin; on ANY red or interruption restore to the recorded commit and report the gate's verbatim output. VERIFY BOTH OUTCOMES, since a boundary exercised only on the happy path is a claim: a green update is retained AND a red one leaves git status --porcelain EMPTY over .engine and .tracking. The red case is manufactured by shipping a guard the fixture tree violates - the issue089/issue090 class, which is why an empty plan proves nothing about safety."; }
        // RAN: cargo test --release --no-fail-fast: 534 passed, 0 failed, exit 0 (2026-09-05) incl. migration_fixture_is_realistic::a_green_update_is_retained_and_a_red_one_is_reverted_and_recorded (green retained + pin moved; red reverted, porcelain empty over .engine/.tracking, pin unmoved, attempt recorded, status and re-run name it)
        part dcAutoUpdateVerifiedOrRevertedDoDR1 : TestResult { :>> id = "0d90f57b-3d21-4162-8bb4-3e8f938edb79"; :>> outcome = VerdictKind::pass; :>> judgedAgainst = "9a726d2f2ee58a2a9faf64f518871bdca4ca41c0"; :>> judgedAt = "2026-09-05"; :>> judgedBy = "claudeOpus5"; }
        action dcLibraryStatusShowsDrift;
        verification dcLibraryStatusShowsDriftDoD : Test { :>> id = "1799a4d5-aa8c-4301-bba3-0378cf5ef38b"; :>> method = VerificationMethod::test; :>> procedureText = "Verifies srDriftIsReportedPerUnit. Today answering 'which of my units are behind' means reading keel library list and keel process show and comparing by hand - the friction the human named when they said they just want better distribution management. DO: one command listing each installed unit with its installed version, the library's version, and the update command for each unit that is behind. VERIFY: a project with a unit deliberately held at an older version reports it BEHIND and prints the command; a project at parity reports none behind; and a project with NO library configured says it cannot tell rather than reporting zero drift - 'nothing is behind' and 'I cannot tell' must not render identically, which is the pass-at-zero hazard this codebase has now caught three times."; }
        // RAN: // RAN: keel status reports units behind AND never-imported, with the exact command for each, plus cache age; an unreachable library reports UNKNOWN rather than zero drift (status_distinguishes_unknown 4/4)
        part dcLibraryStatusShowsDriftDoDR1 : TestResult { :>> id = "5eef6e2f-2c2c-41a2-941f-01ad6049fbbc"; :>> outcome = VerdictKind::pass; :>> judgedAgainst = "a16624c"; :>> judgedAt = "2026-08-31"; :>> judgedBy = "claudeOpus5"; }
        action dcScheduledCurrency;
        verification dcScheduledCurrencyDoD : Test { :>> id = "0c41fd98-4461-432c-bd24-bb1e9f673c9e"; :>> method = VerificationMethod::test; :>> procedureText = "Verifies srUnattendedPullIsIdempotent and closes the unattended half of nUnattendedCurrency. DO: a declared, removable schedule that runs the currency pass for a project - github-pull, library sync, and the drift report - and reports what it found in one place. Autonomy stays bound by D0264: a pull records utterances and NEVER triages, because triage is a judgment and an unattended judgment on untrusted input is the thing the trust tier exists to prevent. VERIFY: two consecutive runs over the same open issues produce identical Statements with no duplicate ids and the second REPORTS its skip count; the pass reports a library it cannot reach rather than treating unreachable as up-to-date; and the schedule is removable by deleting one declared file, per D0163."; }
        // RAN: cargo test --release --no-fail-fast 536 passed 0 failed (suite574.txt); keel currency . --by githubRecorder run twice: 6 ingested (GH#54-59 -> st092-st097) then 0 ingested / 18 already recorded; cargo test --lib currency 1 passed; keel guard cli-surface-declared . PASS 105
        part dcScheduledCurrencyDoDR1 : TestResult { :>> id = "b1270cfa-528c-4f8f-9c8f-3c899f18e1f1"; :>> outcome = VerdictKind::pass; :>> judgedAgainst = "c8a200e658d4d6d0c031ea68ddf66c3ef51c7852"; :>> judgedAt = "2026-09-06"; :>> judgedBy = "claudeOpus5"; }
        action dcUnknownFlagIsRefused;
        verification dcUnknownFlagIsRefusedDoD : Test { :>> id = "e388dac3-cf56-4f7b-b5dc-3539dabe7c27"; :>> method = VerificationMethod::test; :>> procedureText = "Resolves GH#14. A mistyped or unsupported flag used to be accepted as the ROOT: keel guard --read gated a directory literally named --read, found no files, and reported every guard PASS with 0 scanned. TWO defects compounding - silent argument mis-parsing and pass-at-zero - producing a GREEN RUN OVER NOTHING, which is worse than an error because it is indistinguishable from a clean tree. The same shape recurred while building github-ingest, where a trailing --at value was read as the root, which is why the fix is a SHARED refusal rather than a patch in one command. DO: refuse_flag_as_path on every path-taking entry point (guard, validate, check-engine), naming the argument and saying why refusing beats answering. VERIFY BOTH DIRECTIONS: all three commands exit 2 on --read and emit NO verdict line; and an ordinary ROOT argument still works AND actually scans the corpus - otherwise the refusal would have traded one vacuous pass for another."; }
        // RAN: // RAN: unknown_flag_is_refused 2/2 - guard, validate and check-engine all exit 2 on --read with no verdict line; an ordinary ROOT still scans the corpus (identity-present PASS, non-zero scanned). Reproduced the defect first: every guard PASS, 0 scanned, on a phantom directory
        part dcUnknownFlagIsRefusedDoDR1 : TestResult { :>> id = "c831a583-e72b-4068-ae52-4c33c9f4ab5d"; :>> outcome = VerdictKind::pass; :>> judgedAgainst = "9d349dd"; :>> judgedAt = "2026-08-31"; :>> judgedBy = "claudeOpus5"; }
        // PRIORITY INVERSION HERE IS DELIBERATE (D0258): this resolves a High issue and sits BELOW ten
        // lower-severity items on purpose, because it is BLOCKED ON THE HUMAN. It is a breaking change
        // to a surface 118 call sites invoke by name; ranking unworkable work to the top would make the
        // frontier lie about what can be picked up. It moves the moment they authorise it.
        action dcCliSurfaceConsolidation;
        verification dcCliSurfaceConsolidationDoD : Test { :>> id = "1b4e120f-3aca-4ac5-b3e1-fe47e671e3e4"; :>> method = VerificationMethod::test; :>> procedureText = "Resolves issue321, and is BLOCKED ON THE HUMAN'S CHOICE - it is a breaking change to a surface other things call by name, so it is not started on my initiative. MEASURED: 111 dispatch arms, ~30 of them read-only lenses performing one act (compute a view, print it); 16 of the 32 declared viewpoints also have a same-named top-level command, and the two mechanisms are only half-connected (keel view orphans fails while keel orphans works); 118 references in .engine skills and processes invoke these commands by name, and guard 39 fails a process naming a tool it did not receive. DO, if authorised: one `keel show <lens>` command routing to the existing implementations, every current name kept as an alias for a deprecation window so nothing breaks on landing day, then the alias list shrinks as call sites move. VERIFY: every lens reachable through the router returns BYTE-IDENTICAL output to its old command (a consolidation that changes an answer is a rewrite wearing a rename's clothes); every alias still works; the visible verb count falls below 25; and guard 39 stays green throughout, since a half-migrated skill reference is exactly what it exists to catch."; }
        // RAN: 35 lens verbs collapsed into keel show <lens>, old names REMOVED with no alias window (the human's choice over my recommendation). BYTE-EQUALITY: 31 of 31 comparable lenses byte-identical against outputs captured from the pre-collapse binary; the 1 that differed was hardening, and the diff WAS the change (it counts dispatched commands, 100 -> 66). 141 call sites rewritten across 57 files in the same commit, so no tree exists where a skill names a command the binary lacks. capability_refusal_bites 5/5 including both inventories held equal to their dispatch and a_retired_lens_verb_is_no_longer_a_command. Workspace suite 463 passed / 0 failed across 36 binaries; clippy clean; all 56 guards pass. MISSED CRITERION, stated: D0273 says the verb count falls below 25 and it is 66 - collapsing the lens family alone does not reach that, and the gate/record/audit families were never measured or argued
        part dcCliSurfaceConsolidationDoDR1 : TestResult { :>> id = "dd22a6e7-6802-4e58-8de5-f253e78e4eb5"; :>> outcome = VerdictKind::pass; :>> judgedAgainst = "cf985ec"; :>> judgedAt = "2026-09-01"; :>> judgedBy = "claudeOpus5"; }
        action dcObligationDoesNotLockTheTree;
        verification dcObligationDoesNotLockTheTreeDoD : Test { :>> id = "aba588f8-eb0a-494b-b147-025ed2e493d0"; :>> method = VerificationMethod::test; :>> procedureText = "Resolves issue324. NOT started. Three individually-correct controls compose into a lock: migrate refuses on a dirty tree (migrate.rs:652-687, and its git status --porcelain sees UNTRACKED files), committing to clean it fails because pre-commit validate refuses under engine-version skew (main.rs:226-230, D0251), and skew clears only by running the pinned binary or by migrate. The file that springs it is written by the engine itself - record_obligation (write.rs:471-481) under D0176/K7, whose own doc comment reasons about deadlock at the FILE level and misses it at the TREE level. DO: let migrate proceed when EVERY uncommitted path under .tracking/ is an engine-authored obligation record, and have it NAME the files it tolerated so the exemption is visible rather than silent. Keep the carve-out narrow - .tracking/obligations/ only, untracked-or-added only. The two rejected alternatives are the argument for this one: staging the file does not help (staged is still uncommitted), and degrading validate under skew weakens a gate to work around a different gate. VERIFY: a fixture project that is BEHIND ITS PIN and holds exactly one untracked obligation record runs migrate to completion; the same project with any OTHER uncommitted .tracking file still refuses; and the tolerated path is named in migrate's output. The test must be armed against the current binary, where it deadlocks. NOTE: not reproducible in this repo at all - check_preconditions refuses any tree holding keel-cli/Cargo.toml as a self-build (migrate.rs:664-666) - so this is downstream-only and the fixture is the only way to see it."; }
        // RAN: obligation_does_not_lock_the_tree 4/4 - a project behind its pin holding one engine-written obligation record migrates; the tolerated file is NAMED; any other uncommitted .tracking file still refuses naming what blocked it; a MODIFIED obligation record is not tolerated. ARMED: the escape and naming cases both observed FAILING against the pre-fix binary with the deadlock's own refusal text in the output. The first implementation was correct in principle and did nothing - git collapses a wholly-untracked directory to one entry, so -uall was needed for a per-file decision; found by running it, not by reading it
        part dcObligationDoesNotLockTheTreeDoDR1 : TestResult { :>> id = "d9e4bbd3-f8f8-4531-8d08-076b5fd0d9f5"; :>> outcome = VerdictKind::pass; :>> judgedAgainst = "0e001a6"; :>> judgedAt = "2026-09-01"; :>> judgedBy = "claudeOpus5"; }
        action dcUnitIdentityIsCarriedNotMinted;
        verification dcUnitIdentityIsCarriedNotMintedDoD : Test { :>> id = "2330649e-16b0-4b19-a1e0-eb018323f01c"; :>> method = VerificationMethod::test; :>> procedureText = "Resolves issue323. DONE in this commit. THE DEFECT: keel process export resolved a unit's id from unit-ids.toml alone - the registry of ids this project MINTED - so a project that IMPORTED a unit and re-published an improvement found nothing there, minted a fresh id, and shipped the improved content under an identity no consumer had ever installed; next_unit_version then missed on the new id and took its None arm, restarting the version at 1. Content changed, identity changed, version did not, so every consumer's drift check AFFIRMED they were current. DO: make the INSTALL RECORD outrank the minted registry in unit_id_for, repair unit-ids.toml in place when the two disagree (it is what the next export reads), REFUSE when one process name is filed under two ids, and make next_unit_version refuse rather than restart when the id misses on a process the project demonstrably has installed. VERIFY: the round trip issue323 named - publish, import into a second project, change one shipped file, publish again, and assert the unitId is UNCHANGED and the version INCREMENTED - plus the two refusal arms, all three ARMED by running them against the pre-fix binary (D0253) where all three fail. And repair the live damage: exec-summary was filed under two ids in this repo's own install record, both at v1."; }
        // RAN: unit_identity_survives_republish 3/3 - round trip keeps unitId across a republish from an importing project and advances v1->v2 with the improved bytes present; forked identity refuses naming both ids; registry disagreement is repaired in place. ARMED: all 3 FAIL against the pre-fix binary (git stash of process_cmd.rs), the round trip showing the re-mint directly, 9287c762 published over 969856ab. Live repair verified: library exec-summary now unitId a2428932 v2, 151-line SKILL.md, and the duplicate section is gone from installed-units.toml
        part dcUnitIdentityIsCarriedNotMintedDoDR1 : TestResult { :>> id = "b7a8f2c6-2490-432f-9f95-0bc0e308d336"; :>> outcome = VerdictKind::pass; :>> judgedAgainst = "93eb6dc"; :>> judgedAt = "2026-09-01"; :>> judgedBy = "claudeOpus5"; }
        action dcDodProseCannotBreakTheModel;
        verification dcDodProseCannotBreakTheModelDoD : Test { :>> id = "981f4add-8f9e-461f-b4e6-960f06813b52"; :>> method = VerificationMethod::test; :>> procedureText = "Resolves issue325. DONE in this commit. THE DEFECT: add_task_locked interpolated its DoD prose RAW into a SysML string literal (write.rs:1193) while every other prose write path bound sanitize_field. A DoD containing a double-quoted phrase closed the literal early and left the BACKLOG UNPARSEABLE, so the next command could not read the model at all - including to report the problem - and the repair had to be made by hand. DONE: sanitize at the WRITE PATH rather than in cmd_add_task, because issue322's lesson was that the previous prose defect recurred from being fixed per-command. SWEPT the whole file first rather than patching the one line: every other interpolation into a SysML literal in write.rs already routes through sanitize_field, so this was the last one. VERIFY: a_dod_containing_quotes_cannot_break_the_backlog writes a DoD carrying a quoted phrase, a newline and a tab, then asserts the interior holds no double quote, the phrase survives as apostrophes, it stays one line, and - the assertion that matters - the file still LEXES AND PARSES. ARMED per D0253 by commenting the sanitize call out: the test fails on the parse assertion."; }
        // RAN: a_dod_containing_quotes_cannot_break_the_backlog 1/1 - a DoD carrying a quoted phrase, a newline and a tab writes an interior with zero double quotes, the phrase surviving as apostrophes, one line, and the file still lexes and parses. ARMED: commenting out the sanitize_field call makes it FAIL at write.rs:1799 on the parse assertion. Swept write.rs first: every other interpolation into a SysML literal already binds sanitize_field, so the count of unsanitized ones is now zero
        part dcDodProseCannotBreakTheModelDoDR1 : TestResult { :>> id = "fc9c06bd-1ffe-4fb4-a7a5-c10570dba346"; :>> outcome = VerdictKind::pass; :>> judgedAgainst = "19eb078"; :>> judgedAt = "2026-09-01"; :>> judgedBy = "claudeOpus5"; }
        // CharteredBy d0275: the process Decision states this limit and this task closes it.
        action dcMigrationFixtureIsRealistic;
        verification dcMigrationFixtureIsRealisticDoD : Test { :>> id = "a64f1792-3b69-4af5-9841-4afe638d3812"; :>> method = VerificationMethod::test; :>> procedureText = "Charters D0275's stated limit. NOT started, and it is the prerequisite that makes every other migration claim more than construction. F9 in federation.rs proves a FRESH SCAFFOLD migrates - refusals fire, pin re-stamped, project comment preserved, adoption survived, gate green - and a fresh scaffold is the EASY case, which is why seven defects got past it. DO: extend the downstream fixture from a scaffold to a REALISTIC project, one that has each of the four properties the seven defects actually came from. (1) It CUSTOMISED an engine-shipped file, so the resync must preserve or conflict rather than silently replace. (2) It authored its OWN skill naming an engine command, so a removed or renamed command is detectable - this is the case D0273's clean break makes urgent. (3) It holds an UNTRACKED obligation record while behind its pin, which is issue324's deadlock and must be reproduced before it can be fixed. (4) It has its own CI workflow, so issue326 and issue327 become visible to a test instead of to a downstream human. VERIFY, and the arming matters more here than usual: cases 3 and 4 must FAIL against today's binary, because they encode defects that are still open - a green suite on all four would mean the fixture is not reproducing them. Cases 1 and 2 assert the behaviour that must hold. The honest completion signal is that the count of defects in this path found by a TEST rather than by a human stops being zero."; }
        // RAN: migration_fixture_is_realistic 3/3 - a lived-in project (behind its pin, a customised engine file, its own skill naming an engine command) migrates; the resync NAMES the files it wrote; the project's own skill survives untouched and the tree gates green; and issue324's escape holds on a realistic project not just a bare one. The fixture found issue328 on its first run - a customised engine file was silently discarded with only a count reported - which is what the fixture exists for. ARMED: emptying report_written makes case 1 FAIL. Case 4 (the project's own CI) deliberately NOT here: issue326/327 are open, so it would assert the defect or be an ignored test; it lands with the fix
        part dcMigrationFixtureIsRealisticDoDR1 : TestResult { :>> id = "5aeb0ad0-98ab-4abf-ae5d-669af2096c2e"; :>> outcome = VerdictKind::pass; :>> judgedAgainst = "6c21669"; :>> judgedAt = "2026-09-01"; :>> judgedBy = "claudeOpus5"; }
        action dcUnitDeclaresTheCommandsItInvokes;
        verification dcUnitDeclaresTheCommandsItInvokesDoD : Test { :>> id = "1fcaa5d1-aca1-4482-9b5a-d2fce4e924c5"; :>> method = VerificationMethod::test; :>> procedureText = "Builds D0252 clause A's COMMAND half, unbuilt since the Decision was accepted, and D0273's stated prerequisite. DONE in this commit. THE GAP: clause A promised that a unit declares the capabilities it invokes - guards, schema types AND commands - and that an install whose engine lacks one REFUSES naming the missing capability rather than a version number. Only the guard half shipped (D0183/K8). The token commands appeared nowhere in process_cmd.rs and unit.toml carried skills, rules, guards and extras only, so a renamed or removed command failed SILENTLY downstream: the skill landed and its instructions simply did not run. Clause A even records that renaming a command is a breaking change for units that declare it, recorded so a future rename is not made casually - and the human has now authorised exactly such a rename. DONE: a cli_surface module holding COMMAND_NAMES, the inventory the handshake diffs against; unit_commands derives the commands a unit's own files invoke by scanning for a keel-prefixed token that is ALREADY a dispatched name, so the scan is self-limiting and prose cannot invent a dependency; export writes commands into unit.toml; and the handshake refuses a unit naming a command this binary lacks, before any file is written, with NO --degrade escape - a missing guard leaves prose that still reads correctly, a missing command leaves prose that is actively wrong. VERIFY: the inventory MATCHES the dispatch both ways, parsed from main.rs at test time, which is what makes the const trustworthy since Rust cannot introspect a match at runtime - an inventory that drifts would refuse commands the binary has or accept ones it lacks. Plus: an exported unit declares a real command its text invokes and NOT a non-command token following the same prefix; and importing a unit needing a missing command refuses, names only what is missing, and leaves no file behind."; }
        // RAN: capability_refusal_bites 3/3 - the inventory matches the dispatch BOTH ways parsed from main.rs at test time (it caught one mismatch on first run, --version, a flag spelling not a command); an exported unit declares a real command its text invokes and NOT a non-command token after the same keel prefix; importing a unit needing an absent command refuses, names only the missing one, and leaves no file behind. 99 commands in the inventory. Workspace suite 457 passed / 0 failed; clippy clean
        part dcUnitDeclaresTheCommandsItInvokesDoDR1 : TestResult { :>> id = "1b4c0cb8-da2d-456f-a07d-2ab8b78cc79d"; :>> outcome = VerdictKind::pass; :>> judgedAgainst = "21cdce7"; :>> judgedAt = "2026-09-01"; :>> judgedBy = "claudeOpus5"; }
        action dcCountAssertionsParseTheNumber;
        verification dcCountAssertionsParseTheNumberDoD : Test { :>> id = "78d08f23-9c8b-4249-b1d1-a25db61a65db"; :>> method = VerificationMethod::test; :>> procedureText = "Resolves issue329. DONE in this commit. THE DEFECT: two tests asserted a non-zero count by NEGATED SUBSTRING - the form !text.contains('0 <label>') - which is wrong for every count ending in zero, because '580 tracked file(s)' CONTAINS '0 tracked file(s)'. It fired at 370 scanned, was repaired at that one site, and fired again today at 580 tracked files while an IDENTICAL live instance sat in unknown_flag_is_refused.rs untouched by the first repair. DONE: both sites now parse the number via count_before and compare it, which is the only form that says what was meant. AND THE CORRECTION BECOMES A CONTROL (D0047) rather than a third repair: no_test_asserts_a_count_by_substring walks every .rs file under tests/ and fails on any negated-substring count assertion, naming file and line. A lesson is not a control, and the next author reaching for the substring form should be stopped by a failing test rather than by remembering a doc comment. VERIFY: both repaired tests pass; the new control passes over the current corpus and its predicate is narrow enough that prose describing the shape - including its own doc comment - does not trip it. ARMED per D0253 by restoring the OLD form at the status site, where the test then FAILS while the parsed form passes."; }
        // RAN: both sites now parse the count; no_test_asserts_a_count_by_substring walks tests/ and refuses the negated-substring form, naming file and line. status_distinguishes_unknown 4/4 and unknown_flag_is_refused 3/3. ARMED: restoring the OLD substring form at the status site makes it FAIL where the parsed form passes
        part dcCountAssertionsParseTheNumberDoDR1 : TestResult { :>> id = "b07f9fc8-7070-451c-a92e-1ef000a96345"; :>> outcome = VerdictKind::pass; :>> judgedAgainst = "6c21669"; :>> judgedAt = "2026-09-01"; :>> judgedBy = "claudeOpus5"; }
        action dcTurnGateFailsClosed;
        verification dcTurnGateFailsClosedDoD : Test { :>> id = "bbe7ef86-738b-4112-b32d-435b8edcb404"; :>> method = VerificationMethod::test; :>> procedureText = "Resolves the panel's Critical finding (rigorTopologyCritique). The Stop hook - the turn gate - is fail-OPEN: on its own error it prints a warning and ALLOWS the turn to end. So do post-edit and subagent-stop. Only pre-write and the pre-commit git hook fail closed. A gate whose error path permits is a suggestion with a green light attached, and it holds exactly when nothing goes wrong - which is not when a rogue turn happens. DO: the Stop hook's ERROR path (validate crashed, a guard panicked, the binary could not be read) DENIES with the error text, the same way pre-commit does; post-edit stays advisory because a per-edit deny would trap editing on transient states, but says plainly that it is advisory. The harness TIMEOUT resolving to allow cannot be changed from inside keel and stays a recorded residual visible in the fire-ledger. VERIFY: a fixture where validate returns an error (not a violation - an ERROR) makes hook stop exit non-zero with the error in its output; a green tree still returns 0 silently; and the hardening enforcementPoints table reports Stop as fail-closed on error. ARMED against the current binary where the error path allows."; }
        // RAN: the Stop hook's wrapper now emits a block decision when the keel binary is not found, instead of printing 'this gate did not run' and allowing; advisory hooks keep D0134's fail-open. Test asserts both: the Stop command contains decision:block and the UserPromptSubmit command does not. Live: .claude/settings.json regenerated by sync-claude and read back BLOCKING; keel hardening enforcementPoints reports 3 fail-closed of 12 (Stop, pre-write, pre-commit), up from 2. The in-function error paths (validate error, rule-eval error, guard error) were already denied and are now described truthfully in the table. Residual: the second red pass still yields by design, and the harness timeout still allows
        part dcTurnGateFailsClosedDoDR1 : TestResult { :>> id = "64ad4969-cccf-4d2a-8922-e026c1568990"; :>> outcome = VerdictKind::pass; :>> judgedAgainst = "a52d81b"; :>> judgedAt = "2026-09-01"; :>> judgedBy = "claudeOpus5"; }
        action dcRetroFindingsRoute;
        verification dcRetroFindingsRouteDoD : Test { :>> id = "22371286-ce2b-4e97-b38b-d518abb60419"; :>> method = VerificationMethod::test; :>> procedureText = "Resolves the retro_backlog control defect (rigorSubstanceCritique, registered under D0278). THE PREDICATE, at guards.rs:1601-1628: fires only if the retro text contains the literal tokens AVOIDABLE-ISSUE or LESSON:, then is satisfied by names_tracked_item, which returns true when ANY dc-prefixed name appears anywhere in the file. Every sprint file names the task it delivered, so the check is satisfied by construction; and a retro that says FINDING is never examined. Today three control defects and three other findings went through it unexamined. The `changed` parameter - the staged file list - is accepted and discarded (`let _ = changed`), which is the tell: the guard was designed to ask whether THIS COMMIT records a new tracked item and never did. DO: (1) drop the vocabulary gate - a retro gate section with method analyze IS a findings record, examine all of them; (2) the satisfying condition is that the commit ADDS a tracked item - a new `part issueNNN` or `action dc...` in the staged diff - or the retro carries one of the explicit no-item justifications; naming an existing task is not enough, because that is what every retro does; (3) a violation, not a warning, once the corpus is clean. VERIFY: a retro whose analyze text contains a finding and whose commit adds no Issue or task FAILS; the same commit with a `record issue` in it passes; an explicit 'no new item: already tracked as issueNNN' passes. ARMED: today's sprint507 retro text with no new item must fail against the fixed predicate and passes against the current one."; }
        // RAN: retro_backlog on its third shape: every analyze-method retro gate examined regardless of vocabulary; satisfied only when THIS COMMIT adds a tracked item the retro's own text names, or an explicit no-item justification; a violation not a warning. 8 unit cases pass including both earlier failure modes as regressions - the co-staged-file hole (issue189) and the names-its-delivered-task hole (issue335) both FAIL against the new predicate. names_tracked_item and the vocabulary marker list are deleted. Live: this commit's own retro (sprint 514) names issue334-337, which this commit adds, and passes
        part dcRetroFindingsRouteDoDR1 : TestResult { :>> id = "cb2eca0c-7c78-42ca-98de-ecaf59b6f325"; :>> outcome = VerdictKind::pass; :>> judgedAgainst = "a52d81b"; :>> judgedAt = "2026-09-01"; :>> judgedBy = "claudeOpus5"; }
        // ---- THE READY FRONTIER, RANKED 2026-09-07 (D0052 / D0258 clause A / D0311) ----
        // THE SIGNAL: each ready item's COMPUTED class - its resolver Issue's severity, and how many
        // sprint retros named it as the already-tracked home of a finding (two = High, three or more =
        // Critical). Class descending; WITHIN a class the previous declaration order is kept, so the
        // judgment already embedded in that order is reassessed, not discarded.
        // WHAT IT DISCHARGES: 166 priority-inversion warnings, now zero, read back from
        // `keel show priority`. Eleven High-class items had been sitting from position 6 to 29, below
        // twelve Mediums and ten items with no resolving Issue at all - so `keel whats-next` was
        // handing out work in an order that contradicted the only computed priority signal we have.
        // Nothing here is a new judgment about any item's importance; the reorder only makes
        // declaration order agree with what the model already computed.
        action dcProcessRemoveCommand;
        verification dcProcessRemoveCommandDoD : Test { :>> id = "15630119-583c-444c-8387-545550477198"; :>> method = VerificationMethod::test; :>> procedureText = "DONE MEANS: keel process remove <unit> removes an installed process unit as one act under a co-committed Decision - the process file, its skill and registry, its declared extras, its installed-unit record, its unit id and its adoption entry - and refuses when any live surface still references the unit (tool-reference, process-skill, activation-manifest and control-map-reconciled would go red), naming the references so the remover rewrites them first. Twice now (exec-summary, sprint 524; decision-channel, sprint 527) a unit was removed by hand-editing two contracts because process lists, exports and imports and deactivate is not removal. VERIFY: a fixture imports a unit, removes it, and every contract and file is gone with the tree green; removal with a dangling reference refuses and names it; the library copy is untouched and the output says so."; }
        // RAN: cargo test --release --test process_removal: 3 passed 0 failed (removing_a_unit_takes_its_files_and_every_contract_entry, a_referenced_unit_is_refused_and_nothing_is_removed, removing_a_unit_the_project_does_not_have_says_so); keel suite 574 passed 0 failed receipt e6fce77cc683; keel validate clean; keel guard ALL PASS incl. cli-surface-declared after the cli_facts.rs mirror
        part dcProcessRemoveCommandDoDR1 : TestResult { :>> id = "1ca04102-9934-4cc6-aeeb-0c2ed0390b6b"; :>> outcome = VerdictKind::pass; :>> judgedAgainst = "e0624f36948cba80c35b5408643a970c0bd615d8"; :>> judgedAt = "2026-09-07"; :>> judgedBy = "claudeOpus5"; }
        action dcTestsDoNotWriteTheLiveTree;
        verification dcTestsDoNotWriteTheLiveTreeDoD : Test { :>> id = "8327a0eb-72ed-43c4-8912-e88939c46374"; :>> method = VerificationMethod::test; :>> procedureText = "Resolves issue339. DONE in this commit. adoption_check_can_fail.rs ran `keel process export intake` with no cwd, so the export resolved to the LIVE repository root - and export writes the origin's install record (D0183), so every test run bumped the real project's intake unit version in .engine/contracts/installed-units.toml. Found because the file showed as modified AFTER `git add -A`, during the suite. DONE: the export runs from the test's own scaffolded fixture, which has the process because init copies .engine. VERIFY: the test passes, and after a full run the live installed-units.toml is unmodified - checked with git status, not assumed."; }
        // RAN: adoption_check_can_fail 2/2 with export running from its own fixture; after the run, git status shows installed-units.toml unmodified (0 lines), where before the fix it showed the intake version bumped
        part dcTestsDoNotWriteTheLiveTreeDoDR1 : TestResult { :>> id = "dd32f941-0b9b-45c5-954f-34f64351c9b6"; :>> outcome = VerdictKind::pass; :>> judgedAgainst = "3bb0125"; :>> judgedAt = "2026-09-01"; :>> judgedBy = "claudeOpus5"; }
        action dcPublishSaysWhatMoved;
        verification dcPublishSaysWhatMovedDoD : Test { :>> id = "fcd7bffb-507a-49b2-a5e5-4bc7370dd657"; :>> method = VerificationMethod::test; :>> procedureText = "Resolves issue340. NOT started, Low. publish's no-op detection (issue302) compares the unit's FILE hashes against the install record and holds the version when they match - correct. But it does not compare the MANIFEST, so a manifest-only change (today: every unit gained a `commands` line under D0252 clause A) produces a library commit titled 'publish X vN' at an unchanged N, and the log reads as if the same version was published twice. DO: the no-op check hashes the manifest it would write against the manifest in the library clone; identical files AND identical manifest is 'nothing to publish'; changed manifest with unchanged files commits with a message that says so - 'publish X vN (manifest only)'. VERIFY: re-running publish with no change is a stated no-op and no commit; a manifest-only change commits once with the qualified message and a second run is a no-op."; }
        // RAN: cargo test --release --no-fail-fast 550 passed 0 failed (suite581.txt); library_publish 4/4 incl. a_manifest_only_change_commits_once_saying_so_and_the_version_does_not_move (one commit subject publish X vN (manifest only), version line unmoved, second run stated no-op); clippy -D warnings clean
        part dcPublishSaysWhatMovedDoDR1 : TestResult { :>> id = "7e7e9d3d-912e-426a-87c2-22f3ab16743c"; :>> outcome = VerdictKind::pass; :>> judgedAgainst = "515cf802732f91cdab73150b530052ecf83561eb"; :>> judgedAt = "2026-09-06"; :>> judgedBy = "claudeOpus5"; }
        verification dcExternalFactGateDoD : Test { :>> id = "ca28a415-669d-4425-b30b-b84c8cf1d833"; :>> method = VerificationMethod::test; :>> procedureText = "DONE MEANS: one class of TestResult can be satisfied ONLY by an external fact keel queries, never by the agent's assertion. Landscape finding (Beads gh:run gates): a gate that closes only when a real green CI run exists for the judged SHA is a gate the agent cannot talk its way past; keel's append-gate-result --evidence still records what the agent SAYS it ran. DO: a method or evidence kind - ci-run - whose TestResult carries the GitHub run id and workflow name; CI (not the agent) verifies on every push that each ci-run result's run id exists, is for the same repository, concluded success, and its head SHA equals the result's judgedAgainst; a mismatch is a violation, a result the agent wrote with a fabricated id is caught by the party the agent cannot write to. Beads' second-order lesson applies: bd gate check is a command the agent runs; keel's check runs in CI. VERIFY: a fixture result naming a real green run passes; a fabricated run id fails naming the result; a real run for a DIFFERENT sha fails; the check is in ci.yml under the keystone lock."; }
        // RAN: ci-run id=33978282844 workflow=ci (the CI run for 50175b68d8fb95f333b6d66c7806c580ab3d42b2, success) - and the same suite: 521/0 exit 0 incl. ci_runs unit tests; keel audit-ci-runs . reads this receipt
        part dcExternalFactGateDoDR1 : TestResult { :>> id = "78204709-bb91-442e-af7b-dce4ea66a705"; :>> outcome = VerdictKind::pass; :>> judgedAgainst = "50175b68d8fb95f333b6d66c7806c580ab3d42b2"; :>> judgedAt = "2026-09-05"; :>> judgedBy = "claudeOpus5"; }
        // 2026-09-07: the four perf-program items lead the ready list by the human's direction of that day -
        // 'I'd like to focus on performance in keel for a minute ... run all that are possible'. This is a
        // stated judgment about order, not a computed class, and priority-inversion may warn on it: the
        // discharge is this comment (refineAssessPriority: reorder OR say why), and the items leave the head
        // as they are done. Four of them resolve issue409 (one cause each), so their class is High and
        // the head is inversion-free; the two conditional measurements sit at the tail, sequenced after.
        action dcGuardsRunInParallelAndTimed;
        verification dcGuardsRunInParallelAndTimedDoD : Test { :>> id = "5ae981f1-f88c-4132-b737-6b46b462d17a"; :>> method = VerificationMethod::test; :>> procedureText = "DONE MEANS: `guards::run_all` runs the enforced guards across a fixed pool of OS threads (std::thread::scope, no new dependency) and returns the reports in GUARD_NAMES order exactly as the serial loop did; the activation filter still runs first. KEEL_PERF=2 attributes the cost in-process: one `phase guard:<name>` line per guard, and git spawn time is TIMED at the one constructor (gitx::git) so `git xN in Nms` stops reading 0ms - issue409 and issue410 are resolved by this item. VERIFY: a test that run_all's report names equal GUARD_NAMES filtered by activation, in order; a test that GIT_NANOS advances across one spawn; `keel guard` wall time on this tree recorded in the sprint before and after from the same binary shape, read from the shell's timer not from the perf line."; }
        // RAN: sprint598: cargo test --release -p keel-cli --lib -- gitx parallel_tests 6 passed (order test, determinism test, GIT_NANOS test); keel guard 26.6-30.2 s before, 11.2-14.1 s after, shell timer, same binary shape
        part dcGuardsRunInParallelAndTimedDoDR1 : TestResult { :>> id = "66e1a5a8-c342-492b-963b-b16773fc9cc2"; :>> outcome = VerdictKind::pass; :>> judgedAgainst = "45c0b91347c7931b933170df9fdf35e05d7a0517"; :>> judgedAt = "2026-09-07"; :>> judgedBy = "claudeOpus5"; }
        action dcGitFactsAreContentAddressed;
        verification dcGitFactsAreContentAddressedDoD : Test { :>> id = "b3e11206-c4eb-4c93-80d3-49c828f252f3"; :>> method = VerificationMethod::test; :>> procedureText = "DONE MEANS: the four per-SHA facts orient reads from git - is `<sha>` a commit, the DoD criterion of a task at `<sha>`, the paths changed in `<sha>..<head>`, and the grep fallback for a moved DoD - are served from a machine-local content-addressed cache (`.keel/cache/git-facts.toml`, gitignored, written temp-then-rename) whenever the key is a FULL 40-hex commit id, and computed through the existing batched spawns on a miss with the result written back - the spawn term of issue409. A short SHA is never cached because its resolution can change; a negative is-commit answer is never cached because a fetch can make it true. VERIFY: `keel orient` output byte-identical with the cache absent, cold and warm; KEEL_PERF's git spawn count on a warm second run on this tree, recorded in the sprint next to the cold count; a fixture test that a cache entry keyed by a full SHA is used and a short-SHA query is not written."; }
        // RAN: cargo test --release -p keel-cli --lib -- gitfacts (3 passed); keel orient . stdout byte-identical with .keel/cache/git-facts.toml absent, cold and warm (diff); KEEL_PERF=2 git x24 cold -> x11 warm on this tree, recorded in sprint599_gitFactsCached
        part dcGitFactsAreContentAddressedDoDR1 : TestResult { :>> id = "f488c5c9-f04d-4774-a0fa-f352c4481841"; :>> outcome = VerdictKind::pass; :>> judgedAgainst = "7affb600940adc6447b361c51ef8b1826ecf7c61"; :>> judgedAt = "2026-09-07T23:58:00-06:00"; :>> judgedBy = "claudeOpus5"; }
        action dcOneCorpusPerProcess;
        verification dcOneCorpusPerProcessDoD : Test { :>> id = "65603432-6a32-481d-a646-111fb44e9cf4"; :>> method = VerificationMethod::test; :>> procedureText = "DONE MEANS: one process reads the corpus once. `crate::corpus::read_to_string(path)` answers from a process-global content cache validated by the file's (len, mtime) on every call, so a file rewritten inside the process is re-read and an unchanged one is not reopened - the reopen is the cost on a Defender host, not the bytes; `collect_sysml` memoizes its walk under the mtimes of the directories it walked; `Model::build` returns `Arc<Model>` so a cache hit shares the parsed model instead of cloning it; every read site in guards.rs goes through the corpus - the corpus-reopen and clone terms of issue409. The change DETECTOR (fingerprint::compute) keeps its uncached walk. VERIFY: a test that a second read of an unchanged file does not open it (open counter) and a rewritten one does; a test that a file created after the first walk is seen by fingerprint::compute in the same epoch; `keel guard` output identical before and after on this tree, and the wall time recorded in the sprint."; }
        // RAN: cargo test --release -p keel-cli --lib: 407 passed (corpus tests a_second_read_of_an_unchanged_file_does_not_open_it_and_a_rewrite_does, a_missing_file_is_an_error_even_after_it_was_cached, a_file_created_after_the_first_walk_is_seen, an_absent_directory_is_not_remembered); cargo clippy pedantic clean; keel guard 8293/7176 ms -> 6523/4587/5562 ms, 1951 file open(s) (23410 from corpus), stdout identical modulo ms lines (66 PASS 0 FAIL); keel orient . 2106/1847 -> 1645/1554 ms byte-identical; keel validate . 682 clean
        part dcOneCorpusPerProcessDoDR1 : TestResult { :>> id = "efa67e25-eb2b-48fc-93d4-d7880b535742"; :>> outcome = VerdictKind::pass; :>> judgedAgainst = "f954788ab41fc61408c77112469143ac634bd5b8"; :>> judgedAt = "2026-09-07T23:32:00-06:00"; :>> judgedBy = "claudeOpus5"; }
        action dcGateAnswersFromItsReceipt;
        verification dcGateAnswersFromItsReceiptDoD : Test { :>> id = "e9fce810-3d73-41bf-a84e-480120d43807"; :>> method = VerificationMethod::test; :>> procedureText = "DONE MEANS: a green guard run writes `.keel/metrics/guard-receipt.toml` carrying the KEY of the tree it judged - HEAD's full SHA, a digest of `git status --porcelain -z`, the (len, mtime) of every path that status lists, the (len, mtime) of every file under `.keel/` that a guard may read, and the binary's build id - and `keel guard`, `keel hook stop` and `keel gate` answer green from that receipt when the key they compute is EQUAL, saying so in one line that names the receipt's age; any red run deletes the receipt; `--no-receipt` forces the run - the every-turn-boundary term of issue409. The key is what makes the shortcut honest: an equal key means every input a guard can read is byte-identical to a tree this binary judged green, so it is the same answer, not a skipped one. VERIFY: a fixture in which a green run writes the receipt and the next run answers from it; a touched tracked file, a new untracked file, a changed `.keel/` file and a different build id each force a run; a red run leaves no receipt; the idle `keel hook stop` wall time on this tree recorded in the sprint next to the run-everything time."; }
        // RAN: sprint601 storyGateAnswersFromItsReceiptDoD pass; cargo test --release -p keel-cli 411 pass; idle hook stop 5202/5428 -> 218/260/318 ms
        part dcGateAnswersFromItsReceiptDoDR1 : TestResult { :>> id = "630c5562-5528-4db2-9836-3536a91cb964"; :>> outcome = VerdictKind::pass; :>> judgedAgainst = "dd4d91fd8efd7d7d49e6b521aee9d4467e7b3d44"; :>> judgedAt = "2026-09-08T00:22:00-06:00"; :>> judgedBy = "claudeOpus5"; }
        action dcRoutingNumberIsStable;
        verification dcRoutingNumberIsStableDoD : Test { :>> id = "d40dad38-64cc-481a-bd12-a78887f7ab0f"; :>> method = VerificationMethod::test; :>> procedureText = "DONE MEANS: the routing number, if one is published at all, is stable enough to act on, and what it cost to obtain is stated beside it. Resolves issue392: two of four verdicts flipped between two runs of identical prompts (release WRONG then ROUTED; doc-sync ROUTED then silent), so a one-sample-per-skill sweep would have produced an authoritative-looking number that moves on a re-run and would invite rewriting descriptions that were never broken. DO: take the human's answer on which of three shapes the project is buying - a repeated sweep reporting a rate with its variance (measured at roughly seventy dollars and an hour for three samples over forty-seven skills), a stratified subset sampled repeatedly for the same money, or the rig kept for one-off diagnosis with no standing number - and implement exactly that, with the sample size and the spend recorded next to the metric. If a number is published, the probe must report per-case sample count and disagreement, never a bare percentage. VERIFY: a re-run of whatever is chosen moves the published number by less than the amount that would change an action, or the number is not published; the recorded cost matches a measured run rather than an estimate; and no skill is reported as not-routing on a single sample."; }
        // RAN: python .engine/tools/routing_probe.py (no args) -> refusing: name the case(s) ... no whole-set sweep and no standing routing number (D0378 C) exit 1; --investigate release --dry-run -> estimate from the last measured run (per run 0.65 USD, 40s, measured 2026-09-08); --investigate release --samples 3 -> #1 WRONG intake 49.4s 0.635 USD, #2 ROUTED 35.7s 0.669 USD, #3 WRONG intake 35.6s 0.635 USD; finding: DISAGREES release: 1 routed, 2 wrong - the CHECK is the defect (D0381); spend 1.95 USD over 3 runs, 49s wall, measured per run 0.6489 USD 40.2s; wrote .keel/metrics/routing-investigation.json (kind investigation, no rate field); issue415 recorded against the check, resolver dcRoutingVerdictReadsTheWholeTurn; dcSkillsRouteBehaviourally DoD re-read: no published number; keel validate 693 clean; keel guard ALL PASS
        part dcRoutingNumberIsStableDoDR1 : TestResult { :>> id = "b481199f-5060-44ca-8f16-20c44ec73098"; :>> outcome = VerdictKind::pass; :>> judgedAgainst = "fe82629"; :>> judgedAt = "2026-09-08"; :>> judgedBy = "claudeOpus5"; }
        action dcSkillReferencesAreDeployed;
        verification dcSkillReferencesAreDeployedDoD : Test { :>> id = "b4f80d72-b9bf-42c6-aa98-2861428bab60"; :>> method = VerificationMethod::test; :>> procedureText = "DONE MEANS: a path a deployed skill tells the agent to open resolves where the agent is standing. Resolves issue393: the stpa skill's opening instruction is to read references/sop.md before running a step, and the deployed .claude/skills/stpa/ holds only SKILL.md - the 121-line SOP carrying the four steps, the per-element data fields and the per-step completeness gates was never deployed, so following the deployed instruction produces a missing path and an agent either invents the procedure or skips the gates. DO: deploy a skill's reference directory alongside the skill in sync-claude, and add a check that reads every deployed SKILL.md for relative paths it instructs the agent to open and fails when one does not resolve - compute how many other skills are affected rather than hand-counting, since a hand count is stale by the next commit. The check belongs with claude-surface-drift, which already owns whether the deployed surface matches the generator and simply never asked whether the surface's own instructions are followable. VERIFY: .claude/skills/stpa/references/sop.md exists after sync-claude; the check FAILS on a skill whose SKILL.md names a reference that is not deployed, shown by constructing that case rather than by describing it; it does not fire on a skill that names no reference; and the count of affected skills is computed and reported rather than asserted."; }
        // RAN: cmp .engine/skills/stpa/references/sop.md .claude/skills/stpa/references/sop.md -> BYTE-EQUAL; sync-claude --check before the fix: 2 deployed skill(s) name a reference that does not resolve (stpa -> references/sop.md, requirement-quality -> references/ears.md, references/ruleset.md); after: keel-owned subset matches (46 skills); cargo test --release claude_surface 13 passed 0 failed (a_deployed_instruction_that_cannot_be_followed_is_drift, a_skills_references_deploy_beside_it); keel guard --no-receipt ALL PASS (WARN only)
        part dcSkillReferencesAreDeployedDoDR1 : TestResult { :>> id = "19a4d46e-18b6-4030-bb43-0404172fb1ca"; :>> outcome = VerdictKind::pass; :>> judgedAgainst = "748746a"; :>> judgedAt = "2026-09-08"; :>> judgedBy = "claudeOpus5"; }
        action dcStpaStepTwoIsComplete;
        verification dcStpaStepTwoIsCompleteDoD : Test { :>> id = "48130965-41b1-482f-be2c-666a0a1fcad3"; :>> method = VerificationMethod::inspect; :>> procedureText = "DONE MEANS: this project's STPA step 2 is complete against the handbook's element set, and where it cannot be, the gap is declared rather than absent. Resolves issue394: our SOP named four of the five element types the handbook lists (p.25), so every run produced four; the model had zero sensors, zero actuators, no representation of a control algorithm, process models for four of eight controllers, one controller role with no authored anchor, and no schema type at all for the fourth class - other inputs and outputs, neither control nor feedback - which is where an instrument measuring the wrong tree belongs (scenario S-F9). DO: author the missing process models or justify each absence in the model rather than in a commit message; compute or author the actuators, which are the mechanisms on the control path and are as derivable as the sensors turned out to be; give the `channel` role its authored Controller or remove the role; and put the fourth element type to the human as a Change Request, since the schema is frozen and a type addition is exactly what that gate exists for - carrying the cost either way, because leaving it out means the model cannot express an input nobody controls and that reports on nothing. VERIFY: the step-2 gate in the SOP passes on this project's own structure with no clause satisfied by prose; keel show control-structure reports actuators and process models per controller with any absence carrying its reason; and the fourth type is either in the schema with the human's sign-off or recorded as a declined Decision with what that costs."; }
        // RAN: sprint610: keel show control-structure . stepTwoGate 8/8 holds with evidence per clause (no clause from prose); actuators computed per controller and per action, processModel per present controller (pmCommitGate, pmRemote, pmConsole authored), channel role in absentRoles; fourth type in schema under D0363 (accepted, d0363AcceptR1) with 11 OtherInputOutput items authored; cargo test --release --lib control_structure 8 passed; keel guard exit 0
        part dcStpaStepTwoIsCompleteDoDR1 : TestResult { :>> id = "a5fe24d8-976e-4ba3-a661-276654ce8abc"; :>> outcome = VerdictKind::pass; :>> judgedAgainst = "9f109ba05435213a7f6341ff83d1a8a6e5dfb9ca"; :>> judgedAt = "2026-09-08"; :>> judgedBy = "claudeOpus5"; }
        action dcUnknownMarkerRefused;
        verification dcUnknownMarkerRefusedDoD : Test { :>> id = "2af58583-2649-48bb-baaf-fc377d119590"; :>> method = VerificationMethod::test; :>> procedureText = "DONE MEANS: record decision --from refuses an unrecognised marker value by name and writes nothing. MEASURED 2026-09-02: marker: prospective-change - a plausible spelling of the real process-change - produced an UNMARKED Decision silently (D0282 landed that way; D0283 nearly did), and the locked-file edit the Decision was meant to authorise was refused by process-change for want of the marker that had been written. The vocabulary is two words (process-change -> #ProspectiveChange, safety-change -> #SafetyChange). VERIFY: the integration test an_unknown_decision_marker_is_refused_not_dropped - exit 2, the value named in the refusal, the decisions directory unchanged."; }
        // RAN: cargo test -p keel-cli --test unknown_flag_is_refused an_unknown_decision_marker_is_refused_not_dropped 1/1: exit 2, refusal names prospective-change, .engine/decisions count unchanged; the live D0283 file was marked by hand after the silent drop was observed
        part dcUnknownMarkerRefusedDoDR1 : TestResult { :>> id = "7ad2f0d6-a7b7-4a0b-8957-f9e3f382ea0f"; :>> outcome = VerdictKind::pass; :>> judgedAgainst = "52424e3"; :>> judgedAt = "2026-09-02"; :>> judgedBy = "claudeOpus5"; }
        action dcSupersessionIsSaidOnce;
        verification dcSupersessionIsSaidOnceDoD : Test { :>> id = "fee9b129-2ee7-4f09-be02-81ab90ccdea8"; :>> method = VerificationMethod::inspect; :>> procedureText = "DONE MEANS: supersession is expressed once, and a retired Decision never appears on the human's queue. Resolves issue396: d0353 read status=proposed while a #Supersede edge from d0356 already retired it, so the pending-acceptance list asked the owner to sign a rule the project had reversed, and it did so for a day until the attribute was edited by hand. DO: decide which representation is authoritative and remove the other from the authored surface - if the EDGE is, then DecisionStatus::superseded stops being an authored value and supersession is computed wherever it is read, starting with pendingAcceptances, which is a schema and view-meaning change needing the frozen-schema gate; if the STATUS is, then something must refuse a #Supersede edge whose target still reads proposed. Do not leave both writable, which is the state that produced the defect. VERIFY: a Decision with an incoming #Supersede edge does not appear in pendingAcceptances, shown by constructing that pair rather than by reading this tree; the removed representation cannot be authored at all rather than being merely discouraged; and the choice is recorded as a Decision with what it costs, since one of the two is load-bearing in existing records."; }
        // RAN: cargo test --release --test supersession_is_said_once 3/3 on a fresh scaffold (constructed pair: d0001 proposed + retired by d0003 absent from show authority-queue and orient pendingAcceptances while d0003/d0004 present; report governance 1 accepted / 1 retired of 4 total with d0002 under a SupersedeClause edge; check-engine FAILS naming unknown member superseded / DecisionStatus; --supersedes + --supersedes-clause on one target refused, nothing written); mod.rs standing_is_the_status_minus_the_edge + pending test with d0004 retired by edge; transform dry run {7,3,0} -> {0,7,7} hash 4b800cde279bf98a EQUAL, --apply 18 files, re-run idempotent; conformance_lane --construct ACCEPTED; keel validate 708 clean; check-engine clean; keel guard ALL PASS; clippy --all-targets clean; keel suite 625 passed 0 failed (receipt ae8e4d788476, after a first run whose one failure was run_all_is_deterministic reading the live tree while this session edited two skills mid-run); CLAUDE.md 1.4/4, guards.md, syntax-notes state the rule
        part dcSupersessionIsSaidOnceDoDR1 : TestResult { :>> id = "41e1b6e8-c3ab-4f13-b33d-6c2d3f854df2"; :>> outcome = VerdictKind::pass; :>> judgedAgainst = "9369863"; :>> judgedAt = "2026-09-09"; :>> judgedBy = "claudeOpus5"; }
        action dcEmptyIsNothingDone;
        verification dcEmptyIsNothingDoneDoD : Test { :>> id = "a89c6783-deb6-4621-985b-c683c075d4c9"; :>> method = VerificationMethod::test; :>> procedureText = "DONE MEANS: no ratio or readiness verdict keel computes reads 100 percent or READY over an empty population. MEASURED before: a fresh scaffold's report assurance showed three 100 percent cards and READY; tier-satisfaction pct 100 per empty tier; assured ready true. DO: every pct helper returns 0 on an empty denominator; a missing tier is 0; readiness requires governed > 0 and the verdict is three-valued (NOTHING TO ASSURE / READY / NOT READY); an empty tone on ratio cards; the pinned 'vacuously complete' test inverted with its reason; a source-scan test that fails the build on any division falling back to 100. VERIFY: the scaffold sweep across every lens and report finds no 100, READY or PASS-over-nothing; this repository's own verdicts are unchanged (NOT READY, 379 governed); the scan test catches a planted map_or(100."; }
        // RAN: fresh scaffold before: report assurance 3x 100% + READY, tier-satisfaction pct 100, assured ready true; after: 0% x3 tone empty, NOTHING TO ASSURE, pct 0, ready false verdict NOTHING TO ASSURE governed 0; this repo unchanged: NOT READY, governed 379; sweep of 16 lenses/reports on the scaffold finds no 100/READY/PASS; cargo test --lib empty_population_tests 3/3 + view::tests::pct_handles_empty_denominator inverted; ARMED: planted checked_div(0).map_or(100 in pm.rs -> scan test FAILED naming src/pm.rs:126; reverted -> ok; full suite 445/0; clippy clean
        part dcEmptyIsNothingDoneDoDR1 : TestResult { :>> id = "2f7f9ac7-f373-4b02-94d8-8f379dca5897"; :>> outcome = VerdictKind::pass; :>> judgedAgainst = "4674965"; :>> judgedAt = "2026-09-03"; :>> judgedBy = "claudeOpus5"; }
        action dcVerdictsAreColoured;
        verification dcVerdictsAreColouredDoD : Test { :>> id = "d015b4ca-cd37-4716-8bf7-18d4d7f1925f"; :>> method = VerificationMethod::test; :>> procedureText = "DONE MEANS: on a terminal, keel's verdict words are coloured - PASS/ALL PASS/validated clean green, FAIL/FAILED/ERROR red, WARN yellow, a control-defect note magenta - and when piped the bytes are identical to before, so hooks, CI, tests and land parse what they always parsed. NO_COLOR disables; KEEL_COLOR=1|0 forces. The words are wrapped, never replaced. VERIFY: guard and validate piped through cat -v show bare words by default and ANSI codes under KEEL_COLOR=1; NO_COLOR wins; the two colour unit tests; the full suite unchanged; the two env vars documented in CLAUDE.md section 5 and guards.md."; }
        // RAN: keel guard cli-surface-declared . | cat -v -> bare PASS; KEEL_COLOR=1 -> ^[[1;32mPASS^[[0m; KEEL_COLOR=1 keel validate -> green 'validated clean'; NO_COLOR=1 -> bare; cargo test color::tests 2/2; full suite 447/0 with colour off under capture; clippy clean
        part dcVerdictsAreColouredDoDR1 : TestResult { :>> id = "ad708dc2-e981-4207-bd7e-18cc6a5c1320"; :>> outcome = VerdictKind::pass; :>> judgedAgainst = "a88ae5b"; :>> judgedAt = "2026-09-03"; :>> judgedBy = "claudeOpus5"; }
        action dcExecSummaryRemoved;
        verification dcExecSummaryRemovedDoD : Test { :>> id = "6cce95f1-8cee-457d-a6e7-0fd3e8e27f0c"; :>> method = VerificationMethod::test; :>> procedureText = "DONE MEANS: the engine carries no exec-summary process, skill, template, test directory, installed-unit record or unit id, and nothing on the living doc surface claims it does; decision-surfacing renders its own page; library-stewardship and stpa-diagram name other things; history that mentions the unit stays as history. VERIFY: a grep over processes, skills, contracts, docs, source and workflows (excluding decisions, done sprints, intake, issues, knowledge and reviews) finds no reference; process-skill, process-applicability, activation-manifest, tool-reference, cli-surface-declared and control-map-reconciled pass; the .claude mirror has 45 skills; the suite is green on the rebuilt binary; the library's copy at v3 is stated as untouched."; }
        // RAN: grep exec-summary|execSummary|se-templates over live surfaces -> only incident-history comments and done-work records; keel sync-claude 45/45 skills, .claude/skills/exec-summary absent; keel guard . ALL PASS (58); cargo test 447/0 on the rebuilt binary; clippy clean; library untouched (installed-units.toml no longer lists a2428932; unit-ids.toml no exec-summary)
        part dcExecSummaryRemovedDoDR1 : TestResult { :>> id = "6abaebba-7d02-415b-8862-5844611a60db"; :>> outcome = VerdictKind::pass; :>> judgedAgainst = "c3dd223"; :>> judgedAt = "2026-09-03"; :>> judgedBy = "claudeOpus5"; }
        action dcAcceptHonoursDelegation;
        verification dcAcceptHonoursDelegationDoD : Test { :>> id = "fbcd045c-9937-47c1-89f7-36c69f3743bb"; :>> method = VerificationMethod::test; :>> procedureText = "DONE MEANS: keel accept in an agent session honours the declared recording delegation for decisionAcceptance - a note quoting the human (the substance rule's own predicate) records the acceptance and cites the delegation; an unquoted note is refused with QUOTE named; a withdrawn delegation refuses as before. The doc surface no longer implies a terminal is required. VERIFY: the three integration tests in accept_honours_delegation.rs; clippy; the full suite; CLAUDE.md section 4 states the rule and the human's words."; }
        // RAN: cargo test --test accept_honours_delegation 3/3: quoted note -> recorded, file shows accepted + the quote, message cites d0192; unquoted -> exit 1 with QUOTE; delegation line deleted in the fixture -> exit 1 'no recording delegation'
        part dcAcceptHonoursDelegationDoDR1 : TestResult { :>> id = "5e2cd9ec-1bba-434f-b228-3915365b37e9"; :>> outcome = VerdictKind::pass; :>> judgedAgainst = "27f6944"; :>> judgedAt = "2026-09-03"; :>> judgedBy = "claudeOpus5"; }
        action dcSupersessionIsRecorded;
        verification dcSupersessionIsRecordedDoD : Test { :>> id = "5a312e6c-3af4-4b6d-ab57-441f069e7200"; :>> method = VerificationMethod::test; :>> procedureText = "DONE MEANS: D0289 carries the human's word as its quote receipt and the edges that say what it changed - #Supersede to d0178 (layer 3, scoped in the receipt), dependency on d0192, #DerivedFrom us076 - and the policy contract's four TO WITHDRAW comments state that withdrawal is a superseding Decision plus the line deleted in the same commit. VERIFY: keel show why d0289 reports d0289 ->supersede d0178 and ->dependency d0192; the receipt quotes st075 verbatim; guards pass with the contract edit under D0290's marker."; }
        // RAN: keel show why d0289 -> 'd0289 ->supersede d0178' and 'd0289 ->dependency d0192'; d0289AcceptAttest1 quotes st075 verbatim; attestation-policy.toml four TO WITHDRAW comments name the superseded Decision; keel guard . ALL PASS; keel show trace is empty for every Decision - GitHub #34, open, not this change
        part dcSupersessionIsRecordedDoDR1 : TestResult { :>> id = "65185f60-bb1d-4a31-8ddd-9e05c6a7bcbb"; :>> outcome = VerdictKind::pass; :>> judgedAgainst = "f72aef4"; :>> judgedAt = "2026-09-03"; :>> judgedBy = "claudeOpus5"; }
        action dcChannelDisconnected;
        verification dcChannelDisconnectedDoD : Test { :>> id = "e6438880-9863-48e0-a8f4-171b7097fcc0"; :>> method = VerificationMethod::test; :>> procedureText = "DONE MEANS: no GitHub issue is raised for a Decision and nothing notifies the human; standing consent (D0207) is applied by keel record decision at record time for a non-fork when exactly one decider is declared, the note quoting the standing words; forks and zero-or-many-decider projects stay proposed and say why; the decision-channel workflows, scripts, process, skill and unit record are gone; github-intake stays; every live claim that named the channel states what is. VERIFY: three integration tests (non-fork accepts, fork stays, no decider stays); D0291 itself accepted at record time on this repo and carrying the human's quoted instruction as receipt; ci.yml and release.yml are the only workflows; 44 skills mirrored; full suite green on the rebuilt binary; the control-structure view reads the channel role inert."; }
        // RAN: cargo test --test standing_consent_at_record_time 3/3; keel record decision (D0291) -> 'accepted D0291 at record time under standing consent d0207 (judge wweatherholtz)'; ls .github/workflows -> ci.yml release.yml; keel sync-claude 44/44; full suite 448/0; clippy clean; control_structure test pins channel inert + no ctChannel anchor
        part dcChannelDisconnectedDoDR1 : TestResult { :>> id = "05029fc8-0ae3-4433-81d5-45594a7c683f"; :>> outcome = VerdictKind::pass; :>> judgedAgainst = "10f2571"; :>> judgedAt = "2026-09-03"; :>> judgedBy = "claudeOpus5"; }
        action dcQuotedWordsAreBounded;
        verification dcQuotedWordsAreBoundedDoD : Test { :>> id = "048399fd-0557-499f-affc-5b2651d8c240"; :>> method = VerificationMethod::test; :>> procedureText = "DONE MEANS: the human words a read-back check reads are bounded by something prose cannot fake. Resolves issue397: the check extracts the quoted span by splitting on the apostrophe character, so an ordinary possessive in the surrounding sentence shifts the span boundaries - my acceptance note for eight decisions was refused because the apostrophe in a possessive captured the wrong text, and the identical note without it passed. It failed CLOSED here, which is why nothing was harmed; the mechanism is symmetric, and a spliced span that happens to carry the decision id would PASS on words the human never said, defeating the one control that stops a gesture being attached to a record the agent chose. DO: bound the span unambiguously - a typographic quote pair, a doubled delimiter, or a dedicated flag carrying the human words as their own argument - so the boundaries are declared rather than inferred, and keep the refusal message naming what it looked for. VERIFY: the check FAILS on a note whose apostrophe-spliced span carries the id while the human words do not, which is the passing-direction case that matters and must be constructed rather than argued; a note containing ordinary possessives around a correct quote passes; and both cases are tests, since this is an attestation path and D0360 applies."; }
        // RAN: keel suite . 589 passed 0 failed (receipt 37f6d8356120, suite606.txt); checks::tests::quoted_spans_are_bounded_and_an_in_word_apostrophe_never_opens_one (live issue397 note yields the human's marked line; spliced note yields only the human's words; contraction and unclosed opener yield nothing), view::tests::read_back_names_the_decision_or_refuses (live note binds d0360, spliced refused, c for d375 binds d0375 by digits and letter), delegated_records_must_quote_or_cite_a_gesture; LIVE: keel accept d0375 --words c for d375 --by wweatherholtz recorded d0375AcceptR1 against 7a61044
        part dcQuotedWordsAreBoundedDoDR1 : TestResult { :>> id = "e32ff0c5-dd6c-4fad-b2c2-446a0e8b7b96"; :>> outcome = VerdictKind::pass; :>> judgedAgainst = "7a61044816c7c01fbbe10976596d68bcbdc8c88c"; :>> judgedAt = "2026-09-08"; :>> judgedBy = "claudeOpus5"; }
        action dcDeactivatedSkillSaysSo;
        verification dcDeactivatedSkillSaysSoDoD : Test { :>> id = "59bf4163-3605-4b58-941e-a639a74899fc"; :>> method = VerificationMethod::test; :>> procedureText = "DONE MEANS: sync-claude deploys the skill of a DEACTIVATED process with its inactive state written first in the skill's description, so an agent reading its skill list learns the channel is closed before acting. GH#49 (st080): deactivate turned off the guard but the skill stayed deployed unchanged. OPTION B, the reporter's own lean, chosen over removal because a removed file reads as drift (GH#46) and a stated state teaches the model. VERIFY: deactivate a process in a fixture, sync-claude, the skill file begins with the inactive statement; reactivate, it does not; claude-surface-drift stays green in both states."; }
        // RAN: keel suite . 562 passed 0 failed (receipt af357bb03f1a, suite585.txt); surface_states_its_state::a_deactivated_processes_skill_is_deployed_saying_it_is_inactive_and_reactivating_clears_it (deactivate render, sync, banner first, check clean, reactivate clears); federation F9 green with activate/deactivate regenerating the surface
        part dcDeactivatedSkillSaysSoDoDR1 : TestResult { :>> id = "64004c0e-131a-464f-beb2-2ae03843ecc4"; :>> outcome = VerdictKind::pass; :>> judgedAgainst = "a66324cffb59b843c32591c1a2e5f19ee1639036"; :>> judgedAt = "2026-09-06"; :>> judgedBy = "claudeOpus5"; }
        action dcRedYieldKeepsTheDiagnostic;
        verification dcRedYieldKeepsTheDiagnosticDoD : Test { :>> id = "b5dd6284-2bd4-4928-8720-b6b8c29ae477"; :>> method = VerificationMethod::test; :>> procedureText = "DONE MEANS: the red-yield obligation the Stop hook records preserves the captured gate output whole, or cuts at a line boundary and says how many lines were cut. GH#50 (st079): three obligations each exactly 726 characters, cut mid-token, losing the first problem at yield the field exists to preserve. VERIFY: a long gate output round-trips into the obligation intact or ends on a line boundary with a '(N more lines)' marker."; }
        // RAN: keel suite . 562/0 (receipt af357bb03f1a); write::tests::clipping_keeps_whole_output_or_cuts_on_a_line_boundary_and_counts_the_cut (whole when it fits; ten lines cut to whole lines with (7 more lines); a 900-char first line kept whole with (1 more line)); the red-yield obligation uses clip_at_line_boundary with budget 2000 in place of chars().take(500)
        part dcRedYieldKeepsTheDiagnosticDoDR1 : TestResult { :>> id = "2a0fe915-9b2f-44ab-b709-f5d0248f6621"; :>> outcome = VerdictKind::pass; :>> judgedAgainst = "a66324cffb59b843c32591c1a2e5f19ee1639036"; :>> judgedAt = "2026-09-06"; :>> judgedBy = "claudeOpus5"; }
        action dcSurfaceStampNamesTheBuild;
        verification dcSurfaceStampNamesTheBuildDoD : Test { :>> id = "4246b544-4d19-4d85-9cdb-76ae28ebb288"; :>> method = VerificationMethod::test; :>> procedureText = "DONE MEANS: the .claude surface stamp carries the build commit as well as the version, and the drift message names the stamped build and the running build when they differ. GH#51 (st078): two 0.3.1 builds (cf985ec+dirty, 6eafa86+dirty) generated different surfaces and the report named no binary. VERIFY: sync-claude stamps version+commit; the drift guard's message on a mismatch names both; a fixture with a forged stamp shows the diagnosis."; }
        // RAN: keel suite . 562/0 (receipt af357bb03f1a); surface_states_its_state::the_stamp_carries_the_build_and_a_drift_report_names_both_builds (two-token stamp = keel version's build; forged stamp plus mutated skill names stamped by build deadbee and this binary's build; regenerate restores); this tree's sidecar reads 0.3.1 a66324c+dirty
        part dcSurfaceStampNamesTheBuildDoDR1 : TestResult { :>> id = "8b078b7d-f38a-47b1-b587-8a10a7e519a6"; :>> outcome = VerdictKind::pass; :>> judgedAgainst = "a66324cffb59b843c32591c1a2e5f19ee1639036"; :>> judgedAt = "2026-09-06"; :>> judgedBy = "claudeOpus5"; }
        action dcStopAdvisoryIsOneLine;
        verification dcStopAdvisoryIsOneLineDoD : Test { :>> id = "ae477060-2997-4256-b06d-5bbc4d919a47"; :>> method = VerificationMethod::demo; :>> procedureText = "DONE MEANS: the Stop hook's exit-0 advisory is one line - N decisions outstanding, their short names, and how to accept (your quoted word, or keel accept) - with the console/bridge nag gone. GH#52 (st077) quotes the owner's wanted format. Partly moot after D0289 (accept by quoted word) and D0291 (record-time consent leaves few outstanding), which is why it is Low. VERIFY: the advisory on a project with N pending forks is one line naming them; on none, silence."; }
        // RAN: keel suite . 562/0 (receipt af357bb03f1a); stop_advisory_is_one_line 2/2 (two proposed Decisions produce exactly one JSON line starting 2 decisions outstanding (d0001..d0002), naming how to accept, ending Covering: probeOne, probeTwo, no console/deck words; none is silence); live keel hook stop on this tree printed 7 decisions outstanding (d0337..d0346) ... (+1)
        part dcStopAdvisoryIsOneLineDoDR1 : TestResult { :>> id = "4812f874-d214-4ab5-922e-e7649d3719fc"; :>> outcome = VerdictKind::pass; :>> judgedAgainst = "a66324cffb59b843c32591c1a2e5f19ee1639036"; :>> judgedAt = "2026-09-06"; :>> judgedBy = "claudeOpus5"; }
        action dcLandRequiresASuiteReceipt;
        verification dcLandRequiresASuiteReceiptDoD : Test { :>> id = "c93d0de2-3874-472a-a5d1-dce58dda2d49"; :>> method = VerificationMethod::test; :>> procedureText = "DONE MEANS: keel land refuses to push a tree whose deliverable changed since the last recorded green suite run on that tree, unless the suite ran at HEAD. On 2026-09-02 sprint 521 was landed on validate plus guards alone; the full suite had last run at sprint 520; CI went red for twenty minutes on a test the suite would have caught locally (a shipped process naming a tool the scaffold did not ship). CI is detective (the control structure says so, computed) - the commit was already on main. DO: the suite run writes a machine-local receipt (tree fingerprint, timestamp, pass/fail) beside the hook fire-ledger; land compares the receipt's fingerprint to HEAD's and refuses when the deliverable manifest files differ from the receipted tree, printing what to run; KEEL_LAND_UNTESTED=1 overrides with an obligation recorded, never silently. VERIFY: a fixture whose source changed after the last receipt is refused by name; a fresh receipt at HEAD lets it through; a docs-only change needs no receipt."; }
        // RAN: keel suite . 562/0 wrote .keel/metrics/suite-receipt.toml (fingerprint af357bb03f1a) and this commit landed through keel land's new receipt gate; land_requires_a_suite_receipt 2/2 (no receipt refused naming keel suite; green receipt lands; docs-only lands; source change refused CHANGED; red receipt refused RED; KEEL_LAND_UNTESTED=1 lands with exactly one land-untested obligation); suite unit tests 2/2; cli-surface-declared PASS 106; audit-adherence PASS
        part dcLandRequiresASuiteReceiptDoDR1 : TestResult { :>> id = "3c6f101d-efbf-44af-9535-f03f9cf8ae45"; :>> outcome = VerdictKind::pass; :>> judgedAgainst = "a66324cffb59b843c32591c1a2e5f19ee1639036"; :>> judgedAt = "2026-09-06"; :>> judgedBy = "claudeOpus5"; }
        action dcScaffoldShipsNoGrants;
        verification dcScaffoldShipsNoGrantsDoD : Test { :>> id = "b18a52c4-257e-49e9-a845-a083733e0905"; :>> method = VerificationMethod::test; :>> procedureText = "DONE MEANS: a fresh keel init ships attestation-policy.toml WITHOUT this repository's standingConsent line and WITHOUT its delegatedRecording lines - those are THIS project's grants (the human's words of 2026-08-22 and 2026-08-23 are quoted in them) and a downstream project never made them. Found 2026-09-03 (sprint 527 retro): a scaffold declares standing consent it never granted; inert today only because it also declares no decider, which is an accident of two absences cancelling. The D0219 class: project data shipped as engine data. DO: the shipped policy carries the classes with kinds and roles and a commented example of each delegation; init or migrate never copies a grant; this repository's own file keeps its grants. VERIFY: a fresh scaffold's policy has no delegatedRecording and no standingConsent; record decision on the scaffold stays proposed and says so; this repository's behaviour is unchanged."; }
        // RAN: delivered by D0340 (sprint 575): standing_words_are_project_local::a_fresh_scaffold_carries_the_policy_and_no_live_grant - a fresh keel init policy has no live delegatedRecording or standingConsent (every grant line commented under GRANTS ARE NOT INHERITED), record decision on the scaffold stays proposed and prints accept later via an explicit human sign-off; this repository's own auto-accept unchanged (D0341/D0342/D0347 accepted at record time 2026-09-06); suite581 550/0
        part dcScaffoldShipsNoGrantsDoDR1 : TestResult { :>> id = "7187c888-e07c-429d-90dc-05c93fe74600"; :>> outcome = VerdictKind::pass; :>> judgedAgainst = "515cf802732f91cdab73150b530052ecf83561eb"; :>> judgedAt = "2026-09-06"; :>> judgedBy = "claudeOpus5"; }
        action dcRecordDecisionDeclaresSupersedes;
        verification dcRecordDecisionDeclaresSupersedesDoD : Test { :>> id = "cdedf98b-4e56-489e-9478-14f5974190da"; :>> method = VerificationMethod::test; :>> procedureText = "DONE MEANS: keel record decision accepts --supersedes <dNNNN>[,<dNNNN>] (and the --from file a supersedes: line) and writes the #Supersede edge with the Decision, so a Decision that reverses another cannot land edgeless. Found 2026-09-03: D0289 reversed D0178 layer 3 and carried no edge to it; the human noticed, not a guard, because decision-requirement-link warns only when prose names an item by id and D0289's text did not. Also: --derived-from <stNNN|usNNN> for the statement or story it came from. VERIFY: a decision recorded with --supersedes carries the edge and keel show why reads it back; a --supersedes naming a missing Decision refuses; the record-time acceptance path is unaffected."; }
        // RAN: keel suite . 562/0 (receipt af357bb03f1a); record_decision_declares_supersedes 3/3 (edge in the Decision's own file, validates, keel show why reads it back; missing target refuses naming --supersedes and writes nothing; --from draft header lines author both edges, --derived-from to a Decision refused); no_public_write_reads_outside_the_lock green
        part dcRecordDecisionDeclaresSupersedesDoDR1 : TestResult { :>> id = "a8e47834-0bb6-46f0-a962-e3671db18c44"; :>> outcome = VerdictKind::pass; :>> judgedAgainst = "a66324cffb59b843c32591c1a2e5f19ee1639036"; :>> judgedAt = "2026-09-06"; :>> judgedBy = "claudeOpus5"; }
        verification dcForkShapeIsDetectedDoD : Test { :>> id = "27f5985f-1a9b-4193-b060-a12b808f4e6a"; :>> method = VerificationMethod::test; :>> procedureText = "DONE when record decision refuses to auto-accept a Decision whose text weighs alternatives without the OPTION marker: a lexical fork detector beyond deck::fork_options - two or more of 'alternative', 'either', 'or we could', 'option', 'versus', 'trade-off', 'A:', 'B:' style enumerations, or a decision field that names more than one course and recommends one - makes the Decision stay proposed with a message asking the author to write it as a fork (OPTION X (label) ... COST ...) or to state in the text that it is not one. Measured first over the accepted corpus: how many auto-accepted Decisions the detector would have held, read by hand for precision before the threshold is set (the D0102 way). Arming test: a disguised fork stays proposed; a genuine non-fork with the word alternative in passing auto-accepts. Records: ucaRecordForkDisguised, ccRecordForkShape (stpa-self run 1)."; }
        // RAN: cargo test --release: 521 passed, 0 failed, exit 0 (2026-09-05) incl. deck::fork_shape_tests and tests/disguised_fork_stays_proposed.rs; corpus measured 109 auto / 4 held / 1 real (D0292)
        part dcForkShapeIsDetectedDoDR1 : TestResult { :>> id = "5cdb7415-f8ec-4502-bb86-be226dbb4a73"; :>> outcome = VerdictKind::pass; :>> judgedAgainst = "50175b68d8fb95f333b6d66c7806c580ab3d42b2"; :>> judgedAt = "2026-09-05"; :>> judgedBy = "claudeOpus5"; }
        action dcPatchesFailWhenTheyMiss;
        verification dcPatchesFailWhenTheyMissDoD : Test { :>> id = "1a80847a-12d3-484c-9ec3-a1d184f9b734"; :>> method = VerificationMethod::test; :>> procedureText = "DONE MEANS: a patch that cannot find its anchor fails, and never lands somewhere it does no work. Resolves issue398: a patch adding a computation section to the facts script fell through to an append when its anchor did not match, putting the section AFTER the serialisation - so the script ran clean, exited zero, wrote its file and silently omitted everything the section computed, visible only on reading back the keys it should have added. DO: make the assertion the only available shape rather than a convention - a patch asserts its anchor's presence and its count, exits non-zero when either is wrong, and where an end-of-file addition is genuinely intended it is stated explicitly rather than reached by failure. Decide whether this belongs as a shared helper these scripts import or as a documented rule with an example, and record which and why, because a rule nobody imports is a rule that decays. VERIFY: a patch whose anchor is absent exits non-zero and writes nothing, shown by constructing that case; a patch whose anchor appears twice refuses rather than picking one; and a deliberate append is distinguishable in the script's own text from an accidental one."; }
        // RAN: scripts/textpatch.py --probe: 11 pass 0 failures (absent anchor refused + file byte-identical + nothing appended; duplicate anchor refused; append is its own named operation); CLAUDE.md section 6 names the helper; D0386 records helper-named-by-rule and why; see sprint612
        part dcPatchesFailWhenTheyMissDoDR1 : TestResult { :>> id = "f0446cb1-2c16-4b01-a68e-d990fa135494"; :>> outcome = VerdictKind::pass; :>> judgedAgainst = "4b85cde944f3034fdc75478c78a1ff8f7dfe4ff4"; :>> judgedAt = "2026-09-08"; :>> judgedBy = "claudeOpus5"; }
        action dcInstrumentsLeaveNoStaleArtifact;
        verification dcInstrumentsLeaveNoStaleArtifactDoD : Test { :>> id = "b7aa0308-c257-4777-b3a6-7f3e3eb6e61a"; :>> method = VerificationMethod::test; :>> procedureText = "DONE MEANS: a failed instrument leaves no artefact that reads as a current answer. Resolves issue399: the computed-facts script raised partway through a run and left the previous run's JSON in place - valid, timestamped, indistinguishable from current, and the source the standing brief is built from. DO: sweep every instrument that writes an artefact - the facts file, the suite receipt, the routing JSON, the census output, the rendered pages - and give each the same property: a run that cannot complete removes or unmistakably marks its previous output, so a missing answer is what failure produces. A non-zero exit is not sufficient, because the exit code lives in the shell and the artefact outlives it. Weigh writing the run's own outcome INTO the artefact against deleting it, and record the choice - a file that says it failed is more useful than no file, provided every reader checks the field. VERIFY: killing each instrument mid-run leaves no artefact a reader would take as current, shown per instrument rather than argued once; and the standing brief refuses to build from an artefact whose run did not complete."; }
        // RAN: per-instrument kill/break demonstrations 2026-09-08 (facts.py, six builders via the supersession builder, stpa_diagram.py, routing_probe.py, keel suite) each left no artefact a reader takes as current; require_complete refuses a running/failed/pre-D0387 facts file so the brief cannot build from one; artefact.py --probe 11 pass; guard receipt has the property by construction; choice recorded as D0387; see sprint613
        part dcInstrumentsLeaveNoStaleArtifactDoDR1 : TestResult { :>> id = "b23274e0-e14d-4ad4-852b-7f350f85fdab"; :>> outcome = VerdictKind::pass; :>> judgedAgainst = "e0acb5604cd137fbcf8745a145cbee527dda1b84"; :>> judgedAt = "2026-09-08"; :>> judgedBy = "claudeOpus5"; }
        action dcAdHocChecksAreProbedFirst;
        verification dcAdHocChecksAreProbedFirstDoD : Test { :>> id = "6eda7c8c-02d3-4f13-bc74-763c6476f2c8"; :>> method = VerificationMethod::test; :>> procedureText = "DONE MEANS: no number from a hand-written check is stated before the check has been probed against a known answer. Resolves issue400: two ad-hoc checks in one session returned wrong answers on their first run - a census that scored 64 of 64 by matching its own registry, caught only because the answer was too good, and a controller check that reported the human's process model missing by comparing a role name to an anchor name case-sensitively, which was stated in a response before being recomputed. DO: make the probe a step rather than a virtue - for any check written to answer a question, run it first against one case known to be positive and one known to be negative, and only then read the real tree. Decide whether the probe cases are recorded with the check (which makes it an instrument under D0361, inheriting the propriety lenses) or discarded with it, and record which. VERIFY: the two checks from this issue are re-run against their known cases and the artefacts of the original defects are reproduced - a census that matches its own registry, a comparison that fails on case - so the probe is shown to catch what it is for rather than asserted to; and the practice is written where a future session reads it, not only in this criterion."; }
        // RAN: scripts/probes/issue400_reproduction.py re-runs both defective checks against known-positive/known-negative cases: the 64-of-64 census artefact reproduces (67 of 67, doc-guard-count read covered), the case-comparison artefact reproduces (human anchorless), both corrections pass; CLAUDE.md section 4 states the step; D0388 records kept checks carry --probe, discarded ones name their cases in the receipt; see sprint614
        part dcAdHocChecksAreProbedFirstDoDR1 : TestResult { :>> id = "6abc8364-de1f-4575-bf54-657ddac75931"; :>> outcome = VerdictKind::pass; :>> judgedAgainst = "82d826c43bb5b1d4e20e9f5e8ef8735638a7a693"; :>> judgedAt = "2026-09-08"; :>> judgedBy = "claudeOpus5"; }
        action dcHookDegradationIsCounted;
        verification dcHookDegradationIsCountedDoD : Test { :>> id = "cbfffa09-a2ac-4ec7-bca5-73388d3bb785"; :>> method = VerificationMethod::test; :>> procedureText = "DONE MEANS: a hook that degrades says so where someone can count it, and a documented cost matches the distribution rather than the best case. Resolves issue402: the recall payload is dropped when its walk exceeds the 2,500ms cap - 18 times in 808 fires, with a maximum of 33.5 seconds - so the agent's memory channel is least available exactly when the machine is busiest, and nothing records which turns went without facts. In the same ledger the per-edit tier documented at about 0.35 seconds has a median of 0ms and a maximum of 54.4 seconds. DO: count the skips as a fact rather than a transcript line, so the rate is readable after the fact; state the documented cost of a gating tier as a distribution; and decide, from the ledger rather than by feel, whether the cap should rise, the walk should get faster, or the skip should be surfaced to the turn that lost its facts. VERIFY: the skip rate and the tail are computed from .keel/metrics/hooks.jsonl rather than estimated; a turn whose recall was skipped can be identified afterwards; and CLAUDE.md's stated per-edit cost is one a reader would recognise from the measured distribution."; }
        // RAN: keel enforcement-report computes per-event median/p90/p99/max and recall.skipped / skipRatePct / skippedTurns from hooks.jsonl (user-prompt 760/1385/12225/33503 ms over 941 fires; post-edit 0/0/2323/54439 over 1694) matching an independent scratch analysis; recall-skipped ledger lines carry ts+session so a turn that lost its facts is identifiable; CLAUDE.md states the cost as a distribution; the cap decision is D0390 from the ledger (drop saves nothing: check runs after the walk); see sprint615
        part dcHookDegradationIsCountedDoDR1 : TestResult { :>> id = "2d2a2e2b-eecd-4a10-9c5b-a9941da31013"; :>> outcome = VerdictKind::pass; :>> judgedAgainst = "d071820522e8332e406c87feb67e28721d7a395a"; :>> judgedAt = "2026-09-08"; :>> judgedBy = "claudeOpus5"; }
        action dcSelfBuildHooksLeaveTheBuildTree;
        verification dcSelfBuildHooksLeaveTheBuildTreeDoD : Test { :>> id = "bf90b65f-887e-4692-8390-851f37e0cfe3"; :>> method = VerificationMethod::test; :>> procedureText = "DONE MEANS: a self-build project's hooks do not run the file its build is writing. Resolves issue408. The pin probe's order is KEEL_BIN, then .keel/bin/keel(.exe), then the pin cache, then PATH. In a project whose DELIVERABLE is the engine, nothing writes .keel/bin/keel.exe - init seeds .keel/bin/<version>/<asset> and keelw fetches into the same shape - so the probe falls through to PATH and resolves into target/release, which is the exact file cargo must unlink to relink. DO: on a self-build tree (the one check_preconditions already makes - a tree holding keel-cli/Cargo.toml), the surfaces that write hook commands ALSO place or refresh a stable copy at .keel/bin/keel(.exe), and say which binary the hooks will run; and the copy is refreshed by the build path that produces a new binary rather than by a human remembering. The staleness this trades for is real and must be visible, not silent: keel status names the hook binary's build commit beside the engine pin, so a hook set running an older image than the tree is a fact a reader can see rather than an inference from behaviour. VERIFY: on this repository, a cargo build followed by a suite run completes with no `failed to remove file target/release/keel.exe`; the fire-ledger's bin field names the stable copy, not target/release; keel status shows the hook binary's build and flags it when it differs from the tree's HEAD; a non-self-build project is unaffected."; }
        // RAN: cargo build + keel suite today: 601 passed, no failed-to-remove error, hooks running .keel/bin/keel.exe (ledger bin field); hooks refresh the copy themselves from target/release on the first fire after a build (tests: placed, refreshed, young output left, plain project untouched, sync-claude places and names); keel status names the hook binary and its commits behind HEAD; D0391; see sprint616
        part dcSelfBuildHooksLeaveTheBuildTreeDoDR1 : TestResult { :>> id = "ba8a12ab-5c07-40b1-97fb-8a77a01a7027"; :>> outcome = VerdictKind::pass; :>> judgedAgainst = "cafde85c5a8d0e08120d41ad7e5412eacc969ad7"; :>> judgedAt = "2026-09-08"; :>> judgedBy = "claudeOpus5"; }
        action dcBriefBudgetsAreHeld;
        verification dcBriefBudgetsAreHeldDoD : Test { :>> id = "67057c52-0c65-427f-bf65-0de374600267"; :>> method = VerificationMethod::test; :>> procedureText = "check_brief in scripts/check_templates.py holds every word budget the brief contract's section table declares (asi-templates skill section 2.1): the headline (data-digest='title') at most 18 words, the ask block (class='ask') at most 70, the provenance strip (data-digest='provenance') at most 60, and - once accepted by Decision - the whole of the reader's prose under its ceiling. A page over any budget fails `python scripts/check_templates.py --brief` naming the section, its count and its limit. The 2026-09-08 empty-queue page as published (26-word title, 133-word ask, 71-word provenance) fails the check naming all three, and the page rewritten to replace it passes; `python scripts/check_templates.py --self-test` holds the same clauses over synthetic fixtures in both directions - an in-budget page passes, an over-budget headline and an over-budget ask are refused naming their counts, the ceiling refuses only when given - and exits non-zero when any direction fails. Resolves issue413."; }
        // RAN: python scripts/check_templates.py --self-test: 5 of 5 pass, exit 0; --brief on the published 2026-09-08 empty-queue page: 3 violations naming headline 26/18, the ask 133/70, provenance strip 71/60, exit 1; --brief on the terse replacement: clean, and clean with ceiling=450 forced at 447 reader words; sprint607
        part dcBriefBudgetsAreHeldDoDR1 : TestResult { :>> id = "8917b5ff-60b3-4c32-8269-9df46d57e561"; :>> outcome = VerdictKind::pass; :>> judgedAgainst = "d6d5556fbf24b6cd30a6669d40b1cd7eecbf6c70"; :>> judgedAt = "2026-09-08"; :>> judgedBy = "claudeOpus5"; }
        action dcSuiteReceiptDoesNotTurnOnPath;
        verification dcSuiteReceiptDoesNotTurnOnPathDoD : Test { :>> id = "482612eb-8923-4bdc-9489-8337b8eef798"; :>> method = VerificationMethod::test; :>> procedureText = "The suite's verdict does not depend on the launching shell's PATH. keel-cli/tests/wrapper_resolves_only_the_pin.rs computes fixture checksums with the sha2 crate already in Cargo.toml instead of spawning `sh -c sha256sum`; a grep of keel-cli/tests for `Command::new('sh')` finds no test whose OUTCOME (as opposed to the wrapper under test, which is a shell script and legitimately needs one) turns on a POSIX shell being present - any remaining spawn of sh in a test is guarded so that its absence yields a SKIP naming the missing tool, never a panic (issue412). Verified by running `keel suite` once from PowerShell and once from git-bash on this host and reading both receipts back as pass with equal counts."; }
        // RAN: keel-cli/tests/wrapper_resolves_only_the_pin.rs computes fixture checksums with sha2 in-process (was sh -c sha256sum); grep of keel-cli/tests finds sh spawned only there, and its one remaining spawn (running the shell-script wrapper under test) is guarded so its absence is a SKIP naming sh, never a panic; the test reads 7 passed 0 failed from PowerShell (no sh on PATH, Get-Command sh null) AND from git-bash - equal counts, so the verdict does not turn on the launching shell (issue412); D0392; see sprint617
        part dcSuiteReceiptDoesNotTurnOnPathDoDR1 : TestResult { :>> id = "5f1157bb-9ffd-4912-8102-3b8f4ccfb146"; :>> outcome = VerdictKind::pass; :>> judgedAgainst = "4b75101b6cda8ce6a72768657ba4f3670fb4e0ac"; :>> judgedAt = "2026-09-08"; :>> judgedBy = "claudeOpus5"; }
        // issue414 is High: a rejection given in chat had no write path (D0311 ranks it above the Medium and unranked items below).
        action dcRejectHasACliPath;
        verification dcRejectHasACliPathDoD : Test { :>> id = "4c63b673-80c4-43cc-bd88-18b0ccf69167"; :>> method = VerificationMethod::test; :>> procedureText = "DONE MEANS: a human's rejection of a proposed Decision given in chat is recorded through the write API from an agent session, the same way keel accept records their acceptance. Resolves issue414: on 2026-09-08 the human answered a brief ask with the reverse of D0376 and there was no `keel reject` - write::reject_decision exists only behind the console's POST /api/decision/reject, so the first rejection in this project's history was a hand edit mirroring the writer's output, which no guard distinguishes from a fabricated one. DO: add `keel reject <d> --words '<verbatim>' --by <human> --date <d>` as a CliCommand fact (family: attestation, beside accept) dispatching to write::reject_decision with the same channel rules as accept - delegation d0192 quote receipt bounded with typographic quotes, read-back ratification (the words name the id, an option letter or three title words), TTY gesture at the human's own terminal, refusal when the session actor is unbound - and stamp createdBy on the RejectR1 result (D0299). VERIFY: a test rejects a fixture proposed Decision through the command and asserts status rejected + a Reject confirmation test + a fail result judged by the human and created by the session actor; the command refuses a bare 'no' with the same read-back message accept uses; cli-surface-declared holds facts, help and dispatch equal; keel guard ALL PASS."; }
        // RAN: keel reject <d> (--words|--note) --by --date records a human's rejection from an agent session under accept's channel rules (delegation, quote receipt, read-back, TTY gesture, unbound-recorder refusal); write::reject_decision stamps createdBy on RejectR1 (D0299), console passes judge as recorder; cliReject CliCommand + CLI_FACTS + COMMAND_NAMES + dispatch, cli-surface-declared PASS 107; tests: recorded with judge/recorder apart, bare-no refused with read-back, unbound refused, help+surface carry it; D0393; see sprint618
        part dcRejectHasACliPathDoDR1 : TestResult { :>> id = "1422db10-bf5b-43b0-a5a8-1606a90d3739"; :>> outcome = VerdictKind::pass; :>> judgedAgainst = "4b75101b6cda8ce6a72768657ba4f3670fb4e0ac"; :>> judgedAt = "2026-09-08"; :>> judgedBy = "claudeOpus5"; }
        action dcScriptProbesRunInCi;
        verification dcScriptProbesRunInCiDoD : Test { :>> id = "dc5148b0-2363-4ec2-b448-e2c5db073b7b"; :>> method = VerificationMethod::test; :>> procedureText = "DONE MEANS: a python check that ships with its own probe is run by CI, so a regression in the check is found by the next push rather than by the next session that happens to run it. Retro finding of sprint 612: scripts/check_templates.py --self-test (D0377's brief cap) and scripts/textpatch.py --probe (D0386's refusal shape) are the two controls whose correctness is verified only by hand, because ci.yml runs no python. DO: one CI step that runs every scripts/*.py declaring a --probe or --self-test entry, discovered from the tree rather than listed, so a third probe joins without editing the workflow; the step is a gate (red fails the push) since each probe is a known-answer check of a control. This is a CI workflow change and rides a co-committed marker Decision. VERIFY: a probe made to fail on purpose in a branch turns CI red naming the script; the discovery picks up a new script with a --probe and ignores one without."; }
        // RAN: ci.yml runs every scripts/*.py carrying a # ci-probe: marker line with that flag as a gate (sys.exit 1 on any non-zero); discovered from the tree, so a new marked script joins with no workflow edit and the sensor facts.py (flag only in prose) is ignored; four probes marked and green (artefact, check_templates, issue400_reproduction, textpatch); the stale check_templates self-test the gate surfaced is fixed; facts.py ciRunsProbes True scriptsWithProbes 4; rides D0394; the real CI run on the push is the external check; see sprint620
        part dcScriptProbesRunInCiDoDR1 : TestResult { :>> id = "88196d96-2eda-4769-bb27-536621df4674"; :>> outcome = VerdictKind::pass; :>> judgedAgainst = "639d8d36aac7ab2d7b10332eee87da2eda6a0521"; :>> judgedAt = "2026-09-09"; :>> judgedBy = "claudeOpus5"; }
        action dcSignedPlanCoversItsNamedSteps;
        verification dcSignedPlanCoversItsNamedStepsDoD : Test { :>> id = "0c3a17d0-2091-41b5-b621-e85edd49c010"; :>> method = VerificationMethod::test; :>> procedureText = "DONE MEANS: a signed plan covers the steps it names (D0375, option C, the human's word 2026-09-08). A process-change or safety-change Decision recorded with `plan: dNNNN` and `step: <name>` in its draft is accepted AT RECORD TIME when the plan Decision (a) exists, (b) was accepted by a HUMAN'S OWN word - its AcceptR carries no AUTO-ACCEPTED token, and its judgedBy is a Person named in github-actors.toml as a decider - and (c) names the step in its own decision or consequences text, matched on the step name exactly; the acceptance note carries a PLAN-COVERED token, the plan id, and the step name, and the judge is the plan's judge. Any of (a)-(c) failing leaves the Decision proposed and says which clause failed and what the plan text was searched for. A guard `plan-covers-step` fails an accepted Decision whose note carries the token when its named plan no longer holds (a)-(c) against the tree - so the cover cannot outlive the plan it cites - and a plan cannot cover itself or another plan-covered Decision (one level: the human's word, then the steps it names, never a chain). VERIFY: tests in both directions - a marker Decision naming a step the plan text carries is accepted with the plan's judge; the same with the plan AUTO-ACCEPTED stays proposed naming clause (b); a step the plan does not name stays proposed naming clause (c) and quoting the searched text's length; a plan covering a plan is refused; the guard fails a fixture whose plan text was edited to drop the step; and the LIVE case - this rule's own Decision records `plan: d0375` `step: plan-covers-step` and is accepted at record time, because D0375's consequences text names it."; }
        // RAN: keel record decision with plan:/step: accepts a marker Decision at record time when the plan exists, is human-signed (no AUTO-ACCEPTED/PLAN-COVERED token, judge a decider) and names the step; note carries PLAN-COVERED + plan + step, judge is the plan's; failing clause leaves it proposed naming which and the searched lengths; guard plan-covers-step (68) re-checks; one level (no plan-of-plan, no self); tests signed_plan_covers_its_steps.rs 5 passed; live case D0396 accepted under d0375 step plan-covers-step; D0375 option C / D0396; see sprint619
        part dcSignedPlanCoversItsNamedStepsDoDR1 : TestResult { :>> id = "12c77a73-14a2-46b8-9c19-a21631764926"; :>> outcome = VerdictKind::pass; :>> judgedAgainst = "216018767b33f8837870e96503aa9e526a34aca5"; :>> judgedAt = "2026-09-08"; :>> judgedBy = "claudeOpus5"; }
        action dcRemainingCliFamilies;
        verification dcRemainingCliFamiliesDoD : Test { :>> id = "6bd11590-5cb4-4dfc-8867-4ff488b97327"; :>> method = VerificationMethod::test; :>> procedureText = "Resolves issue338. NOT started. D0273's consequences promise the visible verb count falls BELOW 25. The lens collapse yields 66 - 100 dispatch arms minus 35 lens verbs plus one router. The criterion was written without deriving it from the measurement in the same Decision's context (43 lenses of ~111 arms already implied roughly 66), so it is a wish with a number attached, and the work would have been called done against it. TWO HONEST RESOLUTIONS, and this task exists to make one of them happen rather than let the miss stand as a recorded criterion nobody revisits. (a) Collapse the remaining families the same way: gate (12 - validate, guard, gate, check, check-engine, rules, assured, reverify, 4 audits), record (11), and the orient/surface/github set (17). Each is a measured consolidation with its own byte-equality baseline, and each is BREAKING with call-site rewrites landing in the same commit via a D0067 transform - the shape sprint 512 established. (b) Amend D0273 by a superseding Decision that states the achieved number and withdraws the 25. DO: measure the remaining families first - how many are read-only lenses in disguise versus verbs that earn their name - and put the choice to the human as a fork with the counts, because (a) is a second breaking change to a surface other things call by name and is not started on my initiative. VERIFY, for whichever is chosen: `keel hardening` helpCoverage.dispatched reads back the number the Decision states, and the two agree."; }
        // RAN: keel show hardening . -> helpCoverage.dispatched 35, namedInHelp 35; python scripts/exec_brief/facts.py -> cliFamilyCensus.topLevel 34, dispatchArms 35, cliShowLenses 51, tree 25527cc; D0458 decision text states 34 verbs, 35 dispatch arms, 51 lenses - equal
        part dcRemainingCliFamiliesDoDR1 : TestResult { :>> id = "482b7735-b36c-4571-b041-e185819f0e5a"; :>> outcome = VerdictKind::pass; :>> judgedAgainst = "25527cc"; :>> judgedAt = "2026-09-12"; :>> judgedBy = "claudeFable5"; }
        action dcRecordSubVerbsAreControlActions;
        verification dcRecordSubVerbsAreControlActionsDoD : Test { :>> id = "8c6d2f56-2246-4294-8cf0-1d461cb04135"; :>> method = VerificationMethod::test; :>> procedureText = "DONE MEANS: the computed control structure (keel show control-structure, D0284) shows one control action per sub-verb of a routing write command, so the D0451 fold of nine writers under keel record does not collapse nine analysed-or-unanalysed actions into one. Resolves issue497: after sprint 680 the structure reads 41 actions (32 open under stpa-currency) where the pre-fold tree read 49 (39 open) - seven never-analysed write actions (cmdAddTask, cmdAppendGateResult, cmdApplyReview, cmdNew, cmdRecordMeasurement, cmdReverify, cmdSnapshotIndicators) vanished into cmdRecord, which run 1 analysed as `record decision` only, and the 8 engine-ucas.sysml contexts naming cmdAppendResult now name an action the structure no longer computes. DO: in control_structure.rs, when a CliCommand fact's invocation is a `|`-separated list of sub-verb forms (the `record` fact is the instance; `show` and `render` are reads and `gate`/`audit`/`github` follow under D0452/D0453), emit one action per sub-verb named cmd<Verb><SubVerb> (cmdRecordResult, cmdRecordTask ...) carrying that segment as its data, in place of the single cmd<Verb> action; the sub-verb list is read from the invocation the same way tests/capability_refusal_bites.rs the_record_sub_verbs_match_the_fact reads it, so the two cannot disagree. Then re-run stpa-self (skill, D0313) over the new actions, recording ANALYSED: with the new names, the 8 recorded UCAs whose context names cmdAppendResult are facts and stay as written - the new run's constraints bind to cmdRecordResult by name, which is how a reader crosses from the old name to the new. VERIFY: keel show control-structure . lists cmdRecordDecision, cmdRecordIssue, cmdRecordStatement, cmdRecordStory, cmdRecordTask, cmdRecordSprint, cmdRecordResult, cmdRecordGateResult, cmdRecordReview, cmdRecordMeasurement, cmdRecordIndicatorSnapshot, cmdRecordReverify and cmdRecordMint - mint writes nothing (D0451) but no declared fact says so, and a hardcoded exclusion would be the literal vocabulary D0271 forbids, so it is emitted and the run records it considered safe; its removal is issue501 (dcSubVerbEffectIsDeclared) - and no bare cmdRecord; keel guard stpa-currency . names none of them as unanalysed after the run; a control_structure.rs unit test holds a fixture fact with a three-segment invocation to three actions and a plain invocation to one; the count of open actions is read back from the guard, not asserted."; }
        // RAN: same receipts as the sprint 681 story DoD (storyRecordSubVerbsAreControlActionsDoDR1): control-structure 63 actions / 13 cmdRecord* / no bare router action (cs681_final.json); cargo test --lib sub_verb_tests 3 + control_structure 11, --test control_structure_is_computed 3, --test capability_refusal_bites 6 passed; keel suite --touched pass 619/0 at 1789180957; stpa-currency 41 of 62 with none of the 13 open; stpaRun4R1 pass at 76b106e; cmdRecordMint emitted and recorded considered safe, its removal tracked as issue501 (dcSubVerbEffectIsDeclared, DoD names it)
        part dcRecordSubVerbsAreControlActionsDoDR1 : TestResult { :>> id = "bd51c63e-220a-4eea-9098-8d2847d1cc85"; :>> outcome = VerdictKind::pass; :>> judgedAgainst = "76b106e"; :>> judgedAt = "2026-09-12"; :>> judgedBy = "claudeFable5"; }
        action dcStandingSummaryUsesTheKit;
        verification dcStandingSummaryUsesTheKitDoD : Test { :>> id = "c20b4846-5f78-4841-8ec9-e1c6a34d1997"; :>> method = VerificationMethod::test; :>> procedureText = "DONE MEANS: the standing executive summary - the one published page that carries what waits on the human - is rendered from the asi-templates exec-summary surface, not hand-authored HTML. The human's direction (st098): 'use the asi template skill for this standing executive summary process.' DO: import the asi-templates unit from the library (it ships the template, the brand tokens, the contract checker and the harness; it declares no guard, so the checker is its only enforcement and this repository's pre-commit runs it whenever templates/ is staged); the page follows the surface's contract - one tab per decision, every choice steel-manned with its real cost, the reasoning chain (what decides it, why this wins over the named alternative, what would flip it, confidence), a mechanism diagram where structure exists, and the Copy-for-AI digest that carries the reasoning back into a session; the source project is named in the title, the badge and the first line of the digest; the brand baseline is re-verified before building and never refreshed to bump its date. VERIFY: python scripts/check_templates.py is clean over the rendered page and over templates/; EXEC_SUMMARY_FILE=<page> python -m pytest tests/exec_summary passes 8/8 including the mobile one-tap copy; the brand-watch comparator reports no drift against brand/manifest.json on every observed field; the page is published to the standing artifact URL so the queue keeps one link; and the pre-commit hook refuses a staged templates/ change that breaks the contract."; }
        // RAN: keel suite . 562 passed 0 failed (receipt 2adf3b98f93f, suite586.txt); python scripts/check_templates.py clean over the rendered page AND over templates/; EXEC_SUMMARY_FILE=<page> pytest tests/exec_summary 8 passed (incl. mobile-webkit one-tap copy, persistence, 44px targets); brand-watch: Microsoft 365 read_resource over the three watched roots then check_manifest.py = no drift on every observed field, baseline untouched; keel validate 664 clean; keel guard ALL PASS; keel sync-claude 46/46 skills; published to the standing artifact URL
        part dcStandingSummaryUsesTheKitDoDR1 : TestResult { :>> id = "002b94dd-4294-4e9b-ba11-7b833a4a88ef"; :>> outcome = VerdictKind::pass; :>> judgedAgainst = "24911a2072ac8d6430a4e95ccff8a28b6eac5483"; :>> judgedAt = "2026-09-06"; :>> judgedBy = "claudeOpus5"; }
        action dcDecisionReportIsArguable;
        verification dcDecisionReportIsArguableDoD : Test { :>> id = "8e3da42c-a78c-4667-b7a2-c67783759237"; :>> method = VerificationMethod::test; :>> procedureText = "DONE MEANS: the standing report is an EXECUTIVE BRIEF the reader can decide from without opening anything else. AMENDED 2026-09-06 after the owner's steering, before any result: the first criterion specified a QOC field set (mechanism prose, a forces table, a claims ledger, a foreclosure line). Their words redirected it: 'I need all information critical to making the decision in one place, no references, high amounts of visuals to illustrate ideas, and strong logical recommendation to guide decision making', and 'I want diagrams relating to the logic. how do things works today and how would the change affect them? ... I want downstream impact'. DO: answer first - the title IS the recommendation and the ask carries response options and reversibility; one page, no tabs, because tabs hide what the reader needs; NO record id, task name or process name in anything the reader reads - the fact replaces the pointer, and identity rides only in the copy-for-AI digest so a pasted answer can still be attached to a record; every number computed from a facts file rather than typed, with numbers in one sentence drawn from one scope; per ask two mandatory logic exhibits - how it works today versus changed, and what lands downstream, each carrying magnitudes; every figure titled with a sentence that makes a claim, every label a thing that happens rather than an id; a do-nothing course priced; and the state of each item stated, so an ask that is really a ratification says so and prices the revert. VERIFY: the skill carries the contract; check_templates.py --brief enforces the mechanical half (no ids in reader text, a verb in the headline and in every figure title, options that declare what they decide, a provenance strip with a date, at least two figures, both themes, viewport, external links in a new tab) and is shown to BITE on a falsified page; the brief passes it; the rendered page is read as an image before publishing; and what the checker cannot judge - whether the stated fact is the right one, whether a course is steelmanned - is named as judgment in the skill rather than faked as a regex."; }
        // RAN: python scripts/check_templates.py --brief <the published brief> = clean; the same checker on a probe with one injected id and one stripped figure title = 2 violations, both named (it bites); cargo test --test push_gate_is_withdrawn 2 passed; keel validate 665 clean; keel guard ALL PASS; clippy -D warnings clean; keel sync-claude 46/46 skills; the rendered page read as an image before publishing
        part dcDecisionReportIsArguableDoDR1 : TestResult { :>> id = "9b32d3f1-c76b-4c7a-a521-ffcb33ae9ca2"; :>> outcome = VerdictKind::pass; :>> judgedAgainst = "2091b10dd28190347ee99cf7a2bacb7ee2d26466"; :>> judgedAt = "2026-09-06"; :>> judgedBy = "claudeOpus5"; }
        action dcMigrateReportsTheFailingLines;
        verification dcMigrateReportsTheFailingLinesDoD : Test { :>> id = "d35d5986-0d7a-4e88-a81f-86b4120f64d2"; :>> method = VerificationMethod::test; :>> procedureText = "DONE MEANS: a failed engine update names what failed. Resolves issue384: keel migrate printed output.lines().take(40) of the gate run, which on a 63-guard run is forty PASS lines, so the violation that caused the revert was invisible in the printed report and in the recorded attempt, which stored the same clipped text - the 0.4.0 bump reverted on claude-surface-drift and neither surface contained the word. DO: select the lines that name a failure, violation, error or refusal, cap the list with a count of the remainder, and fall back to the tail when nothing names itself; store the same selection in the attempt record so keel status and the next run report the cause rather than the preamble. VERIFY: the three migration suites pass (migration_rolls_back, migration_fixture_is_realistic, federation); a gate output whose only failing line sits past line forty is reported by gate_failure_lines rather than clipped."; }
        // RAN: cargo test --test migration_rolls_back --test migration_fixture_is_realistic --test federation = 11+6+3 = 20 passed 0 failed after the fix; the 0.4.0 bump that exposed it now migrates clean; gate_failure_lines selects failing lines and the recorded attempt stores the same selection
        part dcMigrateReportsTheFailingLinesDoDR1 : TestResult { :>> id = "f6a8081f-aecc-453e-8766-34e99d26ff79"; :>> outcome = VerdictKind::pass; :>> judgedAgainst = "8dc7c7710ba4daf3dfa0a8633c14c36b6bf9d9de"; :>> judgedAt = "2026-09-06"; :>> judgedBy = "claudeOpus5"; }
        action dcReleaseGateHasTheToken;
        verification dcReleaseGateHasTheTokenDoD : Test { :>> id = "e4f8295c-0a15-430a-bfc6-dc256cd970f4"; :>> method = VerificationMethod::test; :>> procedureText = "DONE MEANS: the release gate runs the same tests CI runs, and a release that cannot publish says so where someone reads it. Resolves issue385: the release workflow's cargo test step supplied no GitHub token, so the one test that calls the real repository through gh failed there while passing on every push - the tag for v0.4.0 gated red, the build job was skipped, and no release object was ever created. The class is issue260's exactly one workflow over: a gating surface that only runs at release time drifts from the surface that runs constantly, and rarity hides it. DO: give the release gate the same repo-scoped token ci.yml already supplies, with the reason recorded beside it; correct forward to v0.4.1 rather than moving the v0.4.0 tag, because a tag that moves makes a recorded judgement unreadable and the Release record already names the tagged commit. VERIFY: the release workflow for v0.4.1 concludes success, the build matrix runs rather than being skipped, and the three platform assets are attached to the published release; the v0.4.0 tag is left in place as the evidence and the Release record states that it published nothing."; }
        // RAN: ci-run id=34048681892 workflow=release
        part dcReleaseGateHasTheTokenDoDR1 : TestResult { :>> id = "5cb7fcd6-cdc6-4efa-973f-f68bdb7be5bb"; :>> outcome = VerdictKind::pass; :>> judgedAgainst = "b171cd7"; :>> judgedAt = "2026-09-06"; :>> judgedBy = "claudeOpus5"; }
        action dcResultBindsToItsLandingCommit;
        verification dcResultBindsToItsLandingCommitDoD : Test { :>> id = "9393c050-ba83-482d-ac3d-51ce0630c4b6"; :>> method = VerificationMethod::test; :>> procedureText = "DONE when a TestResult is bound to the tree that carries the work it judges, not the tree that preceded it. FOUND by stpa-self run 1 (UCA-A2): the ordinary shape of a DoD pass is `append-result --sha HEAD` while the work sits uncommitted, so judgedAgainst names a commit whose tree does NOT contain what was verified; deliverable-drift suspicion then measures drift from the wrong baseline, and `governing-version`-style reads of the result point at a tree where the claim is false. DO: the same fallback D0308 gave acceptances - when the result's judgedAgainst commit is an ancestor of the commit that INTRODUCED the result, every reader that dereferences judgedAgainst (orient's deliverable suspicion, reverify, attestation) treats the introducing commit as the binding; `append-result` says so in its output when the working tree is dirty, so the author knows which tree the pass will read against. VERIFY: a fixture that records a pass at HEAD, then commits the work, reads the pass as bound to the landing commit; a pass recorded on a clean tree is unchanged; this repository's own history re-reads with no suspect added EXCEPT a done task whose own DoD was edited after its pass and whose old baseline predated the DoD (blind before, so those are the defect being fixed, each named in the receipt) - and the suspect set shrinks, since drift from a later baseline is a subset of drift from an earlier one."; }
        // RAN: unit fixture a_pass_recorded_before_its_landing_commit_binds_to_the_landing_commit (landing commit bound; unknown id absent; non-ancestor judgedAgainst unchanged) passes; keel orient . re-reads this repository at 27 suspects against 74 at 896ef88, the 6 added - dcBatchedGovernanceIndex, storyBatchedGovernance, storyCritiquePass3, storyCritiquePass7, storyDeadFields, storyFederationPlatform - each a post-pass own-DoD edit whose old baseline predated the DoD; append-gate-result on this dirty tree printed the binding note; cargo test --workspace --release 676 passed 0 failed
        part dcResultBindsToItsLandingCommitDoDR1 : TestResult { :>> id = "7f2e832b-874f-4229-91d7-510d174e3193"; :>> outcome = VerdictKind::pass; :>> judgedAgainst = "896ef88"; :>> judgedAt = "2026-09-09"; :>> judgedBy = "claudeOpus5"; }
        action dcSuiteSurvivesItsOwnImage;
        verification dcSuiteSurvivesItsOwnImageDoD : Test { :>> id = "f575a5d9-36c6-46ea-a30b-3cf7e733b267"; :>> method = VerificationMethod::test; :>> procedureText = "DONE MEANS: keel suite cannot be defeated by the fact that it is itself running. Resolves issue386: keel suite shells out to cargo test --release, which rebuilds the very binary executing it; on Windows the running image cannot be replaced, so cargo exits with 'failed to remove file target/release/keel.exe - Access is denied (os error 5)' and the command reports 'fail - 0 passed, 0 failed' and writes a receipt over the deliverable fingerprint saying so. It is not a false green - the verdict is fail - but it is a verdict about the file lock rather than about the code, recorded in the same field a real red would use, and the operator's only clue is a line in a log file. Same family as issue150, where keel serve held the binary and blocked every rebuild. DO: make the command handle its own image - run the tests from a copy, or detect that the executing binary sits inside the target directory the build will write and say exactly that with the copy-and-rerun remedy, rather than emitting a receipt whose outcome cannot be distinguished from a failing test. A receipt written for a run that never ran the tests must not claim the deliverable was measured. VERIFY: keel suite invoked as target/release/keel.exe on a tree whose sources have changed completes and reports real counts, or refuses with the named cause and writes NO receipt; the case is covered by a test that does not need a Windows host to be meaningful."; }
        // RAN: unit test the_suite_knows_its_own_image_and_a_run_that_never_ran passes (cargo test --release -p keel-cli --lib, 430 passed); live: target/release/keel.exe suite . exit 2 with receipt md5 3cc53f648e6852caeb8994641e834a3d unchanged and no new log; keel-serve.exe suite . -- --no-such-cargo-flag exit 2, receipt restored byte-identical, log written
        part dcSuiteSurvivesItsOwnImageDoDR1 : TestResult { :>> id = "946ee262-6db4-47b8-8991-02dfe5205633"; :>> outcome = VerdictKind::pass; :>> judgedAgainst = "9a5ae60"; :>> judgedAt = "2026-09-09"; :>> judgedBy = "claudeOpus5"; }
        action dcStopSaysNothingAboutDecisions;
        verification dcStopSaysNothingAboutDecisionsDoD : Test { :>> id = "f7bf56e1-0ea5-454f-8abe-459bde28f35b"; :>> method = VerificationMethod::test; :>> procedureText = "DONE MEANS: a green turn says nothing about outstanding decisions, and what waits reaches the human as a published page that is refreshed when the set moves. Chartered by D0359, accepted on the owner's quoted words 2026-09-06. DO: the Stop hook's green branch returns silently, its one-line helper is deleted rather than disabled, and the test that pinned the line is replaced by one that pins the silence WITH decisions pending - the state the line existed to talk about. keel show authority-queue carries each row's shortName so the page can be built from one lens instead of re-reading decision files, and the now-unused short-name helper is deleted rather than left as a tombstone. The decision-surfacing process and skill are reshaped from 're-surface every turn and lead every response with the link' into a post-analysis: read the lens, apply a state test against the ids recorded in .keel/decision-page.toml, and produce NOTHING when the published set equals the pending set. The brief's computed-facts script and its chart primitives move from a session scratchpad into scripts/exec_brief/, because a process the next session cannot re-run is a memory rather than a process. CLAUDE.md stops describing a line the binary no longer emits. VERIFY: stop_says_nothing_about_decisions passes on a scaffold holding two proposed Decisions, asserting empty stdout, and its third case asserts the lens still answers what waits with a shortName; scripts/exec_brief/facts.py runs from the repository root and computes every fact it emits with none null; validate, check-engine and the full guard set green; clippy -D warnings clean; the full suite green."; }
        // RAN: keel suite . = 562 passed 0 failed (receipt 95df485b038f); cargo test --bin keel the_turn_boundary 1/1; --test stop_says_nothing_about_decisions 3/3; python scripts/exec_brief/facts.py = 51 facts, 0 null; keel validate 668; keel guard ALL PASS; clippy -D warnings clean
        part dcStopSaysNothingAboutDecisionsDoDR1 : TestResult { :>> id = "744bbeae-8420-40a6-9e9d-87a283cd7dc5"; :>> outcome = VerdictKind::pass; :>> judgedAgainst = "HEAD"; :>> judgedAt = "2026-09-06"; :>> judgedBy = "claudeOpus5"; }
        action dcReleaseRecordNamesItsTag;
        verification dcReleaseRecordNamesItsTagDoD : Test { :>> id = "dd8137d9-2ddb-450e-9535-951b064c91ca"; :>> method = VerificationMethod::test; :>> procedureText = "DONE MEANS: a tag is bound to its Release record by an authored field, not by prose that happens to contain the tag string. Resolves issue387: release-recorded matches with title.contains(tag) and takes the first hit, so a v0.4.0 record whose title mentioned v0.4.1 was reported as the v0.4.1 tag's record and produced a disagreement between two records that were both correct; unanchored containment also means a v0.4.1 tag matches a v0.4.11 title, where the wrong record would silently VOUCH for a tag rather than merely warn about it. DO: give Release the tag it names as its own attribute, match on that field, keep 'a tag with no record naming it' as the violation it already is, and migrate the existing Release records to carry their tag - it is a schema attribute addition, so it goes through the Change Request route with the frozen-schema gate rather than being added in passing. VERIFY: a Release record whose prose mentions another version does not match that version's tag; a record for vN.N.1 does not match the tag vN.N.11 or the reverse; every existing tag still resolves to exactly one record after the migration; guard release-recorded reports no warning on this tree for a reason that can be pointed at rather than because a title was reworded."; }
        // RAN: cargo test --release -p keel-cli --lib release_tag_tests: a_release_is_bound_to_its_tag_by_the_field_and_nothing_else 1 passed (prose-mentions-another-version, v0.4.1 vs v0.4.11 both ways, missing tag, retired record); migration 2026-09-09-release-tag-field.py dry run 9 of 9 tags covered, applied 10 inserts, idempotent; live probe: removing v0.4.1's tag line -> guard release-recorded WARN naming v0.4.1; restored md5 eb3fe497 -> 9 scanned 0 warnings
        part dcReleaseRecordNamesItsTagDoDR1 : TestResult { :>> id = "97ede324-743f-4d55-8999-4e2ddaa82534"; :>> outcome = VerdictKind::pass; :>> judgedAgainst = "3a3d821"; :>> judgedAt = "2026-09-09"; :>> judgedBy = "claudeOpus5"; }
        action dcFactsNameNoVersion;
        verification dcFactsNameNoVersionDoD : Test { :>> id = "209d4ddb-0402-444c-97d4-46c6e1ac71ce"; :>> method = VerificationMethod::test; :>> procedureText = "DONE MEANS: the facts the standing brief is built from cannot describe a release other than the current one. Resolves issue389: facts.py named one release tag literally in seven places - the tag date, the commit count, the day count and the CI-run filter - so after v0.4.1 shipped every since-the-release fact would have measured against a release two versions back, carrying a `how` string that reads as authoritative because it names a real git command. DO: derive the tag with git describe --tags --abbrev=0 --match v*, emit it as its own fact so a reader can see which release the numbers are about, carry it in the unit of every dependent fact, and make the script REFUSE to run while its own source contains a version literal - the one case where reading source text is correct, because the property is about source text. VERIFY: the script runs clean and reports the current tag with the commit, day and CI counts measured from it; an injected version literal makes it exit with the reason named; removing the literal makes it clean again; and the check scans the WHOLE file rather than only the part above itself, which is how its first version would have passed over the very defect it was written for."; }
        // RAN: python scripts/exec_brief/facts.py = 52 facts with releaseTag v0.4.1 derived, 0 null; with a version literal injected the script exits naming it; with the literal removed it runs clean again
        part dcFactsNameNoVersionDoDR1 : TestResult { :>> id = "941a619b-c6ce-4fd2-98c6-e241a0891093"; :>> outcome = VerdictKind::pass; :>> judgedAgainst = "HEAD"; :>> judgedAt = "2026-09-06"; :>> judgedBy = "claudeOpus5"; }
        action dcTestsBindToPropertiesNotSource;
        verification dcTestsBindToPropertiesNotSourceDoD : Test { :>> id = "cc8cdcb3-1153-4f77-b5fb-5e80e05d8d07"; :>> method = VerificationMethod::test; :>> procedureText = "DONE MEANS: a test cannot silently police a mechanism it has memorised as a string. Resolves issue388: the_turn_boundary_blocks_only_on_dishonest_state asserts that main.rs CONTAINS a given line, so it broke when D0359 deleted that line while the property it names held throughout - the second such breakage of the same test, its predecessor having failed the same way when the D0270 advisory was removed. DO: decide first, on the evidence in the tree, whether the rule is a refusal or a warning, because several source-reading checks here are legitimate controls - the doc-claim, guard-catalogue and CLI-surface tests read files on purpose, and a blanket refusal would break them. Then implement whichever was chosen over the test surface: a test that reads program source with include_str! of a .rs file AND asserts on substrings of it is reported with the property it should bind to instead. Where a behavioural equivalent already exists, say so in the report rather than only naming the offence. VERIFY: the check fires on the current shape of the_turn_boundary test if that shape is reintroduced, and does NOT fire on the doc-claim, guard-catalogue or CLI-surface tests that read files by design; the full suite stays green; whichever tier was chosen is recorded with its reason, since a warning nobody reads and a refusal that breaks legitimate checks are different failures and the choice between them is the substance of this item."; }
        // RAN: tier REFUSAL recorded in D0401 with reason (census: 14 source-reading tests, 3 offenders, 0 overlap); keel-cli/tests/tests_bind_to_properties.rs probes: the_turn_boundary shape refused (probe_positive_the_turn_boundary_shape...), doc-claim/guard-catalogue/CLI-surface shapes not refused (probe_negative_the_legitimate_source_reading_shapes...); real-tree run before fixes named exactly the 3 offenders; cargo test --release 59 suites 0 failed
        part dcTestsBindToPropertiesNotSourceDoDR1 : TestResult { :>> id = "a2ae6a78-a769-4fd1-b290-2d8b32c5a5f0"; :>> outcome = VerdictKind::pass; :>> judgedAgainst = "b9294ef"; :>> judgedAt = "2026-09-09"; :>> judgedBy = "claudeOpus5"; }
        action dcExhibitsDoNotHideText;
        verification dcExhibitsDoNotHideTextDoD : Test { :>> id = "24d986f6-3eca-4bec-b91a-93b7c981c172"; :>> method = VerificationMethod::test; :>> procedureText = "DONE MEANS: an exhibit that cannot fit its content says so instead of hiding it. Resolves issue390: the stacked legend spaced entries at even intervals so a long label overprinted its neighbour and its own count, and a logic exhibit's note was a single SVG text element that the canvas edge cut mid-word - SVG does not wrap, so the reader sees a sentence that looks finished. DO: lay the legend out by measured width with a wrap, and break notes on word boundaries with the figure growing to fit; both in the shared modules so every future brief inherits them. THEN decide the harder half, which is why this is tracked rather than closed: nothing measures whether a rendered exhibit fits. The naive check - each text element's length against the viewBox - reported five false positives on right-anchored labels during this fix, so it is worse than none; a real one measures in a browser, which the contract checker does not do today. Weigh that cost against the failure it catches and record the choice either way. VERIFY: a legend whose labels are long enough to overflow wraps rather than overlapping, shown on the real page; a note longer than one line renders every word, shown by reading the rendered page as an image; and whatever is decided about measurement is recorded with its reason rather than left as a residual nobody revisits."; }
        // RAN: delivered by sprint628 (0d5be97, storyExhibitsAreMeasuredDoDR1 at a651fb3): legend_verify.py 4-label stacked legend wraps to two rows and a two-line note renders every word, screenshot read; the measurement choice is D0402 (accepted) with fit_check.py --probe 4 of 4 known cases, and the standing brief measured 12 findings at 0.5px -> 1 real 7px overrun -> 0 after the title split; sprint629 (3f3f39f) keeps assert_fits as the last line of the tabbed builder
        part dcExhibitsDoNotHideTextDoDR1 : TestResult { :>> id = "bce4f75f-0d90-403d-baaa-a2ca9b9bbd76"; :>> outcome = VerdictKind::pass; :>> judgedAgainst = "3f3f39f"; :>> judgedAt = "2026-09-09"; :>> judgedBy = "claudeOpus5"; }
        // Blocks the land of every commit until fixed (issue534): a lib test racing the clock.
        action dcReceiptTestDoesNotRaceTheClock;
        verification dcReceiptTestDoesNotRaceTheClockDoD : Test { :>> id = "a729eaba-3f22-41dd-8ed7-bef9febde6e1"; :>> method = VerificationMethod::test; :>> procedureText = "Resolves issue534. receipt::tests::a_red_run_deletes_the_receipt_and_an_unsettled_key_is_never_trusted stamps fresh.txt with an mtime the two-second racy window cannot age past while the test runs (now + 600 s, the issue481 shape), so the unsettled-key clause is judged on the mtime the key reads and not on how fast the host reaches it. VERIFY: cargo test --release --lib receipt::tests passes (5 tests) on this host; the assertion still names the racy window; the one code path to settled = true for an existing file is hash_path (keel-cli/src/receipt.rs 158: age >= RACY), so a future mtime is unsettled by construction. D0388 pair: the fixed test (a file whose mtime is not two seconds old is unsettled) and a_green_run_writes_the_receipt_and_the_next_run_answers_from_it (an aged tree is settled) - one assertion each way, in the same module."; }
        // RAN: verifier-receipt-2: PROBE PAIR: cargo test --release --lib receipt::tests -> positive a_red_run_deletes_the_receipt_and_an_unsettled_key_is_never_trusted: ok; negative a_green_run_writes_the_receipt_and_the_next_run_answers_from_it: ok; TOUCHED RECEIPT: outcome=pass passed=775 failed=0 seconds=751; cargo clippy --release --all-targets -- -D warnings -> pass; exit=0
        part dcReceiptTestDoesNotRaceTheClockDoDR1 : TestResult { :>> id = "0980f977-f1fd-4e78-adb6-ac305cb4bd1a"; :>> outcome = VerdictKind::pass; :>> judgedAgainst = "08268f9"; :>> judgedAt = "2026-09-14"; :>> judgedBy = "claudeFable5"; }
        // The three accepted panel items of 2026-09-13 (D0474-D0476): the touched run memoised, parallel, and behind one ladder.
        action dcTouchedReceiptIsContentKeyedPerBinary;
        verification dcTouchedReceiptIsContentKeyedPerBinaryDoD : Test { :>> id = "ae25cb09-e81e-4f2a-a066-e4c6f6c08845"; :>> method = VerificationMethod::test; :>> procedureText = "Resolves issue537. The touched receipt is content-keyed per binary and keel land runs only what lacks a green observation (D0474). keel-cli/src/receipt.rs hashes file CONTENT (not len+mtime) so the RACY window is gone; the touched receipt records, per test binary, the two keys it was observed green under: K_code (content of keel-cli/**, .engine/**, Cargo.toml, Cargo.lock, .githooks/**) and K_tree (every tracked and untracked path outside .keel/). touched.rs marks a binary self-reading when its text names CARGO_MANIFEST_DIR; land skips a binary whose K_code is equal and, for a self-reading binary, whose K_tree is also equal, and prints the skipped set and the run set. The receipt files (.keel/metrics/*-receipt.toml, touched-*.log) join claude_surface.rs PROTECTED_PATHS. Known-positive: a repeat land on an unchanged tree runs zero binaries. Known-negative: a .tracking edit after a green run reruns exactly the self-reading binaries and no other; a keel-cli/src edit reruns them all."; }
        // RAN: cargo test --release --test touched_tests_run_before_land -> ok (known-positive: repeat run executes nothing; known-negative: .tracking edit reruns the self-reading set only, keel-cli/src edit reruns all); cargo test --release --lib -- contentkey:: receipt:: touched:: claude_surface::tests::protected -> 22 passed; TOUCHED RECEIPT run 1: KEEL_PERF=1 keel suite --touched . -> outcome=fail passed=792 failed=5 seconds=1246 at=1789366319 head=8b731e6 code_key=3075e7dc4e6bdcbe tree_key=334ce8b08922fb81 observed=60 rows, failing=[control_structure_is_computed, library_read_side, stop_says_nothing_about_decisions] all on perf lines in stdout (issue539); run 2 without the variable: outcome=pass passed=12 seconds=56 over those 3, 60 skipped observed green; run 3: nothing to execute, 63 skipped, 1513 ms wall
        part dcTouchedReceiptIsContentKeyedPerBinaryDoDR1 : TestResult { :>> id = "e3bec174-655e-47de-9249-316ab40f7686"; :>> outcome = VerdictKind::pass; :>> judgedAgainst = "8b731e6"; :>> judgedAt = "2026-09-14"; :>> judgedBy = "claudeFable5"; }
        action dcNextestIsTheTouchedRunner;
        verification dcNextestIsTheTouchedRunnerDoD : Test { :>> id = "02c4da78-cb36-4590-b3ad-baaeb09e7b9e"; :>> method = VerificationMethod::test; :>> procedureText = "Resolves issue536. cargo-nextest is the touched runner (D0475). touched.rs invokes cargo nextest run for the touched set (binaries in parallel, one process per test), the log parser reads nextest output (per-test timings kept in the receipt), the host and the CI workflow install a pinned nextest, and device_bound_taps.rs is reviewed for its fixed port before adoption. Known-positive: the same touched set that summed 673-840 s serially completes in a measured wall the receipt states. Known-negative: a failing test in one binary still names that binary in the receipt's failing list and refuses the land."; }
        // RAN: Resolves issue536. touched.rs runs the set under cargo nextest run --release --no-fail-fast --no-tests pass (binaries in parallel, one process per test), parse_nextest reads each test's verdict and duration into the receipt's [[timing]] rows (slowest first) and the summary names the slowest test; the harness = false binaries (custom_harness_tests over keel-cli/Cargo.toml) run under cargo test in a second invocation; a host without nextest runs everything under cargo test and the receipt's runner says so; ci.yml and release.yml install nextest 0.9.144 from get.nexte.st and mirror the split; device_bound_taps.rs:115 reviewed - one pid-derived port, one binder in the workspace, passed in every run. KNOWN-POSITIVE (the measured wall the receipt states): before, cargo test over the 63-binary set of 2026-09-14 = 1246 s wall (per-binary sum 913 s, lib alone 145 s); after, nextest test phase 723 s at 20 threads, 653 s at 8, 701 s at 4 (797 passed each), and the real-tree receipt under the shipped runner: 823 passed, 0 failed, 995 s wall over 68 binaries including 265 s of build and 641 s of nextest. KNOWN-NEGATIVE: touched_tests_run_before_land -> a_stale_test_naming_a_changed_module_refuses_the_push_and_the_fixed_one_lands passes under the new runner - the failing widget_check names its binary in failing = [widget_check] and land REFUSES; the parser's unit pair counts the re-listed failure once. STATED PLAINLY: the gain is 1.91x at best, UNDER the 2x of D0475's consequence clause; the receipt's first timing row names why (issue540). The keep-or-supersede judgment on D0475 is deferred to the remeasure after dcReportTestBuildsTheModelOnce lands; this result does not make it. Unit tests: cargo test --release --lib -- touched:: -> 17 passed; clippy -D warnings clean
        part dcNextestIsTheTouchedRunnerDoDR1 : TestResult { :>> id = "89c270ba-759e-49c7-a696-3014c8b1cb73"; :>> outcome = VerdictKind::pass; :>> judgedAgainst = "d64d319"; :>> judgedAt = "2026-09-14"; :>> judgedBy = "claudeFable5"; }
        action dcVerifyLadderStopsAtTheFirstRed;
        verification dcVerifyLadderStopsAtTheFirstRedDoD : Test { :>> id = "0c848a68-2577-4698-a0be-b3778aa34f78"; :>> method = VerificationMethod::test; :>> procedureText = "keel verify (D0476) runs the ladder in cost order and stops at the first red: gate validate, gate guard (answering from its receipt), cargo clippy -D warnings, the D0388 probe pair named on the command line, then suite --touched (keyed per D0474). One receipt names the rung it stopped at. Declared as a CliCommand in .engine/cli/commands.sysml. Known-positive: a clippy lint is reported within a minute, before any test binary compiles. Known-negative: a green ladder ends with the touched receipt written and the next keel land skips what it observed."; }
        // RAN: cargo test --release --lib -- verify:: -> 6 passed, 0 failed; cargo clippy --release --all-targets -- -D warnings -> exit 0; KEEL --help line 86 is verify [ROOT] [--probe POSITIVE,NEGATIVE] [--no-receipt]; KEEL verify . --probe onlyone -> --probe names 1 side(s); a D0388 pair is exactly two, exit=2; capability_refusal_bites 9 passed; guard cli-surface-declared PASS 86 scanned. D0388 pair on the real tree from target/release/keel-serve.exe, both detached (s708/verify-pos2.log, s708/verify-neg.log): KNOWN-POSITIVE with one clippy lint injected into keel-cli/src - validate pass 0 s, guard pass 6 s, clippy fail exit 101 68 s, probe not-run, touched not-run; keel verify: fail - stopped at clippy after 74 s; verify-receipt.toml outcome fail stopped_at clippy; no test binary compiled. The DoD says within a minute of reaching that rung: it was 68 s at the rung (cargo check of the whole crate on this machine), stated plainly, not within a minute. KNOWN-NEGATIVE with the lint removed - validate pass 0 s, guard pass 7 s, clippy pass 49 s, probe pass 129 s (cargo test --release --lib -- verify:: 13 passed and -- touched:: 17 passed), touched pass 885 s; keel verify: pass - every rung green in 1071 s; verify-receipt.toml head 1e2ed25 at 1789379978 outcome pass stopped_at none; touched-receipt.toml 800 passed 0 failed 883 s runner cargo-nextest 0.9.144 skipped [] code_key 593ea821b10f6d8e tree_key 14adcb209c805209. The next keel land (commit 593147c, this tree) then skipped 49 of its 61 selected binaries at code_key 593ea821b10f6d8e and ran the 12 that read this repo plus lib: touched-receipt.toml head 593147c at 1789381323 outcome pass 662 passed 0 failed 498 s ran 12 skipped 49 - what the ladder observed, the land honoured (D0474).
        part dcVerifyLadderStopsAtTheFirstRedDoDR1 : TestResult { :>> id = "d70f3c20-1f30-4997-8dc0-6ed1ca4df77b"; :>> outcome = VerdictKind::pass; :>> judgedAgainst = "593147c"; :>> judgedAt = "2026-09-14"; :>> judgedBy = "claudeFable5"; }
        action dcCiNextestExcludesEveryCustomHarness;
        verification dcCiNextestExcludesEveryCustomHarnessDoD : Test { :>> id = "572868c2-f1fa-4197-87ee-d5c02ab8621e"; :>> method = VerificationMethod::test; :>> procedureText = "DONE MEANS: every harness = false test target in the WORKSPACE runs under cargo test in CI and none is handed to nextest, and a test pins the workflows to the manifests so a new custom-harness binary fails locally before it fails on ubuntu. Resolves issue542. TODAY: ci.yml:35 and release.yml:52 run `cargo nextest run --workspace` excluding only keel-cli's trio (cli_bdd, orient_bdd, write_bdd); keel-parser/Cargo.toml:29-42 declares four more (lexer_bdd, parser_bdd, semantic_bdd, spec_compat_bdd), and nextest's `--list` on lexer_bdd exited 2 (`unexpected argument '--list'`), so the CI run for 1e2ed25 concluded failure - main is red. sprint707's retro dismissed this drift because custom_harness_tests reads a manifest: it reads keel-cli's alone (touched.rs:688), and CI runs the workspace. DO: (1) the nextest expression excludes every harness = false binary of every workspace member and the cargo test line runs each with -p <crate> --test <name>; (2) touched::custom_harness_tests is read over every workspace manifest (Cargo.toml [workspace].members) and an integration test asserts that both workflows' exclusion set and cargo test set EQUAL that list - the control (D0047), so the hand-mirrored split cannot drift again; (3) gate-environment-parity keeps counting `cargo nextest` as a test step. VERIFY: known-positive - the test, run against the workflows as committed at 1e2ed25 (a fixture copy), names the four keel-parser binaries as missing; known-negative - against the fixed workflows it passes, and the CI conclusion for the fixing commit is success (gh run list --json conclusion). Chartered by D0475 (nextest is the runner); the local touched run is unchanged by this."; }
        // RAN: ci-run id=34841977614 workflow=ci - the DoD's CI clause read from `gh run list --limit 1 --json conclusion,status,headSha` -> conclusion success at 838f75f9, job rust step `test` success over the nextest exclusion of all seven `harness = false` binaries and the two `cargo test` lines (keel-cli three, keel-parser four; ci.yml:36-38, release.yml the same split). Guard custom-harness-routed: `cargo test --release --lib -- custom_harness_routed` 3 passed (known-positive names keel-parser's four as missing from 1e2ed25's split; known-negative a complete split is clean); `keel gate guard --no-receipt .` -> [guard:custom-harness-routed] PASS 2 scanned; registered in GUARD_NAMES (keel version: 75 guards), guards.md (doc-guard-count PASS), control-map (control-map-reconciled PASS) and, after the land of 6281526 failed on its absence, guard-constraints.sysml (every_guard_has_a_constraint_def_identity passed in the 838f75f ladder). The story's R2 carries the same receipt.
        part dcCiNextestExcludesEveryCustomHarnessDoDR1 : TestResult { :>> id = "4ffb9fb1-80bd-4053-a52c-5d1ca962db32"; :>> outcome = VerdictKind::pass; :>> judgedAgainst = "838f75f"; :>> judgedAt = "2026-09-14"; :>> judgedBy = "claudeFable5"; }
        action dcCeremonyOrderCountsAFailedGateAsRecorded;
        verification dcCeremonyOrderCountsAFailedGateAsRecordedDoD : Test { :>> id = "0c3c8a6b-7575-4d98-9e94-391ddaf9edbd"; :>> method = VerificationMethod::test; :>> procedureText = "Resolves issue544 (D0437's clause, completed): the ceremony guard's ORDER reader counts a gate as recorded when ANY TestResult is written for it - pass, proposed, fail, inconclusive or error - because sequence asks whether the record was written in its turn, not what it says; done-ness stays gate_passed's (orient, advance, the suspect algebra) and the flow view's retro reader (which asks where a sprint FINISHED, and refuses fail on purpose) is unchanged. Known-positive, chosen before the tree is read: a CloseOut recorded fail followed by a Retro recorded pass raises no ordering violation, while gate_passed still reads that CloseOut as not passed; known-negative: a CloseOut with no result at all followed by a Retro is still an ordering violation, and the real tree with sprint708's failed closeOut passes guard ceremony. The guard's doc comment and guards.md row say fail counts for order."; }
        // RAN: KNOWN-POSITIVE (unit, chosen before the tree was read): ceremony_order_counts_a_failed_gate_as_recorded - CloseOut fail then Retro pass -> gates_recorded 2, ordering_violations empty, gate_passed(CloseOut) false, gate_recorded(CloseOut) false; KNOWN-NEGATIVE: CloseOut with no result then Retro pass -> ordering_violations [(Retro, CloseOut)]; cargo test --release --lib -- ceremony custom_harness_routed retro_reader -> 10 passed 0 failed including view::flow::tests::the_retro_reader_accepts_pass_and_proposed_and_refuses_fail; REAL TREE: keel gate guard --no-receipt . -> [guard:ceremony] PASS - 711 scanned, 0 violation(s) with sprint708's closeOut fail 6f640d03 and retro pass in the tree, where the binary at 593147c reported FAIL Retro recorded but CloseOut (earlier) unrecorded; grep gate_recorded keel-cli/src -> callers guards.rs (now gate_has_result) and flow.rs:116 (unchanged); cargo clippy --release --all-targets -- -D warnings exit 0; guards.md ceremony row and the gates_recorded doc comment name fail as counting for order
        part dcCeremonyOrderCountsAFailedGateAsRecordedDoDR1 : TestResult { :>> id = "b450fe65-fae5-4e65-89b8-bd2abd79f1a7"; :>> outcome = VerdictKind::pass; :>> judgedAgainst = "593147c"; :>> judgedAt = "2026-09-14"; :>> judgedBy = "claudeFable5"; }
        action dcEvidenceGoesThroughAFile;
        verification dcEvidenceGoesThroughAFileDoD : Test { :>> id = "67074b85-028c-4016-aad0-99b12443a326"; :>> method = VerificationMethod::test; :>> procedureText = "Resolves issue543 (D0224, fifth occurrence): record result and record gate-result accept --evidence-from FILE (and --notes-from FILE for gate-result), read verbatim, with --evidence still accepted for one-line receipts; passing both is refused naming the two flags. The usage line, CLI_FACTS invocation, commands.sysml and the CLAUDE.md sect.4 writes line name the file form and say PREFER THIS for anything quoting a command. Known-positive: a file whose text carries a backtick span and a parenthesised refusal round-trips into the RAN line byte for byte (unit test), where the same text as a double-quoted shell argument would have been substituted; known-negative: the existing one-line --evidence path is unchanged and every result recorded before this change parses as before (cargo test on the write module; gate validate over the tree)."; }
        // RAN: cargo test --release -p keel-cli --test evidence_goes_through_a_file -> 3 passed 0 failed: known-positive a_receipt_read_from_a_file_lands_verbatim_backticks_included (a file whose text carries two backtick spans and a parenthesised refusal lands in // RAN: byte for byte); known-negative the_one_line_shell_form_still_lands (--evidence TEXT unchanged) and both_flags_at_once_are_refused_by_name_and_nothing_is_written (refusal names --evidence-from and --evidence; file untouched; unreadable file refused with cannot read). cargo test --release -p keel-cli --lib -- write:: -> 36 passed unchanged; keel gate validate . -> 815 clean over every result recorded before this change; cargo clippy --release --all-targets -- -D warnings exit 0; cli-surface-declared PASS 86, cli-reference PASS 441.
        part dcEvidenceGoesThroughAFileDoDR1 : TestResult { :>> id = "792b0232-7d31-4723-8b67-d86b0b55eadb"; :>> outcome = VerdictKind::pass; :>> judgedAgainst = "838f75f"; :>> judgedAt = "2026-09-14"; :>> judgedBy = "claudeFable5"; }
        action dcCliFactSupersessionIsHonoured;
        verification dcCliFactSupersessionIsHonouredDoD : Test { :>> id = "8718ec5c-1563-4c57-abd6-30c3cf57987c"; :>> method = VerificationMethod::test; :>> procedureText = "Resolves issue547: a CliCommand fact whose owner is another actor is changed the D0108 way - a new part owned by the editor plus a #Supersede edge to the old - and every reader of .engine/cli/commands.sysml honours the edge: parse_cli_facts (guards.rs) drops a fact that is a #Supersede target, so cli-surface-declared compares the fact in force alone against cli_facts.rs and the dispatch, and keel --help renders it. Resolves issue548 in the same reader: invocation joins family, effect, stability and synopsis as a compared field (accept's drift - sysml (--words TEXT | --note TEXT), mirror --note TEXT - is the first thing it catches, and the mirror is regenerated to the .sysml), and two facts in force declaring one name is a violation instead of a silent BTreeMap collapse. Known-positive: a fixture with cliX superseded by cliX2 of the same name yields one authored fact, the superseder's, and the mirror equal to it is clean (unit test); known-negative: the same fixture without the edge is a duplicate-name violation (today it is silently collapsed - the check is probed before it is claimed, D0388), and the two delete-and-re-author precedents (74c1923 cliGithub, sprint 711 cliRecord) are not re-opened - they stand, their old ids gone, as the cost this task ends."; }
        // RAN: cargo test --release -p keel-cli --lib -- cli_surface -> 12 passed 0 failed. Known-positive a_superseded_fact_is_not_in_force_and_two_live_facts_of_one_name_are_a_violation: cliX superseded by cliX2 of one name parses to ONE fact (part cliX2, synopsis s) and a level mirror is clean; known-negative: the same two lines without the edge -> violation naming `cliX` and `cliX2` as two CliCommand facts in force. an_invocation_that_drifts_between_the_two_homes_is_caught: mirror invocation differs -> 1 violation containing 'invocation differs' and '--words'; level mirror -> clean. supersede_edges dirs now [.engine/decisions, .engine/cli, .tracking] (lib.rs). cli_facts.rs accept invocation regenerated. keel gate guard --no-receipt . -> cli-surface-declared PASS 86 scanned. Precedents not re-opened (git status: commands.sysml clean).
        part dcCliFactSupersessionIsHonouredDoDR1 : TestResult { :>> id = "d7addecd-762e-4bab-b4e1-eaea04577c9c"; :>> outcome = VerdictKind::pass; :>> judgedAgainst = "c592ef6"; :>> judgedAt = "2026-09-14"; :>> judgedBy = "claudeFable5"; }
        action dcEveryProseFlagReadsAFile;
        verification dcEveryProseFlagReadsAFileDoD : Test { :>> id = "06a88a31-e7d0-4905-9b10-b07b6f353d25"; :>> method = VerificationMethod::test; :>> procedureText = "Resolves issue546: every prose flag still read straight from the shell argument path gains its file form through the one prose_flag reader (D0224, sprint 711) - override --reason, record story --i-want / --so-that / --triage-note (--implication is an ImplicationKind enum member, not prose, and stays inline), accept --note, reject --note and judge-set --note (the fold_words_into_note and fold_warnings_into_note readers included) read --X-from FILE else --X, refusing both by name; accept --words stays a shell argument on purpose (a human's short quote, D0192) and says so in its usage line. The usage lines, cli_facts.rs and commands.sysml name each file form. Known-positive: a file carrying a backtick span round-trips into each field verbatim (integration test extending evidence_goes_through_a_file); known-negative: the inline forms land unchanged and a grep of main.rs for flag(args, over the prose-shaped names finds every read inside one of the five commands after its prose_args call, or inside fold_words_into_note / fold_warnings_into_note / verdict_channel_refusal, whose only callers are those commands after that call - no read of a prose flag ever sees the raw argument list, and that caller map is the grep the retro can re-run."; }
        // RAN: DoD for dcEveryProseFlagReadsAFile (issue546) at af5def6, 2026-09-14. prose_args(args, names, verb) -> Result<Vec<String>, i32> at main.rs 2901 rewrites --X-from FILE into --X TEXT through prose_flag and refuses both by name (prose_flag's error); called first in cmd_override (reason), cmd_record_story (i-want, so-that, triage-note), cmd_accept, cmd_reject, cmd_judge_set (note). --implication stays inline; accept --words stays a shell argument and the usage line says so (D0192). Usage lines, cli_facts.rs and commands.sysml name each file form; cliAccept/cliReject/cliJudgeSet/cliOverride retired by #Supersede edges beside them, re-declared as cliAccept2/cliReject2/cliJudgeSet2/cliOverride2 under minted ids. // RAN: cargo test --release -p keel-cli --test prose_flags_read_a_file -> 3 passed; 0 failed (known-positive: the span 'run `keel gate validate .` first (refused otherwise)' lands verbatim in .keel/override.json, in the story's iWant, and in the accepted decision's note; known-negative: inline forms land, both forms refused naming both flags with nothing written, asserted per command) // RAN: grep -n 'flag(args, '/(reason/|i-want/|so-that/|triage-note/|note/)')' keel-cli/src/main.rs -> 11 reads at 2500 (cmd_override), 3479/3504/3505 (cmd_record_story), 4925 (fold_warnings_into_note), 4980/4989 (verdict_channel_refusal), 5054 (fold_words_into_note), 5097 (cmd_accept), 5207 (cmd_reject), 5333 (cmd_judge_set); the helpers' only callers are cmd_accept/cmd_reject/cmd_judge_set after their prose_args call (grep -n on the helper names) // RAN: keel gate guard --no-receipt . -> cli-surface-declared PASS 86 scanned; ownership PASS; no violations
        part dcEveryProseFlagReadsAFileDoDR1 : TestResult { :>> id = "537a8fc5-a38b-4989-aec0-a48fe5cd6eb4"; :>> outcome = VerdictKind::pass; :>> judgedAgainst = "af5def6"; :>> judgedAt = "2026-09-14"; :>> judgedBy = "claudeFable5"; }
        // D0479 modularity pass (st126): members in layer order; D0481/D0482 receipts and D0483 guard follow the members they need.
        action dcWorkspaceHoldsTheLeafMembers;
        verification dcWorkspaceHoldsTheLeafMembersDoD : Test { :>> id = "e684b848-6c02-4120-a2d8-ae243ab7f9d1"; :>> method = VerificationMethod::test; :>> procedureText = "Chartered by D0479. The workspace gains its first leaf members, each a crate under members/ with its own Cargo.toml and no reference back into keel-cli: keel-git (gitx), keel-perf (perf), keel-json (json, color), keel-actor (actor, device), keel-schema (schema, cli_facts, cli_surface, control_defects, embedded), keel-github (github). keel-cli's lib.rs re-exports each under its old module path (pub use keel_git as gitx;) so no other file changes in the same commit and the CLI surface is byte-identical (keel --help diff empty). Known-positive, chosen before the tree is read: after a whitespace-only edit to keel-cli/src/main.rs, cargo build --release -p keel-git compiles zero crates (cargo's Fresh lines, read from --verbose); after an edit to gitx.rs, keel-cli rebuilds and keel-json does not. Known-negative: the full test set passes unchanged under keel land, and a grep of the members' sources for crate:: names only modules inside that member. Cargo.lock names each member; keel version's guard count is unchanged."; }
        // RAN: // RAN: DoD for dcWorkspaceHoldsTheLeafMembers (D0479) at 396f13f (2026-09-14). cargo build --release from the root: Finished release in 1m 39s, workspace of keel-parser + six members + keel-cli. DoD known-positives (probes.txt): after a whitespace-only edit to keel-cli/src/main.rs, cargo build --release -p keel-git --verbose printed Fresh keel-perf, Fresh keel-git, Finished in 0.13s; after a comment appended to members/keel-git/src/gitx.rs, cargo build --release --verbose printed Compiling keel-git, Compiling keel-cli, and Fresh for keel-perf, keel-json, keel-github, keel-schema, keel-actor (3m 11s). Known-negatives: keel --help byte-identical to the pre-move keel-land.exe render (cmp, 14593 bytes); probe_pair.py neg exits 0 (no member reaches outside itself via crate::) and exits 1 with a planted crate::perf:: line; the D0388 pair ran inside the ladder. keel verify . --probe pos,neg: validate pass, guard pass (75 guards, 0 violations), clippy pass (cargo clippy --release --workspace --all-targets, exit 0), probe pass, touched pass - keel suite --touched: 851 passed in 704s under cargo-nextest 0.9.144, changed modules [actor, cli_facts, cli_surface, color, contentkey, control_defects, device, embedded, github, gitx, init, json, perf, schema, touched], the member-lib invocation ran (touched log rows keel-git gitx::tests::*, keel-github github::*, 81 tests over the non-cli members); every rung green in 710 s; receipt .keel/metrics/verify-receipt.toml. Member unit suites: keel-actor 11, keel-git 4, keel-github 12, keel-json 6, keel-perf 2, keel-schema 14 passed; keel-cli touched/contentkey 22 passed.
        part dcWorkspaceHoldsTheLeafMembersDoDR1 : TestResult { :>> id = "1fd55e7f-c2f9-49ca-8cc9-0262581575c6"; :>> outcome = VerdictKind::pass; :>> judgedAgainst = "396f13f"; :>> judgedAt = "2026-09-14"; :>> judgedBy = "claudeFable5"; }
        action dcReadyHonoursItemDependencies;
        verification dcReadyHonoursItemDependenciesDoD : Test { :>> id = "79ffa840-8155-4858-95c1-717d47562fb5"; :>> method = VerificationMethod::test; :>> procedureText = "Resolves issue549: the ready set (orient.rs narrowing_filters, three filters today: superseded, #DependsOn a proposed Decision, claimed by another) also excludes an item that #DependsOn another backlog item whose DoD has no passing result at a resolvable SHA, and keel show orient lists it under blocked with the item it waits on. Known-positive, chosen before the tree is read: a fixture with A #DependsOn B and B undone lists A blocked and B ready; once B carries a pass, A is ready. Known-negative: the real tree's 19 item-to-item edges at the adding commit narrow the frontier to exactly the items whose predecessors are done (dcWorkspaceHoldsTheLeafMembers ready, dcGuardsViewOrientCycleIsBroken blocked on it), and no item with only Decision edges changes state. An item depending on a superseded item is blocked, not ready, and says so. Resolves issue552 in the same filter: an item whose #CharteredBy edge names a Decision standing proposed is blocked as a #DependsOn edge to it blocks (view/mod.rs blocked_by reads dependson and dependency only) - known-positive, a fixture Story chartered by a proposed Decision is blocked and ready once it is accepted; known-negative, dcWorkspaceLayeringIsGuarded (chartered by held D0483) leaves the ready list at the adding commit and every item chartered by an accepted Decision keeps its state."; }
        // RAN: // RAN: DoD for dcReadyHonoursItemDependencies (issue549, issue552) at bd5076a (2026-09-14). keel verify . --probe 'python scripts/probes/ready_honours_item_dependencies.py pos,python scripts/probes/ready_honours_item_dependencies.py neg' from target/release/keel-verify.exe: validate pass 0 s, guard pass 2 s, clippy pass 16 s, probe pass 3 s (pos holds: ready=[dcFirst] blocked=[{dcSecond waitsOn dcFirst, not done}]; neg holds: ready=[dcSecond, storyChartered] blocked=[]), touched pass 182 s (keel suite --touched: 674 passed, 0 failed, changed modules [orient, view], set includes ready_honours_item_dependencies and the lib unit tests); every rung green in 206 s; receipt .keel/metrics/verify-receipt.toml. Known-positive fails without the fix: the same pos case against target/release/keel-land.exe (built before the change) exited 1 with ready=[dcFirst, dcSecond, storyChartered] blocked=None. Known-negative on the real tree: keel show orient at the working tree vs the orient JSON captured before the change - ready 77 to 68, the nine removed items are exactly the twelve blocked rows' items (removed == blocked items: True), added: [], declaration order preserved, counts equal, answerStatus COMPUTED; the DoD's named example moved because its predecessor passed at 396f13f (dcWorkspaceHoldsTheLeafMembers done, so dcGuardsViewOrientCycleIsBroken is ready, as the clause requires). issue552: the stopgap #DependsOn from dcWorkspaceLayeringIsGuarded to d0483 was removed in this commit and the #CharteredBy edge alone keeps the story off the ready list (68 ready before and after). Unit tests view::tests a_story_chartered_by_a_proposed_decision_is_blocked_until_it_is_accepted and an_item_depending_on_an_undone_item_is_blocked_and_says_what_it_waits_on pass inside the lib run.
        part dcReadyHonoursItemDependenciesDoDR1 : TestResult { :>> id = "0d8b3da3-5eae-4ab3-8134-ad54fff04388"; :>> outcome = VerdictKind::pass; :>> judgedAgainst = "bd5076a"; :>> judgedAt = "2026-09-14"; :>> judgedBy = "claudeFable5"; }
        action dcGuardsViewOrientCycleIsBroken;
        verification dcGuardsViewOrientCycleIsBrokenDoD : Test { :>> id = "3a6be8ba-b923-4ed9-83ad-8a78937afdc5"; :>> method = VerificationMethod::test; :>> procedureText = "Chartered by D0479. The cycles the module graph shows are broken so the next boundaries can be drawn: guards <-> view (view -> guards 10 references) and guards <-> orient and view <-> orient, write -> view and write -> guards, scaffold -> guards. Each back-edge is removed by moving the shared type or function down into the lower layer (or into a leaf member), never by a trait object hiding the edge. Known-positive, chosen before the tree is read: the module graph script over keel-cli/src, committed as scripts/modgraph.py, reports zero references from view, orient, write or scaffold into guards, and zero from view into orient; a fixture with one such reference is reported naming both ends. Known-negative: the full test set passes, keel --help is byte-identical, and the guard count is unchanged."; }
        // RAN: // RAN: DoD for dcGuardsViewOrientCycleIsBroken at 6a22002 (2026-09-14), working tree. keel verify . --probe 'python scripts/modgraph.py --check,sh probe-neg.sh' --no-receipt from target/release/keel-verify.exe (run 4, scratchpad s717/verify4.log): validate pass 0 s (822 files), guard pass 2 s (ALL PASS, 75 guards, 0 violations; process-change satisfied by the co-committed marked D0485; instruments-declared by Sensor snModGraph), clippy pass 76 s (cargo clippy --release --all-targets -- -D warnings, deny(pedantic, nursery) in lib.rs), probe pass 0 s, touched pass 570 s; every rung green in 650 s. Known-positive: python scripts/modgraph.py --check -> 'modgraph: layering holds - no reference from view, orient, write or scaffold into guards; none from view into orient (71 modules, 272 edges)', exit 0; at 6a22002 the same script read 32 references across the five pairs. Known-negative (probe-neg.sh): the fixture with one reference -> 'FORBIDDEN view -> guards (1 reference(s))' and 'view/mod.rs:2: pub fn lens() { crate::guards::run(); }', exit 1; the probe checks both ends and the file:line. Full set: keel suite --touched pass - 878 passed, 0 failed in 568 s over 74 integration binaries plus the lib unit tests (every module changed: algo, attestation, binding, cli_facts, contentkey, control_structure, critique, cursor, done, evidence, flow, gitfacts, govern, guards, hardening, ident, init, intake_write, launcher, orient, priority, process_cmd, queries, reports, scaffold, serve, staleness, suspect, textscan, touched, view, write); slowest lib reports::tests::report_produces_cards_and_rejects_unknown 233.7 s; receipt .keel/metrics/touched-receipt.toml. keel --help: cmp help-old.txt help-new.txt identical (14593 bytes, old = the 6a22002 binary). keel version guards line identical before and after: 'guards: 75 (66 hard-blocking, 9 warning-only)'. No trait object introduced: the five back-edges were removed by moving down (textscan, ident, done, evidence, suspect, gitfacts, binding, keel-schema cli_facts) or up (reports, priority, guards::compute_readiness); the diff adds no `dyn` and no `Box<dyn` (grep over keel-cli/src: 0 new).
        part dcGuardsViewOrientCycleIsBrokenDoDR1 : TestResult { :>> id = "ac0f760f-6d58-4a39-a909-75c10c00be98"; :>> outcome = VerdictKind::pass; :>> judgedAgainst = "6a22002"; :>> judgedAt = "2026-09-14"; :>> judgedBy = "claudeFable5"; }
        action dcModelAndWriteAreMembers;
        verification dcModelAndWriteAreMembersDoD : Test { :>> id = "623eee38-a085-481c-8e17-4cf319accc97"; :>> method = VerificationMethod::test; :>> procedureText = "Chartered by D0479. Two members: keel-model (corpus, indexer, algo, binding, gitfacts, queries, orient - the read model) and keel-write (write, scaffold, reverify, claim, intake_write - the write API), each depending only on leaf members and, for keel-write, on keel-model. lib.rs re-exports under the old paths. Known-positive, chosen before the tree is read: an edit to view/mod.rs rebuilds neither member (cargo build --verbose shows both Fresh); an edit to write.rs rebuilds keel-write and keel-cli but not keel-model. Known-negative: the full set passes, keel --help byte-identical, no crate:: reference in either member names a module outside it."; }
        // RAN: // RAN: DoD of dcModelAndWriteAreMembers at 0e9f499. members/keel-fs (fsx), members/keel-model (corpus, ident, textscan, gitfacts, indexer, done, binding, evidence, fingerprint, model, queries, claims, suspect, algo, activation, orient), members/keel-write (write, scaffold, reverify, claim, intake_write) exist; Cargo.toml deps: keel-write -> keel-model + leaves, keel-model -> leaves only (python scripts/modgraph.py --check exit 0, 74 modules, 212 edges). Known-positives: cargo build --verbose after touching keel-cli/src/view/mod.rs -> keel-fs, keel-model, keel-write Fresh (probe-view.log); after touching members/keel-write/src/write.rs -> keel-model, keel-fs Fresh (probe-write.log). Known-negatives: keel --help cmp pre-move render IDENTICAL (14593 bytes); guards: 75 (66 hard-blocking, 9 warning-only) unchanged; no crate:: reference in a member names a module outside it (cargo build --release exit 0 under deny(warnings)); keel verify . pass, every rung green in 626 s, touched 880 passed 0 failed (.keel/metrics/verify-receipt.toml, .keel/metrics/touched-receipt.toml, head 0e9f499).
        part dcModelAndWriteAreMembersDoDR1 : TestResult { :>> id = "dd12bee4-24dd-4e93-af09-4f6e7dd895dd"; :>> outcome = VerdictKind::pass; :>> judgedAgainst = "0e9f499"; :>> judgedAt = "2026-09-14"; :>> judgedBy = "claudeFable5"; }
        action dcArchDriftDropsSupersededElements;
        verification dcArchDriftDropsSupersededElementsDoD : Test { :>> id = "40ab1f92-e9c4-4678-982f-a5c343cd68dd"; :>> method = VerificationMethod::test; :>> procedureText = "Resolves issue556. Chartered by D0479: the second extraction (sprint 718) followed four moved CodeElements with successor elements and #Supersede edges (D0108), and arch drift kept reading the retired element's old path as MISSING. arch_model (keel-cli/src/view/mod.rs) drops every #Supersede target before it compares the registry to the tree, so a retired element is history, not drift, and its successor carries the path. Known-positive, chosen before the tree is read: a registry holding one superseded element and its successor reports the successor only (test a_superseded_element_leaves_the_registry_and_its_successor_stays). Known-negative: keel show arch drift on this tree names no MISSING line for keel-cli/src/{write,claim,view/mod}.rs's retired elements."; }
        // RAN: // RAN: cargo test --release -p keel-cli --lib a_superseded_element_leaves_the_registry -> 1 passed 0 failed (the registry holding one superseded element and its successor reports the successor only); keel show arch drift . at 0e9f499 working tree -> 0 MISSING lines, 14 UNAUDITED (catalogued, never hashed), none of them the four superseded claudeOpus5 elements whose files moved to members/ in sprint 718.
        part dcArchDriftDropsSupersededElementsDoDR1 : TestResult { :>> id = "26972c75-bead-477c-a49d-57ebef16607b"; :>> outcome = VerdictKind::pass; :>> judgedAgainst = "0e9f499"; :>> judgedAt = "2026-09-14"; :>> judgedBy = "claudeFable5"; }
        action dcRecordIssueRefusesANonResolverKind;
        verification dcRecordIssueRefusesANonResolverKindDoD : Test { :>> id = "b26a8e9e-3a92-4f89-88e9-8dd8f5f91569"; :>> method = VerificationMethod::test; :>> procedureText = "Resolves issue558. `record issue --resolver` reads the resolver-kind guard's own predicate (guards::resolver_kind_holds, the one home for 'a resolver is a declared action or a Decision') before it writes the #Resolves edge, and refuses any other item kind with the kind it saw and the guard it stands in for; before this the write checked only that the item existed and printed 'triaged on arrival' for an edge the commit gate then refused. Known-positive, chosen before the tree is read: a fixture Story named as resolver exits 2 with nothing written (test a_story_resolver_is_refused_before_anything_is_written). Known-negative: a fixture action and a fixture Decision are both accepted (an_action_and_a_decision_are_both_accepted), and every existing #Resolves edge in this tree still passes the guard."; }
        // RAN: // RAN: cargo test --release -p keel-cli --test record_issue_refuses_a_non_resolver -> 2 passed 0 failed: a_story_resolver_is_refused_before_anything_is_written (fixture Story named as --resolver exits 2, stderr names 'is a Story, not a declared action or a Decision' and 'resolver-kind', 0 Issues written) and an_action_and_a_decision_are_both_accepted (fixture action and Decision both exit 0, 2 Issues written); keel record issue --resolver dcRecordIssueRefusesANonResolverKind on this tree -> recorded issue558 (the action kind, accepted). guards::resolver_kind and main.rs cmd_record_issue both call guards::resolver_kind_holds.
        part dcRecordIssueRefusesANonResolverKindDoDR1 : TestResult { :>> id = "b1ddc436-cad0-4219-87ec-4e4105abfb8f"; :>> outcome = VerdictKind::pass; :>> judgedAgainst = "0e9f499"; :>> judgedAt = "2026-09-14"; :>> judgedBy = "claudeFable5"; }
        action dcInstrumentAnswersCarryTheirSourceHash;
        verification dcInstrumentAnswersCarryTheirSourceHashDoD : Test { :>> id = "1c786bc5-a0fc-4ea0-ad68-65e95f404009"; :>> method = VerificationMethod::test; :>> procedureText = "Resolves issue560. Sprint 719 edited scripts/exec_brief/facts.py (twelve anchors resolved through scripts/module_home.py) and never ran it; the brief was built from the previous run's facts.json at 15a8330 and the edits died at HEAD the next time facts.py ran - module_home('lib') is ambiguous by construction (every crate has a lib.rs) and _src had been removed with two uses left. DO (D0047, a control not a reminder): (1) artefact.finish_json takes sources=[...] and writes each file's sha256 under instrument.sources; artefact.require_complete recomputes them and refuses an answer whose instrument has since changed or is missing, and refuses an answer whose tree is not the HEAD the reader stands on unless KEEL_ARTEFACT_ANY_TREE is set; facts.py passes its three sources; (2) module_home takes crate= and refuses a bare resolution of a module every crate has (lib, main), and its probe scan flags a bare _mh('lib')/module_home('main') call in scripts/**/*.py and .engine/tools/*.py the way it flags a keel-cli/src anchor. Known-positive/known-negative pairs, chosen before the tree is read, in both probes (artefact.py --probe: edited source refused, unchanged accepted, other-tree refused, historical read allowed; module_home.py --probe: bare lib refused, crate= resolves, scan catches _mh('lib') and passes _mh('lib', crate=...)). Done means: both probes exit 0 on this tree; python scripts/exec_brief/facts.py exits 0 at HEAD with complete true and instrument.sources of three entries; the builder for the twenty-ninth publish reads that file through require_complete"; }
        // RAN: RAN at 63221a8 (the tree holding the two uncommitted backlog/issue edits, code unchanged since ecc393e): python scripts/artefact.py --probe -> exit 0, 'artefact probe: 0 failure(s)'; python scripts/module_home.py --probe -> exit 0, 'module_home probe: 0 failure(s)'; python scripts/exec_brief/facts.py -> exit 0, document complete True, tree 63221a8, instrument.sources 3 entries; the twenty-ninth builder (scripts/exec_brief/build_2026_09_14_sample_fork_and_needs.py) reads its facts through artefact.require_complete (sprint 720 story DoD, storyInstrumentAnswersCarryTheirSourceHashDoDR1 at ecc393e). The item's own DoD was left unrecorded when the sprint closed - recorded now from a fresh run, not from the sprint's receipt.
        part dcInstrumentAnswersCarryTheirSourceHashDoDR1 : TestResult { :>> id = "16fbf829-56e4-4b35-ab4e-70d070ff346d"; :>> outcome = VerdictKind::pass; :>> judgedAgainst = "63221a8"; :>> judgedAt = "2026-09-14"; :>> judgedBy = "claudeFable5"; }
        action dcVerifyReceiptSaysRunning;
        verification dcVerifyReceiptSaysRunningDoD : Test { :>> id = "c1bc6b86-16bf-45f2-970f-61404abd8539"; :>> method = VerificationMethod::test; :>> procedureText = "DONE MEANS: the verify receipt (.keel/metrics/verify-receipt.toml) says the truth at every moment of a ladder run - `keel verify` REPLACES the previous receipt with a stub `outcome = 'running'` carrying THIS run's head, the probe pair and an `at` of launch BEFORE the first rung starts, appends each rung's verdict as it lands, and writes the final outcome and stopped_at over it when the ladder ends; a reader during the run, or after a killed one, sees `running` and the rungs finished so far, never the last run's verdict. This is D0387's control (issue399: the suite receipt; issue468: the touched receipt) applied to the third receipt it was not applied to - the same per-file gap that fired twice before (issue322 pattern), so the DoD also names the guard: a unit test over every receipt writer in the crate asserts a Phase::Running render exists, so a fourth receipt cannot ship without one. Resolves issue565: on 2026-09-15 the sprint 721 verifier read verify-receipt.toml while its own ladder was in the touched rung and reported the PREVIOUS run's `outcome = fail, stopped_at = probe` (at 1789476754, 1601 s before its launch) as this run's, then quit; the ladder finished green (773 s, 835 passed) with no reader, and the primary had to resume the verifier by hand. VERIFY: render with Phase::Running yields outcome running, the launch at, the rungs so far and no pass (the known-positive); Phase::Done yields the verdict (the known-negative); the writer census test names verify, touched and suite; a live `keel verify` leaves a `running` receipt on disk during the clippy rung."; }
        // RAN: cargo test --release --lib verify:: -> test result: ok. 9 passed; 0 failed (a_receipt_mid_run_says_running_and_a_finished_one_says_its_verdict, every_receipt_writer_with_an_outcome_renders_a_running_form, the_census_names_a_writer_without_running_and_passes_one_with_it among them) // RAN: cargo clippy --release --all-targets -> exit 0 // RAN: keel verify . --probe ... (keel-serve.exe, detached) -> verify-receipt.toml read 8 s after launch: outcome = 'running', running = 'validate', at = launch epoch, 0 [[rung]] rows; read during clippy: running = 'clippy' with validate and guard passed; a killed run left running = 'touched'; final: head 222a8d8 outcome = 'pass' running = 'none' seconds = 156, five rungs pass // RAN: git commit (post-commit touched set) -> touched-receipt.toml head 6439757 outcome = 'pass' passed = 648 failed = 0 seconds = 232 Delivered at 6439757: Ladder.in_flight + outcome(); climb progress callback writes the receipt before every rung; render emits running = <rung|none>; parse reads a missing running key as finished; help names the form. Census test over every .keel/metrics/* RECEIPT writer that renders an outcome (suite.rs, touched.rs, verify.rs), probed on a fabricated writer without the word. Resolves issue565.
        part dcVerifyReceiptSaysRunningDoDR1 : TestResult { :>> id = "64990906-3841-4ffe-a05b-13f1b92b7a24"; :>> outcome = VerdictKind::pass; :>> judgedAgainst = "6439757"; :>> judgedAt = "2026-09-15"; :>> judgedBy = "claudeFable5"; }
        action dcRetroScanIsCheckedAtTheWrite;
        verification dcRetroScanIsCheckedAtTheWriteDoD : Test { :>> id = "6c0554b7-669b-4e97-9343-ffd876a9dbe2"; :>> method = VerificationMethod::test; :>> procedureText = "DONE MEANS: `keel record gate-result` on a gate whose Test name contains RetroGate REFUSES when the Test's procedureText carries none of the ceremony guard's SCAN_EVIDENCE terms, naming the terms and the Test - the scan requirement (issue011) is checked at the write, by the actor who can satisfy it, not one commit later by a guard the recorder cannot answer; the ceremony guard's violation line names the Test's procedureText as the surface it read ('Retro Test <name> records no avoidable-issue scan in its procedureText'), never the result; and the SCAN_EVIDENCE list has one home both the write and the guard read. Resolves issue566 and discharges obligationda53d7d0: on 2026-09-15 the sprint 721 retro Test lacked the wording, the recorder's write was accepted, the guard went red naming the result, and a second gate-result appeared for the same gate outside the recorder's report - the red was discharged by hand in the Test text. VERIFY: a retro Test without the terms is refused at the write with the term list in the message (known-positive); one with 'avoidable issues scanned' in its procedureText is recorded (known-negative); the guard's message on a legacy red names the Test; one constant is referenced from both sites."; }
        // RAN: dcRetroScanIsCheckedAtTheWrite delivered by sprint 723 (story storyRetroScanIsCheckedAtTheWrite). Evidence is the sprint's DoD result and six gate results, recorded by the D0425 RECORDER from the VERIFIER's receipt: keel verify . --probe pair green through touched; cargo test --release -p keel-write --lib 47 green incl. a_retro_gate_result_is_refused_while_its_test_records_no_scan; guards::tests 24 green; census 9 green incl. every_live_row_has_a_refusal_and_every_refusal_a_row; clippy clean; live refusal ledgered append-gate-result:retro-scan. Resolves issue566; discharges obligationda53d7d0 (computed).
        part dcRetroScanIsCheckedAtTheWriteDoDR1 : TestResult { :>> id = "2e9fb691-8c46-4eef-8f08-6941129b0d87"; :>> outcome = VerdictKind::pass; :>> judgedAgainst = "6439757"; :>> judgedAt = "2026-09-15"; :>> judgedBy = "claudeFable5"; }
        action dcRecorderReportAccountsForEveryOwedRecord;
        verification dcRecorderReportAccountsForEveryOwedRecordDoD : Test { :>> id = "745663a0-13a2-4819-b040-5d7e9eddce35"; :>> method = VerificationMethod::test; :>> procedureText = "DONE MEANS: check_report.py (.engine/skills/delegated-ceremony/references, regenerated into .claude by sync-claude) takes --owed N, the count of records the dispatch named, and REFUSES a recorder report whose WROTE: lines plus REFUSED: lines number fewer than N, naming the shortfall (owed 7, accounted 0); with or without --owed it refuses a report with zero WROTE: lines and no REFUSED: line - a recorder dispatched with nothing to write does not exist, so such a report is a recorder that did nothing and said NONE. The recorder brief in SKILL.md passes --owed <count> and the delegated-ceremony process step says so; the D0388 pair joins PAIRS as fixtures (sprint 723's own three-line report refused naming zero writes; the same report with seven WROTE lines under --owed 7 passes; six WROTE lines under --owed 7 refused naming the shortfall). The change to check_report.py is an enforcement change and carries its own co-committed Decision (D0209 cl.2, D0473 shape), a process-change held for the human. Resolves issue568."; }
        // RAN: RAN: python .engine/skills/delegated-ceremony/references/check_report.py --probe --root . -> exit 0, 'probe: every pair holds.' (8 pairs: 5 known-positive refused, 3 known-negative pass; sprint 723's three reports among them: positive-sprint723-nothing-written refused naming zero WROTE lines with and without --owed 7, negative-sprint723-seven-owed passes under --owed 7, positive-sprint723-six-of-seven refused 'owed 7, accounted 6') // RAN: keel-serve.exe verify . --probe '<check_report --probe positive-sprint723-nothing-written.txt>,<check_report --probe negative-sprint723-seven-owed.txt>' -> outcome=pass stopped_at=none (validate, guard, clippy, probe, touched 839 passed 0 failed) at head ebac62f, the VERIFIER's third receipt // RAN: sync-claude --check -> claude-surface matches (the .claude copy of check_report.py and SKILL.md byte-identical to .engine) // RAN: the D0425 RECORDER wrote sprint 724's seven records under --owed 7 and check_report.py passed its report: 'every one of the 7 owed records accounted for' - the first ceremony recorded under the control this item adds
        part dcRecorderReportAccountsForEveryOwedRecordDoDR1 : TestResult { :>> id = "03e6bfc3-6392-4d91-bdda-54a029287fec"; :>> outcome = VerdictKind::pass; :>> judgedAgainst = "ebac62f"; :>> judgedAt = "2026-09-15"; :>> judgedBy = "claudeFable5"; }
        action dcTouchedRunIsExclusive;
        verification dcTouchedRunIsExclusiveDoD : Test { :>> id = "3e38013f-2647-4553-bbec-3950da8c93d7"; :>> method = VerificationMethod::test; :>> procedureText = "DONE MEANS: one touched run at a time per tree. The D0387 running stub of .keel/metrics/touched-receipt.toml (and verify-receipt.toml) carries `pid`, the process that wrote it; `keel suite --touched` and `keel verify` READ the stub before writing their own and REFUSE (exit 2, nothing written, no cargo started) while it says running and that pid is alive, naming the pid and its `at`; a stub whose pid is gone is a killed run and is replaced as today. Known-positive, chosen before the tree is read: a stub saying running with the current process's own pid - a second launch is refused. Known-negative: a stub saying running with a pid no process holds (pid 1 on Windows, or a spawned-and-exited child) - the launch proceeds and the stub is replaced. Resolves issue569: sprint 724's verifier launched the ladder twice two seconds apart; the two touched runs raced on the receipt rename (verify-touched.out line 536, `receipt could not be written`) and on the lib tests' fixed temp dirs, and the receipt reported five reds of which none holds alone (58/58 keel-write and keel-actor lib tests pass in one run). The refusal is a control on the launch, so a verifier that double-launches gets a receipt line naming it instead of a red no test caused."; }
        // RAN: // RAN: cargo test --release --manifest-path keel-cli/Cargo.toml --lib -- touched:: verify:: -> test result: ok. 31 passed; 0 failed (scratchpad lib725.log); includes the D0388 pairs a_second_launch_is_refused_while_the_stub_writer_is_alive / a_stub_whose_writer_is_gone_is_replaced in touched.rs and a_second_ladder_is_refused_while_the_stub_writer_is_alive / a_stub_whose_writer_is_gone_is_replaced in verify.rs // RAN: cargo clippy --release --manifest-path keel-cli/Cargo.toml --all-targets -- -D warnings -> clean (scratchpad clippy725.log) // RAN: live check on the built binary - .keel/metrics/touched-receipt.toml planted as a running stub with pid 14680 (explorer.exe, alive); ./target/release/keel-serve.exe suite --touched -> exit 2, stderr 'a touched run is already in flight - .keel/metrics/touched-receipt.toml says running, written by pid 14680 at ... REFUSING to launch a second ... (issue569)'; stub byte-unchanged; tasklist showed zero cargo processes; the real receipt restored byte-equal (scratchpad live-pos.log, touched-receipt.bak) // RAN: ./target/release/keel-serve.exe verify --help / suite --help -> both name the pid and the exit-2 refusal (issue569)
        part dcTouchedRunIsExclusiveDoDR1 : TestResult { :>> id = "cff9108f-4c84-477e-8912-f598a91a2a40"; :>> outcome = VerdictKind::pass; :>> judgedAgainst = "ea02af5"; :>> judgedAt = "2026-09-15"; :>> judgedBy = "claudeFable5"; }
        action dcClippyLintsTheOtherHostsCfg;
        verification dcClippyLintsTheOtherHostsCfgDoD : Test { :>> id = "690fd4db-efba-4264-b204-fb9bf795ade2"; :>> method = VerificationMethod::test; :>> procedureText = "DONE MEANS: the D0476 ladder's clippy rung lints the code CI compiles, not only the code this host compiles. `keel verify` runs `cargo clippy --release --all-targets -- -D warnings` a second time with `--target x86_64-unknown-linux-gnu` (the triple ci.yml's ubuntu runner lints) whenever the host is not that triple, so every `#[cfg(not(windows))]` / `#[cfg(unix)]` body is linted before the commit instead of after the push; the receipt's clippy rung row names both commands. A host without the Linux std installed (`rustup target list --installed` lacks it) is a RED rung naming `rustup target add x86_64-unknown-linux-gnu`, never a skipped one - the rung is honest about what it could not lint (D0098). Known-positive, chosen before the tree is read: eb82b52's touched.rs:662 (`.status().map(|s| s.success()).unwrap_or(false)` under `#[cfg(not(windows))]`) run through the rung is red with `clippy::map_unwrap_or`, the lint CI reported. Known-negative: the same file after the `is_ok_and` correction climbs the rung green under both triples. Resolves issue572: local clippy and the VERIFIER's clippy passed sprint 725 while CI's Linux clippy failed it, because the failing line sits in a cfg branch the Windows host never compiles."; }
        // RAN: TOUCHED RECEIPT: outcome=pass passed=854 failed=0 stems=[init, scaffold, verify] lib=true head=6a493f4 runner=cargo-nextest 0.9.144
        part dcClippyLintsTheOtherHostsCfgDoDR1 : TestResult { :>> id = "f5a1d011-2afb-42fa-a961-7e4298856df8"; :>> outcome = VerdictKind::pass; :>> judgedAgainst = "6a493f4"; :>> judgedAt = "2026-09-16"; :>> judgedBy = "claudeFable5"; }
        action dcSprintPurposeIsNotPrefixed;
        verification dcSprintPurposeIsNotPrefixedDoD : Test { :>> id = "f5d0209e-2560-4ff0-b400-eea49ed0e531"; :>> method = VerificationMethod::test; :>> procedureText = "DONE MEANS: `keel record sprint --fill F` refuses a `purpose` section that begins with `Sprint <N>:` (any spacing, any case) before it writes anything, naming members/keel-write/src/scaffold.rs as the place the prefix is added and the doubled title it would have produced; a purpose that merely CONTAINS the words is accepted. Known-positive, chosen before the tree is read: a fill whose purpose is `Sprint 726: clippy lints CI's triple` exits non-zero with no file written. Known-negative: the same fill with purpose `clippy lints CI's triple` writes the file and its Story title reads `Sprint 726: clippy lints CI's triple (P pts)` once. Resolves issue573: seventeen sprint records carry `Sprint N: Sprint N:` titles because the fill restated the prefix the scaffold adds and nothing refused it."; }
        // RAN: TOUCHED RECEIPT: outcome=pass passed=854 failed=0 stems=[init, scaffold, verify] lib=true head=6a493f4 runner=cargo-nextest 0.9.144
        part dcSprintPurposeIsNotPrefixedDoDR1 : TestResult { :>> id = "0140ea0d-7930-4f69-876e-d6410cfe4e98"; :>> outcome = VerdictKind::pass; :>> judgedAgainst = "6a493f4"; :>> judgedAt = "2026-09-16"; :>> judgedBy = "claudeFable5"; }
        action dcScriptProbesRunBeforeCommit;
        verification dcScriptProbesRunBeforeCommitDoD : Test { :>> id = "4f8bed15-e0c5-4a91-ac55-c516c502a64e"; :>> method = VerificationMethod::test; :>> procedureText = "DONE MEANS: the six `# ci-probe:` scripts CI runs (ci.yml step `script probes`) run from ONE discovery script, `scripts/script_probes.py`, that ci.yml calls and .githooks/pre-commit calls whenever a staged path matches `scripts/**/*.py`; a red probe aborts the commit naming the script and its flag; python missing is GATE CANNOT RUN, never a skip. The script ships its D0388 pair (`--probe`): known-positive is a temp tree with one script whose `# ci-probe: --probe` flag exits 1, reported as `SCRIPT PROBES FAILED` with that path; known-negative is a temp tree with one passing script and one with no marker, reported as `1 script probe(s) passed`. Resolves issue574: two commits reached main red on `scripts/module_home.py --probe` because the script probes had no local runner."; }
        // RAN: outcome=pass passed=847 failed=0 seconds=634 at=1789575907 launch=1789575146 (ok)
        part dcScriptProbesRunBeforeCommitDoDR1 : TestResult { :>> id = "855f4c98-dae9-4608-bbc9-3091a2c9b000"; :>> outcome = VerdictKind::pass; :>> judgedAgainst = "1fc06d2"; :>> judgedAt = "2026-09-16"; :>> judgedBy = "claudeFable5"; }
        action dcVerifyWaitsForItsPid;
        verification dcVerifyWaitsForItsPidDoD : Test { :>> id = "51c6fa18-9e92-4f80-a3b1-286f9ae43cdf"; :>> method = VerificationMethod::test; :>> procedureText = "DONE MEANS: `keel verify --wait ROOT` reads .keel/metrics/verify-receipt.toml; while `outcome = running` and the receipt's `pid` is alive it blocks, printing one line per rung change (`in flight: <rung>, pid N alive, Ns`); when the pid exits it prints the finished receipt's rung table and exits as the ladder did (0 green, the red rung's own code otherwise); a `running` receipt whose pid is dead is reported as `KILLED during <rung>` and exits 2, never as a verdict on either side. The test-verify skill's steps 4 and 5 open with that one command in place of the prose wait, and the CliCommand fact in .engine/cli/commands.sysml names the flag. D0388 pair (pure control over a receipt text and a liveness answer): known-positive is a `running` receipt with a dead pid -> KILLED, exit 2; known-negative is a `pass` receipt -> the rung table, exit 0; and a `running` receipt with a live pid -> in flight, not a verdict. Resolves issue575: the sprint 726 verifier read the stub 17 s after launch and reported a green 718 s ladder as killed."; }
        // RAN: verify . --probe passed: positive test a_running_stub_whose_writer_is_gone_is_killed_not_a_verdict (2240ms), negative test a_finished_receipt_is_the_verdict_and_a_live_writer_is_in_flight (2447ms), suite --touched: pass - 865 passed in 688s
        part dcVerifyWaitsForItsPidDoDR1 : TestResult { :>> id = "315dc68f-57b8-42a7-b13c-911238e4a869"; :>> outcome = VerdictKind::pass; :>> judgedAgainst = "6bdd6be"; :>> judgedAt = "2026-09-16"; :>> judgedBy = "claudeFable5"; }
        action dcUnitTestScratchIsPerProcess;
        verification dcUnitTestScratchIsPerProcessDoD : Test { :>> id = "311180fe-aa6e-4569-953f-be9b494fe8fc"; :>> method = VerificationMethod::test; :>> procedureText = "DONE MEANS: no unit test under keel-cli/src or members/*/src names a scratch directory two processes could share. The twenty-odd `std::env::temp_dir().join(\"<literal>\")` sites (write.rs keel-judge-set, keel-atomic-write-test, keel-k6-{tag}; guards.rs, deck.rs, pm.rs, adoption_check.rs, attestation.rs, onboard.rs, main.rs among them) call one helper that suffixes the literal with the process id, and a census test in the lib reads every src tree and fails on a `temp_dir().join(` whose argument is a string literal with no process-id interpolation - the permanent control (D0047), not a sweep. Known-positive, chosen before the tree is read: a source line `temp_dir().join(\"keel-x\")` in a fixture file - the census names it. Known-negative: `scratch(\"keel-x\")` or `temp_dir().join(format!(\"keel-x-{}\", std::process::id()))` - passes. Resolves issue570: two concurrent lib runs during sprint 724's ceremony produced different failing sets (5 and 3) from shared temp dirs, and every one of the named tests passes alone."; }
        // RAN: LADDER: KEEL verify . -> outcome=pass stopped_at=none
        part dcUnitTestScratchIsPerProcessDoDR1 : TestResult { :>> id = "c0473d2b-787c-4270-8f99-34c470c31def"; :>> outcome = VerdictKind::pass; :>> judgedAgainst = "1ecbef0"; :>> judgedAt = "2026-09-16"; :>> judgedBy = "claudeFable5"; }
        action dcProbePairTravelsInAFile;
        verification dcProbePairTravelsInAFileDoD : Test { :>> id = "2f5103d1-a7b0-4716-b7f7-ea43622d644e"; :>> method = VerificationMethod::test; :>> procedureText = "DONE MEANS: `keel verify` takes `--probe-from FILE` beside `--probe POS,NEG`: the file holds exactly two non-empty lines, the known-positive command then the known-negative, written by the PRIMARY (the actor who chose the check and both cases before reading the tree, D0388) and only NAMED by the verifier; a file with any other line count, an empty line, or both flags given is refused at parse the way `--probe a,` is today, and the receipt's probe rung row names the file and both lines. The verifier brief's pair slot becomes the file's path and the test-verify skill says so. Known-positive, chosen before the tree is read: a file whose two lines are `cargo test ... a_second_launch_is_refused_while_the_stub_writer_is_alive` and `... a_stub_whose_writer_is_gone_is_replaced` climbs the probe rung green and the rung row names both. Known-negative: a one-line file, a three-line file, a file whose second line is blank, and `--probe` beside `--probe-from` are each refused before any rung runs. Resolves issue571: two verifiers in two sprints transcribed the pair wrong into the shell argument (724: the bare checker runs; 725: the test names instead of the cargo command lines), each costing a full re-dispatch and reporting a red no check produced."; }
        // RAN: TOUCHED RECEIPT: outcome=pass passed=871 failed=0 seconds=864 keel suite --touched: pass - 871 passed in 864s over [accept_honours_delegation, acceptance_binds_to_text, adoption_check_can_fail, capability_refusal_bites, charter_must_resolve, control_proof_state_is_computed, control_structure_is_computed, device_bound_taps, disguised_fork_stays_proposed, evidence_goes_through_a_file, federation, flow_cycle_time_from_git, forward_only_cutoff_is_the_projects_own, gate_environment_parity_catches_it, gating_workflow_history_reads_routed_spelling, gesture_citation_is_the_commands, guard_reads_the_working_tree, hook_and_push_controls_actually_fire, indicator_trigger_surfaces_work, init_smoke, instruments_declared_catches_it, judge_set_records_each_item, keystone_sees_renames, land_gate, launcher_controls_actually_fire, lib, library_publish, library_read_side, library_unit_retirement, marker_text_without_marker_holds, migration_fixture_is_realistic, migration_rolls_back, no_green_over_nothing, no_op_writes_lose_nothing, obligation_does_not_lock_the_tree, one_gate_definition, orient_bdd, own_dod_drift_is_suspect, pin_actually_bites, process_removal, prose_flags_read_a_file, push_gate_is_withdrawn, ready_honours_item_dependencies, record_decision_declares_supersedes, reference_copy_is_out_of_the_model, reject_has_a_cli_path, release_checksums_catch_it, remaining_controls_actually_fire, resync_is_not_a_self_modification, reverify_demos_replays_each_receipt, self_build_hooks_leave_the_build_tree, signed_plan_covers_its_steps, standing_consent_at_record_time, standing_words_are_project_local, status_distinguishes_unknown, stop_says_nothing_about_decisions, supersession_is_said_once, surface_states_its_state, touched_tests_run_before_land, tty_accept_cites_the_gesture, unit_identity_survives_republish, untrusted_taint, working_tree_eol, wrapper_resolves_only_the_pin]
        part dcProbePairTravelsInAFileDoDR1 : TestResult { :>> id = "61bd9434-ed21-4cff-9d93-b47782c83ba8"; :>> outcome = VerdictKind::pass; :>> judgedAgainst = "e64feae"; :>> judgedAt = "2026-09-16"; :>> judgedBy = "claudeFable5"; }
        action dcVerifierStopIsNeverABlock;
        verification dcVerifierStopIsNeverABlockDoD : Test { :>> id = "1346d609-64d8-415e-89ac-993fdd38689d"; :>> method = VerificationMethod::test; :>> procedureText = "DONE MEANS: the subagent-stop hook never BLOCKS an agent of type verifier - its receipt is its report and the tree's red is the primary's to fix at the turn gate - and instead ledgers what a verifier must never do: the tree fingerprint at the verifier's start (SubagentStart, else the first fire naming its agent_id) compared to the one at its stop, a difference ledgered refused-class under control verifier:tree-written (beside recorder:tree-red, D0425) so control-census and enforcement-report count it. The agent type recorder keeps its block. The hook registration in .claude/settings.json is regenerated by keel sync-claude from the one home, and the change carries its co-committed #SafetyChange Decision (D0209 cl.2). Known-positive, chosen before the tree is read: a stop payload with agent_type verifier over a tree that differs from the session baseline but not from the verifier's own start returns 0 with no block line and no refused-class ledger line; a verifier whose own fingerprint moved yields one ledger line under verifier:tree-written. Known-negative: a recorder payload over the same red tree still blocks under recorder:tree-red, and a payload with no agent_type keeps the control the gate named. Resolves issue578: sprint 730's verifier stopped over a tree the PRIMARY had left red (the retro placeholder), was blocked six times by in-loop-gate with the instruction to make it green, and rewrote a .tracking record - the one thing the role forbids (delegated-ceremony.sysml dcyVerifierReceipt)."; }
        // RAN: verify . --probe-from pair731.txt: outcome=pass; gate check-engine: .engine instance files validated clean; sync-claude --check: claude-surface matches binary's generator
        part dcVerifierStopIsNeverABlockDoDR1 : TestResult { :>> id = "098bb036-a06d-4561-b429-7af053462a97"; :>> outcome = VerdictKind::pass; :>> judgedAgainst = "ebb0214"; :>> judgedAt = "2026-09-16"; :>> judgedBy = "claudeFable5"; }
        action dcViewIsAMember;
        verification dcViewIsAMemberDoD : Test { :>> id = "92d2dff5-56f4-4eb3-aa0c-56d018ed5f34"; :>> method = VerificationMethod::test; :>> procedureText = "Chartered by D0479. keel-view holds view/ and its nine submodules, govern, pm and arch, depending on keel-model, keel-write and the leaves and on nothing above. Known-positive, chosen before the tree is read: an edit to serve.rs or guards.rs leaves keel-view Fresh; an edit to view/reports.rs rebuilds keel-view and keel-cli only. Known-negative: full set passes, keel --help byte-identical, no upward crate:: reference."; }
        // RAN: RAN: verify . --probe-from pair732.txt: outcome=pass stopped_at=none; validate=pass guard=pass clippy=pass probe=pass touched=pass; first red line: none. TOUCHED RECEIPT: outcome=pass passed=904 failed=0; stems=[arch, census, checks, claude_surface, control_proof, control_structure, corpus, critique, delta, embedded, flow, govern, guard_names, guards, init, knowledge, pm, reports, staleness, stpa_diagram, touched, view]. PROBE PAIR: python scripts/module_home.py view/knowledge guard_names view/control_structure (pass); python neg732.py (pass). gate check-engine: .engine instance files validated clean; sync-claude --check: claude-surface matches this binary's generator (47 registry skill(s)). Primary's own reads before dispatch: keel --help byte-identical to the 397e49c render (cmp); keel version guards: 75; cargo clippy --release --workspace --all-targets -D warnings clean; python scripts/module_home.py --probe: 0 failure(s).
        part dcViewIsAMemberDoDR1 : TestResult { :>> id = "fa7f5d7d-0b05-4d49-b229-576561d70478"; :>> outcome = VerdictKind::pass; :>> judgedAgainst = "397e49c"; :>> judgedAt = "2026-09-16"; :>> judgedBy = "claudeFable5"; }
        action dcGuardsAreMembersPerFamily;
        verification dcGuardsAreMembersPerFamilyDoD : Test { :>> id = "6ba45263-a82d-4455-baa7-10db4d3340ec"; :>> method = VerificationMethod::test; :>> procedureText = "Chartered by D0479 (and prepares D0482). guards.rs (9,415 lines, 75 guards) becomes member keel-guards with one module per guard family (the families guards.md already groups by), each guard's constraint identity beside its code, and the receipt and contentkey modules with it; GUARD_NAMES is assembled from the families so a guard in one home is in all four (issue545's identity check keeps holding). Known-positive, chosen before the tree is read: an edit to one family module rebuilds keel-guards and keel-cli and no other member; keel gate guard --no-receipt . reports the same 75 names in the same order as before the move. Known-negative: every guard's probe pair (D0388) passes unchanged; the full set passes; guards.md's catalogue is regenerated and diff-clean."; }
        // RAN: TOUCHED RECEIPT: outcome=pass passed=904 failed=0 Summary [ 43.510s] 496 tests run: 496 passed, 0 skipped
        part dcGuardsAreMembersPerFamilyDoDR1 : TestResult { :>> id = "d495616d-9820-4391-84fe-e794e75c8f18"; :>> outcome = VerdictKind::pass; :>> judgedAgainst = "f8d3d8d"; :>> judgedAt = "2026-09-17"; :>> judgedBy = "claudeFable5"; }
        action dcOneRepoRootHelper;
        verification dcOneRepoRootHelperDoD : Test { :>> id = "69cf3e3a-b67f-4e24-9207-1970f2ff6512"; :>> method = VerificationMethod::test; :>> procedureText = "Chartered by D0479; resolves the recurrence the members-only scan in touched.rs (sprint 718) now controls only for members/. Nine local `repo_root()` helpers (arch.rs, github.rs, cli_surface.rs, activation.rs, fingerprint.rs, orient.rs, queries.rs, write.rs twice) collapse onto one `keel_fs::test_support::repo_root()` (the first ancestor of CARGO_MANIFEST_DIR holding .git), and keel-cli/src's sixteen remaining cwd-relative test anchors (guards.rs seven, hardening.rs five, process_cmd.rs two, reports.rs and view/mod.rs one each) repoint to it, so the scan `no_member_test_anchors_on_a_cwd_relative_path` widens to keel-cli/src and every later D0479 move inherits no path fix. Known-positive, chosen before the tree is read: the widened scan over a synthetic keel-cli source carrying `Path::new('..')` reports it, and over this tree reports nothing; `grep -rn 'fn repo_root' keel-cli/src members/*/src` names one definition. Known-negative: the sixteen repointed tests pass from a member-style cwd two levels down (`cargo test -p keel-cli --lib` run with the crate directory as cwd is the normal case; the probe runs one of them with cwd set to members/keel-fs), and the full set passes."; }
        // RAN: passed=904 failed=0 seconds=791
        part dcOneRepoRootHelperDoDR1 : TestResult { :>> id = "f2bc3183-e52e-4e7c-a4e0-f412b4af5f62"; :>> outcome = VerdictKind::pass; :>> judgedAgainst = "e3714e3"; :>> judgedAt = "2026-09-17"; :>> judgedBy = "claudeFable5"; }
        action dcSuiteIsAMember;
        verification dcSuiteIsAMemberDoD : Test { :>> id = "5def1f42-f11b-494b-9752-c8e43dfaf347"; :>> method = VerificationMethod::test; :>> procedureText = "Chartered by D0479. keel-suite holds suite, touched, verify, eol and hook_binary - the build-and-test tooling - depending on leaves, keel-write and keel-guards' receipt module. keel-land's binary copy (D0422) builds from it unchanged. Known-positive, chosen before the tree is read: an edit to view/mod.rs leaves keel-suite Fresh; keel verify . and keel suite --touched run and write their receipts with the same shape (the receipt tests pass). Known-negative: full set passes, keel --help byte-identical."; }
        // RAN: LADDER: outcome=pass validate=pass guard=pass clippy=pass probe=pass touched=pass; TOUCHED RECEIPT: outcome=pass passed=880 failed=0
        part dcSuiteIsAMemberDoDR1 : TestResult { :>> id = "a8edf1c5-56b7-421c-a1da-5bdb3631335c"; :>> outcome = VerdictKind::pass; :>> judgedAgainst = "7394a28"; :>> judgedAt = "2026-09-17"; :>> judgedBy = "claudeFable5"; }
        action dcProcessIsAMember;
        verification dcProcessIsAMemberDoD : Test { :>> id = "707834d9-e096-45f0-a15e-8215328564f5"; :>> method = VerificationMethod::test; :>> procedureText = "Chartered by D0479. keel-process holds process_cmd, activation, library, adoption_check, onboard, migrate, workspace, sync, status and currency - the engine's own governance processes - depending on keel-view and below. Known-positive, chosen before the tree is read: an edit to serve.rs leaves keel-process Fresh; keel advance, keel activate and keel show status behave identically on this tree (their integration tests pass). Known-negative: full set passes, keel --help byte-identical."; }
        // RAN: TOUCHED RECEIPT: outcome=pass passed=890 failed=0 seconds=787 at=1789649510 launch=1789648259 (at>launch: ok)
        part dcProcessIsAMemberDoDR1 : TestResult { :>> id = "77a9f744-9540-4dab-b463-408b2a4c205f"; :>> outcome = VerdictKind::pass; :>> judgedAgainst = "01f7ad00"; :>> judgedAt = "2026-09-17"; :>> judgedBy = "claudeFable5"; }
        action dcKeelIssuesIsAMember;
        verification dcKeelIssuesIsAMemberDoD : Test { :>> id = "2a3c463e-0e08-4ce7-8767-5e2f44ae8279"; :>> method = VerificationMethod::test; :>> procedureText = "Chartered by D0480. keel-issues holds the item and issue subset: the record issue / task / story / statement paths lifted out of main.rs and write.rs, intake_write, github_ingest, plan_cover, the resolution computation and the open-issues, intake and dispositions views, depending on keel-view and below and never on keel-process. Known-positive, chosen before the tree is read: cargo tree -p keel-issues names no keel-process and no serve; an edit to process_cmd.rs leaves keel-issues Fresh; the record verbs' CLI facts name the member in their synopsis and cli-surface-declared passes. Known-negative: the record-issue, record-story and github-intake integration tests pass unchanged; full set passes; keel --help byte-identical."; }
        // RAN: outcome=pass stopped_at=none
        part dcKeelIssuesIsAMemberDoDR1 : TestResult { :>> id = "afc755f4-3d4e-4adf-91a6-babfc1582267"; :>> outcome = VerdictKind::pass; :>> judgedAgainst = "9e4e79c6"; :>> judgedAt = "2026-09-17"; :>> judgedBy = "claudeFable5"; }
        action dcServeAndGithubAreMembers;
        verification dcServeAndGithubAreMembersDoD : Test { :>> id = "2af97043-9283-4788-9115-03e8bd953e5f"; :>> method = VerificationMethod::test; :>> procedureText = "Chartered by D0479. keel-serve holds serve, deck, launcher, claude_surface and console_registry, and ci_runs joins keel-github; both depend on the members below and on nothing else above. Known-positive, chosen before the tree is read: an edit to serve.rs rebuilds keel-serve and keel-cli only; the serve and deck integration tests pass. Known-negative: full set passes, keel --help byte-identical."; }
        // RAN: // RAN: keel-serve verify . --probe-from pair738.txt -> outcome=pass stopped_at=none seconds=637 at=1789675650 (validate=pass guard=pass clippy=pass probe=pass touched=pass); PROBE PAIR pos738.py pass, neg738.py pass; TOUCHED RECEIPT outcome=pass passed=745 failed=0 seconds=121 stems=[attestation, ci_runs, console_registry, deck, hardening, init, launcher, readiness, reports, serve, verification]; keel-serve gate check-engine . exit=0; keel-serve sync-claude --check . exit=0 (47 skills) - the verifier's receipt, DISCREPANCIES: NONE
        part dcServeAndGithubAreMembersDoDR1 : TestResult { :>> id = "b63eb76b-7210-40b1-bf3c-f048b785daa7"; :>> outcome = VerdictKind::pass; :>> judgedAgainst = "904ff24c"; :>> judgedAt = "2026-09-17"; :>> judgedBy = "claudeFable5"; }
        action dcSittingReviewIsFinishedByAnalysis;
        verification dcSittingReviewIsFinishedByAnalysisDoD : Test { :>> id = "8e1a74fb-01e0-4f8b-8983-aa2a8ba4a28a"; :>> method = VerificationMethod::test; :>> procedureText = "DONE MEANS: D0510 is accepted by the human and applied in one CR: commit - .engine/skills/sprint-review/SKILL.md phase 4 and its record shape say a sitting review is a Test with method = analysis judged by the AI actor, carrying #Covers edges and listing the outstanding per-item asks by verb (keel accept, keel judge-set, a disposition), with no sentence asking the human to confirm the sitting; sittingReviewVP in .engine/views/viewpoint-registry.sysml moves to surface assurance with concernText 'which sprints has a sitting review presented', so /api/obligations on a served copy no longer returns a sittingReviewVP class and the act tab count drops by the sprints it counted; keel show sitting-coverage keeps its numbers and its 'due' key is renamed or reworded so no field says a human owes a review; the doc-sync rides the same commit (CLAUDE.md lens list, the skill registry, the sprint-closeout skill's sentence pointing at the sitting review). A guard `sitting-review-method` (or a clause of an existing ceremony guard) is red when any Test whose name matches sittingRev or whose title names a sitting review carries method = confirmation and was added after D0510's commit, and is green on the eighty existing ones - probed with the D0388 pair before the tree is read: known-positive a planted `sittingRevProbe : Test { method = VerificationMethod::analysis }` in a fixture is green; known-negative the same fixture with method = confirmation is red naming the Test. Resolves issue597. VERIFY: keel gate validate and check-engine clean, keel gate guard all pass with the count from keel version one higher, the guard's two probe lines in pair form, sync-claude --check clean, and gh run list names the landing commit with conclusion success."; }
        // RAN: // RAN: ./target/release/keel-serve.exe verify . --probe-from pair747.txt -> outcome=pass stopped_at=none seconds=969 at=1789810795 (validate=pass guard=pass clippy=pass probe=pass touched=pass; TOUCHED RECEIPT outcome=pass passed=943 failed=0 seconds=850) - the verifier's receipt, DISCREPANCIES: NONE; keel version -> guards: 77 (68 hard-blocking, 9 warning-only); gate guard -> [guard:sitting-review-method] PASS 7795 scanned, 1 counted-history line, 0 violations; served copy /api/obligations -> 3 classes, no sittingReviewVP, uncountableClasses 0; /api/surfaces -> act 3 viewpoints none sitting, assurance carries sittingReviewVP2; keel land: landed at fc00fb08; gh run list --json conclusion -> fc00fb08 completed success
        part dcSittingReviewIsFinishedByAnalysisDoDR1 : TestResult { :>> id = "28c60cd6-5090-46f2-ad33-4024ee3ce33d"; :>> outcome = VerdictKind::pass; :>> judgedAgainst = "fc00fb08"; :>> judgedAt = "2026-09-19"; :>> judgedBy = "claudeFable5"; }
        action dcHooksAreAMember;
        verification dcHooksAreAMemberDoD : Test { :>> id = "e137937c-5110-4e4c-a646-1a92764d6216"; :>> method = VerificationMethod::test; :>> procedureText = "Chartered by D0479; the first slice of dcKeelCliIsThinDispatch, split out because the hook block is the largest single body in main.rs (1246 lines, keel hook <stop|post-edit|pre-bash|pre-write|config-change|subagent-stop|prompt> plus the override, ledger and recall helpers) and the only one whose tests live in two separate test modules. DONE MEANS: members/keel-hooks/ is a workspace member holding src/lib.rs (the cmd_hook body, its consts and the two hook test modules moved out of main.rs), src/shellcheck.rs and src/proactive.rs (moved from keel-cli/src/); keel-cli/src/ holds neither shellcheck.rs nor proactive.rs and main.rs defines no fn cmd_hook - it imports cmd_hook, ledger_gate, ledger_refused, override_path, override_target, refused_injected_prose, OVERRIDE_TTL_SECS and RECALL_BUDGET from keel_cli::hooks, and find_repo_root / engine_version_skew from keel_cli::workspace, where they now live as keel_process::workspace pub fns because every member that resolves a project from cwd needs them, not the binary alone; cargo tree -p keel-hooks names no keel-cli, keel-serve or keel-issues (the hooks sit below the console and the binary); touching members/keel-hooks/src/lib.rs recompiles keel-hooks and keel-cli only, every other member Fresh; the twenty keel-hooks unit tests and the keel-process workspace tests pass; keel --help is byte-identical to the pre-move capture; scripts/modgraph.py --check and scripts/module_home.py --probe hold and module_home names members/keel-hooks for shellcheck and proactive. The transform is scripts/extract_hooks.py (dry-run default, --apply, idempotent), which prints a reconciliation line before it writes: files moved, slices conserved out of main.rs, fns and consts published, anchored edits. NOT a process change: keel-cli/src/main.rs is outside the enforcement-surface lock (is_enforcement_surface, members/keel-guards/src/lib.rs) and the hook dispatch line Some('hook') => cmd_hook(rest) is unchanged, so every hook fires from the same binary path. D0388 pair: known-positive is pos739.py - the three member files exist, the two keel-cli files do not, main.rs has no fn cmd_hook, the dependency tree excludes the three upper crates, a touch of lib.rs rebuilds exactly keel-hooks and keel-cli with sixteen Fresh members, the member tests pass and help matches the capture; known-negative is neg739.py - plant pub use keel_serve::serve; into members/keel-hooks/src/lib.rs and cargo check -p keel-hooks must fail naming keel_serve as an undeclared crate, then restore the bytes and mtime. Both scripts end with PASS or FAIL and a nonzero exit on FAIL."; }
        // RAN: validate=pass guard=pass clippy=pass probe=pass touched=pass
        part dcHooksAreAMemberDoDR1 : TestResult { :>> id = "3a29b1f0-e58d-4097-9c4a-d3832e51a627"; :>> outcome = VerdictKind::pass; :>> judgedAgainst = "2ffa64b4"; :>> judgedAt = "2026-09-17"; :>> judgedBy = "claudeFable5"; }
        action dcSharedHelpersDescendBelowTheVerbs;
        verification dcSharedHelpersDescendBelowTheVerbsDoD : Test { :>> id = "d1b31d47-346c-448f-a85e-c02213772ce5"; :>> method = VerificationMethod::test; :>> procedureText = "DONE MEANS: the five helper seams every cmd_ body in keel-cli/src/main.rs crosses descend below the members that own the verbs, so that each body's least compiling member is the member owning its computation and the parent item can move the bodies without a second layering pass. (1) Project discovery - Workspace, is_project, missing_project_dirs, require_project, canon, discover, find_repo_root, engine_version_skew and the private walkers git_root, walk and git_known_paths - leaves members/keel-process/src/workspace.rs for members/keel-git/src/projects.rs (keel-git reaches gitx and nothing above it; a second workspace.rs would make module_home('workspace') ambiguous, issue559's resolver); the workspace gate (cmd, gate_cmd, gate_problems, gate_outcome, gate_one, declared_rule_violations, unowned_keystone_events) stays in keel-process and keel_process::workspace re-exports the moved names, so every keel_cli::workspace:: and keel_process::workspace:: path resolves unchanged. (2) The hook ledger writers ledger_gate, ledger_refused, refused_injected_prose, ledger_line (pub, the one line writer) and the private ledger_actor_kind leave members/keel-hooks/src/lib.rs for members/keel-write/src/ledger.rs, and the slow-fire threshold SLOW_FIRE_MS and slow_fire_phases that the line writer reads leave members/keel-view/src/pm.rs for the same file (keel-write gains a keel-perf dependency for the attribution; pm re-exports both, so the writer and the reader share one constant); ledger_fire stays in keel-hooks beside the EMITTED_VERDICT it reads, keel_hooks re-exports the three pub names and imports ledger_line, and keel-hooks stops depending on keel-process (project discovery was its only use). (3) Fork detection - fork_options, NOT_A_FORK, disguised_fork and the tests that exercise them - leaves members/keel-serve/src/deck.rs for members/keel-model/src/textscan.rs beside marker_text_without_marker, and deck re-exports them. (4) walk_longest leaves keel-cli/src/lib.rs for members/keel-fs/src/lib.rs and lib.rs re-exports it. (5) The argument helpers the bodies share - without_flag_values, root_arg, refuse_flag_as_path, flag, prose_flag, prose_args, provenance_date, positional_arg, repo_arg - become member members/keel-args (src/lib.rs under the member lint preamble, depending on keel-git alone), main.rs imports them by name, and keel-cli's lib.rs re-exports keel_args as args. scripts/verb_homes.py is committed: it reads the workspace DAG from every member manifest and lists, for every top-level item of main.rs, the members its body reaches directly and through the main.rs items it calls, and the least members of the DAG that reach them all; --check exits 1 naming any item whose least member is keel-cli or which no member reaches, excluding main, cmd_show and mod tests (the dispatch that stays); --probe runs a known-positive and a known-negative fixture first (D0388). One transform scripts/extract_seams.py (dry-run default, --apply, idempotent, reconciliation line) makes every move; cargo clippy --release --workspace --all-targets -D warnings clean; keel --help byte-identical to the pre-move render; keel version's guard line unchanged; python scripts/modgraph.py --check and python scripts/module_home.py --probe hold; no path under GUARD_SOURCE_FILES or GUARD_SOURCE_DIRS changes. Known-positive: python scripts/verb_homes.py --check on the applied tree exits 1 naming exactly audit_subverb, cmd_audit and cmd_enroll (the three items reaching history, adherence and enroll, keel-cli's own modules until dcTheFourStayingModulesAreMembers moves them) and nothing else, having exited 1 on the tree before the move naming six: those three, and warn_if_paths_are_near_the_limit, print_init_next_steps and cmd_init as unreachable (walk_longest is a pub fn of lib.rs, not a re-export, until seam 4); a member holds a crate it could depend on without widening its reach (the crate reaches neither the member nor anything the member does not, so keel-args is held by every verb-holding member), the table names the addition as keel-write(+keel-args), and the tree before the move gave cmd_accept, cmd_judge_set and cmd_record only keel-serve(+keel-hooks) where the applied tree gives keel-write(+keel-args) and keel-serve(+keel-args); cargo tree -p keel-args names keel-git and no member above it; touching members/keel-args/src/lib.rs recompiles keel-args and its dependents only. Known-negative: a pub use keel_process::workspace planted in members/keel-args/src/lib.rs fails cargo check -p keel-args naming the undeclared crate, lib.rs restored on every path; and verb_homes.py --check against a fixture main.rs whose one fn names keel_serve:: and keel_hooks:: together exits 1 naming that fn."; }
        // RAN: TOUCHED RECEIPT: outcome=pass passed=874 failed=0
        part dcSharedHelpersDescendBelowTheVerbsDoDR1 : TestResult { :>> id = "35936164-ef9e-4746-8280-fc3360ce580f"; :>> outcome = VerdictKind::pass; :>> judgedAgainst = "b93cb8de"; :>> judgedAt = "2026-09-17"; :>> judgedBy = "claudeFable5"; }
        action dcTheFourStayingModulesAreMembers;
        verification dcTheFourStayingModulesAreMembersDoD : Test { :>> id = "8b7185a3-a73c-437a-84ef-011268596080"; :>> method = VerificationMethod::test; :>> procedureText = "DONE MEANS: the four modules still in keel-cli/src beside main.rs and lib.rs move to the members that own them, so keel-cli/src holds main.rs and lib.rs only and no module there exceeds 400 lines. cursor.rs (keel advance, the process cursor) and enroll.rs (keel enroll, the actor-enrollment process) become members/keel-process/src/cursor.rs and enroll.rs; adherence.rs (keel audit adherence) and history.rs (keel audit history), the two audits that re-derive the gate verdict from the git tree by running the guards, become members/keel-guards/src/adherence.rs and history.rs. keel-cli's lib.rs re-exports the four at their old paths so every keel_cli::cursor:: / adherence:: / enroll:: / history:: path resolves. adherence.rs is a locked path: GUARD_SOURCE_FILES in members/keel-guards/src/enforcement.rs names keel-cli/src/adherence.rs and the move puts it under GUARD_SOURCE_DIRS (members/keel-guards/src/), so the file entry is retired from GUARD_SOURCE_FILES, the is_enforcement_surface test asserts the new path locked and the old path not, history.rs becomes locked by the directory it enters, and the change carries a process-change Decision held for the human (D0209 clause 2) before it lands. One transform (dry-run default, --apply, idempotent, reconciliation line) makes the moves; cargo clippy --release --workspace --all-targets -D warnings clean; keel --help byte-identical to the pre-move render; python scripts/modgraph.py --check and python scripts/module_home.py --probe hold and module_home names the four new homes. Known-positive: ls keel-cli/src lists exactly lib.rs and main.rs; keel_guards::is_locked_path(members/keel-guards/src/adherence.rs) and (members/keel-guards/src/history.rs) are true and (keel-cli/src/adherence.rs) is false; the moved test modules pass in their new crates (cargo test -p keel-process --lib, -p keel-guards --lib); keel --help equals the pre-move capture. Known-negative: a weakening of the guard set planted in a scratch clone with adherence.rs in its new home is still refused by keel audit adherence naming the vanished guard - the audit re-derives the same verdict from its new crate."; }
        // RAN: // RAN: ls keel-cli/src -> lib.rs main.rs (two files; main.rs 4509 lines - the clause 'no module there exceeds 400 lines' holds for lib.rs (131) and NOT for main.rs, whose size is dcKeelCliIsThinDispatch's DoD (under 800) and is stated here rather than passed silently) // RAN: cargo test --release -p keel-guards --lib -> 9 passed (adherence::tests x6, history::tests x2, enforcement_surface_locks_workflows_hooks_and_guard_source); cargo test --release -p keel-process --lib -> 11 passed (cursor x7, enroll x4) // RAN: cmp help_pre748.txt help_post748.txt -> identical (148 lines); keel version -> guards: 77 (68 hard-blocking, 9 warning-only), unchanged // RAN: cargo clippy --release --workspace --all-targets -- -D warnings -> exit 0; scripts/modgraph.py --check -> exit 0 (74 modules); scripts/module_home.py --probe -> 0 failures, names members/keel-guards/src/{adherence,history}.rs and members/keel-process/src/{cursor,enroll}.rs; scripts/verb_homes.py --check -> 129 items, 0 that only keel-cli can hold, exit 0 // RAN: scripts/extract_staying_modules.py (dry-run) then --apply then a second --apply -> 'already applied: members/keel-guards/src/adherence.rs exists'; reconciliation: 4 files, 19 crate:: refs each rewritten; text equal modulo the rewrites; 10 anchored edits in 6 files // RAN: scratch clone (core.longpaths=true, status clean, one staged path: .engine/rules/guard-constraints.sysml line 27 'constraint def ceremony;' removed, commit --no-verify, stat '1 file changed, 1 deletion(-)') -> keel audit adherence: guard:ceremony: blocking/bound/core -> absent; guardstate:ceremony: warning/active -> absent; audit-adherence: FAIL - 1 unsigned weakening(s); exit 1 // RAN: keel land: touched tests pass - 929 passed in 720s; keel land: landed. (e6b2eed7 merged as 26f5a175); gh run list --json conclusion -> 26f5a175 completed success
        part dcTheFourStayingModulesAreMembersDoDR1 : TestResult { :>> id = "6cd43586-647b-456b-8bc1-5748944e4737"; :>> outcome = VerdictKind::pass; :>> judgedAgainst = "26f5a175"; :>> judgedAt = "2026-09-19"; :>> judgedBy = "claudeFable5"; }
        action dcKeelCliIsThinDispatch;
        verification dcKeelCliIsThinDispatchDoD : Test { :>> id = "04d951a5-8771-4f31-8c5e-ea532d30d219"; :>> method = VerificationMethod::test; :>> procedureText = "Chartered by D0479. main.rs shrinks to argument dispatch: every cmd_* body moves into the member that owns its verb - the one python scripts/verb_homes.py --by-member names, adding keel-args to that member's manifest where the table says (+keel-args) - and lib.rs is the list of re-exports. One transform (dry-run default, --apply, idempotent, reconciliation line) makes the moves, and its plan asserts that the line preceding every slice start is neither a doc line nor an attribute, printing the count checked on the reconciliation line, so a slice that would strand a doc comment fails the dry run (issue601: sprints 739 and 740 each reattached docs stranded by earlier slices by hand). Known-positive, chosen before the tree is read: python scripts/verb_homes.py --check exits 0 on the applied tree (no item's least member is keel-cli), and a fixture main.rs whose one slice starts on the line after a /// line fails the transform's dry run naming that line; wc -l keel-cli/src/main.rs is under 800 and keel-cli/src holds no module over 400 lines; an edit to any single member rebuilds that member, its dependents and keel-cli only, read from cargo build --verbose. Known-negative: keel --help is byte-identical to the pre-pass render, cli-surface-declared passes, the full set passes, and the touched set for a one-member edit (D0481) is that member's binaries and its dependents'."; }
        // RAN: LADDER: passed=963 failed=0
        part dcKeelCliIsThinDispatchDoDR1 : TestResult { :>> id = "167da450-44eb-48d3-846f-bd4c58ba059d"; :>> outcome = VerdictKind::pass; :>> judgedAgainst = "9453faf5"; :>> judgedAt = "2026-09-19"; :>> judgedBy = "claudeFable5"; }
        action dcVerifierReceiptOutcomeIsRenderedNotTyped;
        verification dcVerifierReceiptOutcomeIsRenderedNotTypedDoD : Test { :>> id = "13808fb5-5a0f-490e-9ceb-3f2cdc941b38"; :>> method = VerificationMethod::test; :>> procedureText = "The test-verify receipt's verdict lines are RENDERED from the receipt files, never typed by the agent: scripts/verify_receipt.py reads .keel/metrics/touched-receipt.toml (outcome, passed, failed, failing, seconds, log) and the guard/validate/check-engine exit codes it is given, and emits the receipt's RESULT block; the skill's procedure runs that script and forbids editing the block, and the DISCREPANCIES line is computed as the diff between the DoD's claims and those fields. D0388 pair in the script's --probe: a toml with outcome = fail and two failing names renders FAIL naming both; a toml with outcome = pass renders PASS with the count. Resolves issue490. ALSO (issue567, sprint 723): a receipt whose outcome = running has two readings - in flight, or killed - and the script reads the observable that separates them instead of the agent guessing: while any keel-serve.exe, keel.exe or cargo.exe process is alive it emits one line, WAIT: ladder in flight (<rung>, <seconds> s), exit 2 and NO RESULT block; only when the receipt says running and no such process is alive does it render KILLED at <rung>, naming verify-launch.epoch and the receipt's at. The skill's step 5 runs the script in a wait loop until it exits 0 or renders KILLED; the pair in --probe carries running+alive (WAIT) and running+none (KILLED) beside the fail and pass cases. Resolves issue567."; }
        // RAN: DISCREPANCIES: NONE
        part dcVerifierReceiptOutcomeIsRenderedNotTypedDoDR1 : TestResult { :>> id = "336a93e6-85d9-40da-b094-55d70ae8693f"; :>> outcome = VerdictKind::pass; :>> judgedAgainst = "b7289c4d"; :>> judgedAt = "2026-09-19"; :>> judgedBy = "claudeFable5"; }
        action dcTouchedSetDescendsTheWorkspace;
        verification dcTouchedSetDescendsTheWorkspaceDoD : Test { :>> id = "a17e142b-9b93-4b4d-b41e-059e4f7d97ed"; :>> method = VerificationMethod::test; :>> procedureText = "Chartered by D0481. touched.rs computes the candidate set over the workspace graph read from the Cargo manifests (changed members plus dependents), and each self-reading test binary keys on the read set the test support layer recorded when it last ran, hashed with its member's code; a binary with no recorded read set falls back to D0474's tree key. Known-positive, chosen before the tree is read: a fixture workspace with three members where only the leaf changes yields a candidate set of the leaf and its dependent and not the third; a fixture receipt with a recorded read set stays green across an edit to a path outside that set and goes stale on an edit inside it. Known-negative: the D0474 tests for the fallback keys pass narrowed to the fallback case; the real land at the landing commit runs and writes the receipt with the per-binary read-set field; nothing in the set is skipped without a matching key."; }
        // RAN: LADDER: keel verify . --probe-from pair741.txt: validate=pass guard=pass clippy=pass probe=pass touched=pass
        part dcTouchedSetDescendsTheWorkspaceDoDR1 : TestResult { :>> id = "b3875341-32c5-4929-b7c2-aa75528a8034"; :>> outcome = VerdictKind::pass; :>> judgedAgainst = "d7ffcc82"; :>> judgedAt = "2026-09-18"; :>> judgedBy = "claudeFable5"; }
        action dcSuiteMeasuresTheWorkspace;
        verification dcSuiteMeasuresTheWorkspaceDoD : Test { :>> id = "5466a4f4-6c09-499c-9c4e-04c07ed56cbd"; :>> method = VerificationMethod::test; :>> procedureText = "Resolves issue588. The full suite's fingerprint population (members/keel-suite/src/suite.rs DELIVERABLE_PATHS) and its cargo scope (--manifest-path keel-cli/Cargo.toml) stop at keel-cli, so a member edit leaves the receipt's fingerprint equal and the members' lib tests outside the full run. DONE MEANS: the fingerprint covers every path the workspace compiles - keel-cli, keel-parser, members, .engine, keelw, Cargo.toml, Cargo.lock - read from the root manifest's members list, not a typed constant; keel suite runs cargo test --release --workspace --no-fail-fast (the three cucumber harness = false binaries included, D0475); the receipt's passed count is the workspace's; the staleness message at suite.rs names the member whose edit moved the fingerprint. Known-positive, chosen before the tree is read: a fixture edit under members/keel-fs/src/ changes fingerprint() and staleness() returns the CHANGED message naming it; keel suite on this tree writes a receipt whose passed count exceeds keel-cli's alone by the members' lib totals. Known-negative: an edit under target/ or .keel/ leaves the fingerprint equal; keel suite --touched is unchanged (D0421/D0474 tests pass)."; }
        // RAN: keel suite --touched: pass - 214 passed in 508s
        part dcSuiteMeasuresTheWorkspaceDoDR1 : TestResult { :>> id = "c5364b36-f007-467a-b2d9-a3684e261808"; :>> outcome = VerdictKind::pass; :>> judgedAgainst = "019078d3"; :>> judgedAt = "2026-09-18"; :>> judgedBy = "claudeFable5"; }
        action dcSourceCitationsOnTheLivingDocsResolve;
        verification dcSourceCitationsOnTheLivingDocsResolveDoD : Test { :>> id = "b16e8f9a-521b-4843-83d3-40c352500ae5"; :>> method = VerificationMethod::test; :>> procedureText = "Resolves issue591. The living doc surface cites source by path and line (`migrate.rs:664-666` beside `check_preconditions` in .engine/skills/project-migration/SKILL.md) and nothing reads the citation against the tree: the file moved to members/keel-process/src/migrate.rs and the function to lines 805-807 with the prose unchanged, and the skills tree is under the keystone lock (is_process_def), so the one-line fix needs a marked Decision and rode no sprint. DONE MEANS: a guard source-reference, in tool-reference's family and scope (.engine/{processes,skills,docs,contracts,workflows,rules}, CLAUDE.md), reads every `<name>.rs:N` or `<name>.rs:N-M` citation on that surface; the file resolves through the same manifest-driven module home scripts/module_home.py reads (a bare basename resolves when exactly one tracked .rs file bears it), and when a backticked identifier sits on the same line the identifier appears within the cited range; a citation that resolves to no file or whose identifier is outside its range is red naming the doc line and the tree's actual line. Known-positive, chosen before the tree is read: the project-migration skill's line 10 is red under this guard at 01f7ad00 (file moved, range stale) and green once repointed to members/keel-process/src/migrate.rs:805-807. Known-negative: a citation to a file under target/ or to a `.py:N` line is outside the population and neither red nor counted; keel version's guard line rises by exactly one."; }
        // RAN: LADDER: keel verify . --probe-from pair743.txt -> outcome=pass stopped_at=none
        part dcSourceCitationsOnTheLivingDocsResolveDoDR1 : TestResult { :>> id = "13306fd5-0f90-4ce4-891f-f2a2de9b74ea"; :>> outcome = VerdictKind::pass; :>> judgedAgainst = "66f74bd0"; :>> judgedAt = "2026-09-18"; :>> judgedBy = "claudeFable5"; }
        action dcAuthorityQueueListsNeedsAwaitingAcceptance;
        verification dcAuthorityQueueListsNeedsAwaitingAcceptanceDoD : Test { :>> id = "8b124142-845b-49b0-9cf3-8bc3e4d78f47"; :>> method = VerificationMethod::test; :>> procedureText = "Resolves issue661. FOUND 2026-09-19: the three EngineSelfAnalysisNeeds (nKeelIsADefinedSystem, nControlGapsFoundByAnalysis, nVerificationByAuthorityAndMethod), recorded 2026-09-02 from st065 and st066, carried no acceptance Test and no result for seventeen days while ten Decisions (D0425 through D0533) were recorded and eleven sprints delivered against them; keel show authority-queue (members/keel-view/src/view/mod.rs authority_queue) computes decisionAcceptance, findingDisposition and contentionAdjudication and has no kind for a Need awaiting the human's word, so nothing computed showed them waiting, and the Business workflow's ordering rule - no SystemRequirement or architecture Decision until the Needs it serves are accepted - was unobservable. Need acceptance is today a per-file convention: a <set>NeedsAccept confirmation Test whose result is judgedBy a Person, bound to its Needs by #Verify inconsistently (engine-needs binds 1 of 13, modular-members 0 of 8). DONE MEANS: (1) authority-queue gains a needAcceptance row kind - a Need is waiting when no method=confirmation Test with a passing TestResult judgedBy a Person reaches it through a #Verify edge; the row carries the Need's shortName, createdAt, days waiting, and the confirmation Test's name when one reaches it without a passing human result, or the words no acceptance test when none reaches it; (2) the decision-surfacing procedure reads these rows beside decisionAcceptance, so the brief carries them; (3) every existing passing confirmation Test under .tracking/business whose procedureText accepts a set is bound to each Need of that set by a #Verify edge, copy-and-add, edges only - no result is touched, moved or fabricated, and a Need no existing Test's words cover stays a true waiting row; (4) the confirmation-authenticity guard already refuses an AI-judged confirmation result, so the kind needs no new guard. Known-positive, chosen before the tree is read: a fixture Need with no #Verify-linked confirmation Test yields one needAcceptance row naming it with no acceptance test. Known-negative: the same Need reached by a confirmation Test whose passing result is judgedBy a Person yields no row; the same Test with its result judgedBy an ai Actor still yields the row naming the Test. Live, read back from keel show authority-queue at the landing commit: the three self-analysis Needs are rows naming engineSelfAnalysisNeedsAccept, and every Need of the engine-needs and modular-members sets is absent."; }
        // RAN: DISCREPANCIES: NONE
        part dcAuthorityQueueListsNeedsAwaitingAcceptanceDoDR1 : TestResult { :>> id = "ab46239a-1efa-4396-bd16-99b5795a7cb2"; :>> outcome = VerdictKind::pass; :>> judgedAgainst = "c3e4635a"; :>> judgedAt = "2026-09-19"; :>> judgedBy = "claudeFable5"; }
        action dcSprintNamesTheItemItDelivers;
        verification dcSprintNamesTheItemItDeliversDoD : Test { :>> id = "8868d81d-1d92-4a7d-a552-a92b6c2b7b5e"; :>> method = VerificationMethod::test; :>> procedureText = "DONE MEANS: a sprint that delivers a backlog item names it with a typed edge, and the sprint-closure guard reads that edge: once a later sprint exists, every item a closed sprint delivers has a DoD TestResult, or the guard names the item. FOUND 2026-09-14: sprint 720 closed (story DoD pass at ecc393e, closeOut and retro recorded) and dcInstrumentAnswersCarryTheirSourceHash - the item it existed to deliver - had no DoD result, so keel show whats-next ranked it first as READY work at 63221a8; the only link between them was the shared slug in the story name, which no guard reads. The sprint-closure guard checks the story DoD; the charter edge points at the Decision (659 of 659 sprints), never at the item. DO: (1) CR, human sign-off, schema/core relationships.sysml gains #Delivers (work item Story -> backlog action; D0209 cl.2 Decision co-committed, process-change marked); (2) sprint-planning skill and record sprint --fill author the edge at prep beside #CharteredBy; (3) sprint-closure: for each sprint with a later sprint, each #Delivers target whose DoD Test has no TestResult is a violation naming sprint and item; a story with no #Delivers edge on a sprint recorded after the CR's date is a violation too (an unnamed delivery is not a delivery); (4) backfill is NOT done by guessing - sprints before the CR carry no edge and are counted history. Known-positive, chosen before the tree is read: a fixture with sprint N delivering item X (no DoD result) and sprint N+1 present is red naming X; known-negative: the same with X's DoD result is green; the live tree at 63221a8, had the edge existed on sprint 720, would have been red on dcInstrumentAnswersCarryTheirSourceHash. VERIFY: guard unit test carries the pair; keel gate guard green on the tree after the first edged sprint closes."; }
        // RAN: keel suite --touched: pass - 925 passed in 776s over [83 binaries]; slowest land_gate land_refuses_to_push_a_workspace_carrying_a_broken_project 219.8s; 0 failed, failing []; receipt .keel/metrics/touched-receipt.toml
        part dcSprintNamesTheItemItDeliversDoDR1 : TestResult { :>> id = "e2e1ecd8-1cbe-4b8f-80a4-ed744ec8cb59"; :>> outcome = VerdictKind::pass; :>> judgedAgainst = "e5ee275b"; :>> judgedAt = "2026-09-20"; :>> judgedBy = "claudeFable5"; }
        action dcRecorderRefusalCannotCiteTheVerifiersNoWritesLine;
        verification dcRecorderRefusalCannotCiteTheVerifiersNoWritesLineDoD : Test { :>> id = "7c3e2ab0-c214-4f78-a65d-0393fe7ed14d"; :>> method = VerificationMethod::test; :>> procedureText = "Resolves issue590. DONE MEANS: check_report.py (the delegated-ceremony skill's references, both .engine and its generated .claude copy) refuses a recorder report whose REFUSED line cites the verifier receipt's OWED WRITES line as the reason a dispatched record was not written, naming the line and whose writes it counts (the verifier's own, none by design); the test-verify receipt shape labels that line VERIFIER-NOTED WRITES so it cannot read as the recorder's owed count, and the recorder brief in the delegated-ceremony skill says the dispatch's count is the only owed count (D0492); fixtures under references/fixtures: the sprint 735 second recorder's first report (REFUSED citing line 19) and its rewritten report. Known-positive, chosen before the tree is read: the rewritten report with one WROTE line passes --owed 1. Known-negative: the first report, REFUSED citing OWED WRITES: NONE, is refused naming the misread."; }
        // RAN: VERIFIER-NOTED WRITES: NONE
        part dcRecorderRefusalCannotCiteTheVerifiersNoWritesLineDoDR1 : TestResult { :>> id = "f6c22b71-0c41-4e98-ae43-8ce0eb34f500"; :>> outcome = VerdictKind::pass; :>> judgedAgainst = "ea60a425"; :>> judgedAt = "2026-09-18"; :>> judgedBy = "claudeFable5"; }
        action dcRecorderReportAccountsForEveryTreeWrite;
        verification dcRecorderReportAccountsForEveryTreeWriteDoD : Test { :>> id = "39c77ffa-208f-4d68-93ed-c12b0da80025"; :>> method = VerificationMethod::test; :>> procedureText = "Resolves issue602. FOUND 2026-09-18, sprint 741: the dispatch named the eighth owed record as --task dcTouchedSetDescendsTheWorkspaceDoD (the Test's name, not the action's), the recorder's first attempt was refused by the write API, its second attempt with --task dcTouchedSetDescendsTheWorkspace landed dcTouchedSetDescendsTheWorkspaceDoDR1 at .tracking/backlog.sysml, and its report carried that record as one REFUSED line and no WROTE line - eight accounted for, check_report.py --owed 8 passed, and the report's account of the tree was false in the one place it mattered. check_report.py reads only the report; nothing reads the report against the tree it describes. DONE MEANS: check_report.py, given --root, counts the TestResult parts the working tree gained since HEAD under .tracking (git diff HEAD plus untracked .tracking files) and refuses a report whose WROTE lines number fewer than that count, naming the surplus result by its part name and file; the recorder brief says a write that lands after a refused attempt is a WROTE line, never a REFUSED one; fixtures under references/fixtures hold the sprint 741 report and its corrected form. Known-positive, chosen before the tree is read: the corrected report (eight WROTE lines) over a tree with eight new results passes --owed 8. Known-negative: the sprint 741 report as returned (seven WROTE, one REFUSED) over the same tree is refused naming dcTouchedSetDescendsTheWorkspaceDoDR1."; }
        // RAN: validate=pass guard=pass clippy=pass probe=pass touched=pass; outcome=pass passed=918 failed=0
        part dcRecorderReportAccountsForEveryTreeWriteDoDR1 : TestResult { :>> id = "709b96aa-d448-4aff-a5cc-8a691a7e015a"; :>> outcome = VerdictKind::pass; :>> judgedAgainst = "6983116e"; :>> judgedAt = "2026-09-20"; :>> judgedBy = "claudeFable5"; }
        action dcVerifierReceiptIsCheckedAgainstTheLadder;
        verification dcVerifierReceiptIsCheckedAgainstTheLadderDoD : Test { :>> id = "8001b74f-04f4-4fa5-b833-f78d3733baa2"; :>> method = VerificationMethod::test; :>> procedureText = "Resolves issue603. FOUND 2026-09-18, sprint 743: the verifier's receipt said LADDER -> KILLED during touched; exit=2 and DISCREPANCIES: pid 29824 dead, while tasklist showed pid 29824 alive, keel verify --wait . printed in flight: touched, pid 29824 alive, and the verifier's own background --wait later returned 101 - the touched rung's red exit - which its report restated as confirming the kill. The receipt was written from a stub read before the ladder ended and never rewritten; the sprint 726 verifier did the same (issue575), and the control added then was a sentence in the test-verify skill saying to wait. Nothing reads a verifier receipt against the ladder receipt it describes. DONE MEANS: a checker check_receipt.py beside check_report.py under .claude/skills/delegated-ceremony/references (the skill's source under .engine/skills) is given the verifier receipt and --root, runs keel verify --wait ROOT (which returns at once when the ladder has ended and blocks while its pid lives), and refuses the receipt when (a) the ladder is still in flight - the receipt was written early; (b) the receipt's LADDER line says KILLED or running while --wait reports an ended ladder with a verdict, naming the rung and exit --wait printed; (c) the receipt's per-rung verdicts differ from the [[rung]] rows of .keel/metrics/verify-receipt.toml; (d) the receipt's TOUCHED RECEIPT line quotes outcome, passed or failed values other than those in .keel/metrics/touched-receipt.toml when the ladder reached that rung. The verifier brief names the checker as the step before the recorder is dispatched, and the delegated-ceremony process carries it as a gate. Fixtures under references/fixtures hold the sprint 743 receipt as returned and its corrected form. Known-positive, chosen before the tree is read: the corrected receipt (touched fail, 880 passed, 23 failed, stopped_at touched) over the ladder receipts of 1789725917 passes. Known-negative: the sprint 743 receipt as returned (KILLED during touched, exit=2) over the same receipts is refused naming the ended ladder's verdict fail (101) at touched."; }
        // RAN: validate=pass guard=pass clippy=pass probe=pass touched=pass
        part dcVerifierReceiptIsCheckedAgainstTheLadderDoDR1 : TestResult { :>> id = "b54c6520-7d4a-4a28-9a8c-66473f7aa0a8"; :>> outcome = VerdictKind::pass; :>> judgedAgainst = "301b6a71"; :>> judgedAt = "2026-09-20"; :>> judgedBy = "claudeFable5"; }
        action dcGuardsCatalogueNamesTheFamily;
        verification dcGuardsCatalogueNamesTheFamilyDoD : Test { :>> id = "bfbfb04c-02ce-472c-b753-b79adf3a14f9"; :>> method = VerificationMethod::test; :>> procedureText = "Resolves issue584. guards.md groups guards by tier (Hard-blocking, Warning-only, burndown) while the code groups them by family (members/keel-guards/src/<family>.rs, sprint 733); a reader of the catalogue cannot find a guard's file. DONE MEANS: every guard row in .engine/docs/guards.md carries its family, read from the FAMILIES tables, and the doc-guard-count guard (the hard guard that already reads .engine/docs/*.md; doc-sync is warning-only by construction, so it cannot make a red gate - D0539) holds the catalogue's family per guard equal to the table that dispatches it, so a guard moved between family files without its row is a red gate. Known-positive, chosen before the tree is read: a fixture row naming a guard under a family other than its table's fails the guard with the row and both families in the message. Known-negative: the catalogue as regenerated passes; the tier grouping is unchanged."; }
        // RAN: keel suite --touched: pass - 922 passed in 822s over [82 binaries]; 0 failed
        part dcGuardsCatalogueNamesTheFamilyDoDR1 : TestResult { :>> id = "f74d3315-2a14-44cd-a895-b0cb3fbf9b4f"; :>> outcome = VerdictKind::pass; :>> judgedAgainst = "957b2888"; :>> judgedAt = "2026-09-20"; :>> judgedBy = "claudeFable5"; }
        action dcBuildScriptHasOneHomeBelowItsUsers;
        verification dcBuildScriptHasOneHomeBelowItsUsersDoD : Test { :>> id = "9178063a-c11a-477c-9a50-69671698b3db"; :>> method = VerificationMethod::test; :>> procedureText = "Resolves issue585. keel-cli/build.rs (the build-provenance stamp: commit, dirty flag) is the build script of three crates, two of them members reaching UP to it by build = ../../keel-cli/build.rs (keel-write since sprint 714, keel-guards since sprint 733); modgraph does not see build-script edges, so the layering check passes a reach it forbids in source. DONE MEANS: the script lives at one path no crate above its users owns (members/keel-fs/build.rs or a workspace-level build/ directory), every Cargo.toml build = names that path, keel version's commit line is unchanged, and python scripts/modgraph.py --check reads build = edges as dependencies so an upward build script is a layering red. Known-positive, chosen before the tree is read: a fixture Cargo.toml with build = ../../keel-cli/build.rs under members/ fails modgraph naming the edge. Known-negative: the workspace as landed passes; cargo build --release from the root is green and keel version prints the same commit as git rev-parse --short HEAD."; }
        // RAN: verify ladder passed: validate=pass guard=pass clippy=pass probe=pass touched=pass
        part dcBuildScriptHasOneHomeBelowItsUsersDoDR1 : TestResult { :>> id = "9124f81a-ddb0-4045-8963-abbd14246e89"; :>> outcome = VerdictKind::pass; :>> judgedAgainst = "e35fb846"; :>> judgedAt = "2026-09-20"; :>> judgedBy = "claudeFable5"; }
        action dcReceiptStdoutIsHeldToTheLaunch;
        verification dcReceiptStdoutIsHeldToTheLaunchDoD : Test { :>> id = "59b5af4d-2bba-4748-b108-aa207d7d0741"; :>> method = VerificationMethod::test; :>> procedureText = "Resolves issue670. FOUND 2026-09-20, sprint 757: the sprint's third ladder (verify-receipt.toml at=1789928370; touched-receipt.toml passed=718, failed=0, 19 ran rows, seconds=257) was launched without the test-verify skill's redirection (SKILL.md:82 sends the ladder's stdout to .keel/metrics/verify-touched.out), so that file kept the second ladder's stdout - mtime 1789927385, last line keel suite --touched: pass - 496 passed in 215s over eight lib rows, the set before contentkey::is_code gained build/. scripts/verify_receipt.py:303 reads the file with no check against verify-launch.epoch - the touched toml's at is held to the epoch at line 350, the .out is not - and rendered test result line: 496 passed in 215s over [8 binaries] under this run's LADDER line. check_receipt.py holds the receipt's TOUCHED RECEIPT counts to the toml and holds nothing to the .out, so it passed, and the recorder quoted that line as --evidence on six gate results (5c16bc97, 9a923ebe, d631695b, 23f3eb98, 04a56b95, 4d6b35f0): their pass verdicts are the ladder's, their quoted count is another run's. DONE MEANS: (a) verify_receipt.py holds verify-touched.out's mtime to verify-launch.epoch as it holds the touched toml's at - an .out older than the epoch, or absent, renders test result line: STALE (mtime M, launch E) or ABSENT, never a line read from it, and adds a DISCREPANCIES line naming the file and both epochs; (b) check_receipt.py refuses a receipt whose test result line quotes N passed while touched-receipt.toml's passed is not N - the printed line and the toml are one Run (touched.rs:644 prints it, :734 writes it), so a disagreement is a line from another run; (c) the test-verify skill's receipt table and the renderer's docstring say the .out is held to the launch. Known-positive, chosen before the tree is read: a fixture .out with mtime epoch-10 beside a touched toml at epoch+50 renders STALE with a DISCREPANCIES line, and a receipt whose test result line says 496 passed over a toml saying 718 is refused by check_receipt.py naming both counts. Known-negative: an .out with mtime epoch+40 whose last line says 718 passed renders that line with DISCREPANCIES: NONE, and check_receipt.py passes the receipt. Not a process change in the item: the change to the two checkers and the skill is one when worked, and its sprint carries the ProspectiveChange Decision and CR prefix."; }
        action dcFactsAboutARangeReadTheRange;
        verification dcFactsAboutARangeReadTheRangeDoD : Test { :>> id = "b60edc1c-dcd9-4a7c-b17c-cf525b8d125a"; :>> method = VerificationMethod::test; :>> procedureText = "Resolves issue586. A facts.py block that describes a fixed commit range (git diff A B -- FILE) read FILE from the working tree; when the file moved (sprint 733) every fact of the block went null although the range had not changed. Fixed for the D0499 block by reading git show B:FILE; the class has no control. DONE MEANS: scripts/exec_brief/facts.py gains --probe, and one probe scans its own source for a run([git, diff, A, B, --, X]) whose X is also passed to read( or module_home( in the same block, failing with the block's first line; the D0499 block passes it as rewritten. Known-positive, chosen before the tree is read: a fixture block pairing git diff 1ecbef0 50e171a -- P with read(P) is reported. Known-negative: a block whose file text is git show B:P is not; the probe exits 0 on the file as landed."; }
        action dcScriptsResolveModuleHomesFromTheManifest;
        verification dcScriptsResolveModuleHomesFromTheManifestDoD : Test { :>> id = "614e0e37-1dfc-46f8-b2f3-785e87944f0c"; :>> method = VerificationMethod::test; :>> procedureText = "Chartered by D0479; resolves issue559 (the Python side of issue557's class). One resolver, scripts/module_home.py, answers where a Rust module lives by reading Cargo.toml [workspace] members - the one list (D0486) - and every script that opened a .rs file by name uses it: receipt_shape_census.py (reverify.rs, the line that turned CI red at d110d0a), guard_dispatch_order.py and issue400_reproduction.py (guards.rs), guard_proof_census.py (guards.rs, and its corpus widens from keel-cli/src to every member's src), facts.py (cli_facts.rs - silently null since keel-schema took it - guards.rs, lib.rs, and the local helper from sprint 718). The binary's proof census (control_proof.rs corpus_bodies) widens the same way so the two instruments D0360 holds against each other read one corpus. Control (D0047): module_home.py --probe is a CI script probe (D0394) whose scan fails on any path EXPRESSION anchoring a .rs file under keel-cli/src in scripts/**/*.py or .engine/tools/*.py. Known-positive, chosen before the tree is read: in a fixture workspace of two crates a module in one resolves to that file and a directory module through a glob member to its mod.rs; the os.path.join line that broke and the pathlib shape are both caught by the scan; a member's test body naming a guard with an asserted failure is PROVEN in the Rust census only when the root manifest lists the member. Known-negative: a module in no crate is None, in two crates is refused naming both; the resolver call and prose naming the directory pass the scan; the real tree scans clean; every CI script probe passes locally; the binary and the script agree on one tree (test functions scanned, proven, unproven, undetermined all equal)."; }
        action dcScriptProbesRunInTheVerifyLadder;
        verification dcScriptProbesRunInTheVerifyLadderDoD : Test { :>> id = "85c37f41-d6a4-407e-aca3-b7b4dbf6bd73"; :>> method = VerificationMethod::test; :>> procedureText = "Chartered by D0476, whose ladder this extends - a process change, so the working sprint carries its own marked Decision and the item is worked under that acceptance. TODAY the D0394 script probes (every scripts/**/*.py carrying a `# ci-probe:` line) run only in CI, so a script broken by a module move reaches the remote before anything local fires (sprint 718 landing, run 34917362100, issue559). DO: keel verify gains a rung between guard and clippy that discovers and runs the same probes the CI step does, from the same marker, stopping at the first red like every other rung (D0476); the receipt names each probe and its exit. Known-positive, chosen before the tree is read: a fixture script under scripts/ with `# ci-probe: --probe` that exits 1 turns keel verify red at that rung naming the script; known-negative: the current tree's six probes pass and verify is green through the touched set; the CI step and the rung read one discovery function, so a script one runs and the other does not is impossible by construction."; }
        action dcQuotedProbeLineIsRefused;
        verification dcQuotedProbeLineIsRefusedDoD : Test { :>> id = "7c812328-a947-467e-8a46-3df6d63dc607"; :>> method = VerificationMethod::test; :>> procedureText = "Chartered by D0500; resolves issue581. A probe line (either side of --probe, either line of --probe-from) is split on whitespace and run shell-free (verify.rs shell_free), so a quote character in it cannot mean what the author meant: the sprint 732 verifier's negative side was a python -c one-liner whose inner quotes reached the interpreter as separate tokens and failed with a SyntaxError the ladder reported as a red probe. The control: keel verify refuses, before any rung runs, a probe line containing a single or double quote character, naming the line and the rule (a check that needs arguments is a script run by path); the test-verify and delegated-ceremony skills say the same in one sentence each. Known-positive, chosen before the tree is read: a pair file whose second line carries a quoted argument is refused with that message and no receipt is written. Known-negative: sprint 732's final pair file (two bare command lines, one naming a script by absolute path) passes the shape check and the ladder runs."; }
        action dcRecordRefusesAnUnknownFlag;
        verification dcRecordRefusesAnUnknownFlagDoD : Test { :>> id = "b1261347-f62f-4338-b5ac-f6ff65e9b3f2"; :>> method = VerificationMethod::test; :>> procedureText = "Resolves issue551. Every keel record sub-verb (decision, issue, statement, story, sprint, task, result, gate-result, review and the D0451 authoring verbs) refuses an argument beginning with -- that none of its flags consumes, exits 2 naming it as an unknown flag in issue179's shape, and writes nothing; the flag table is the one the usage text renders from, so a flag the usage names is by construction accepted. record decision gains --depends-on dNNNN[,..], authoring the #DependsOn edge with the Decision the way --derived-from and --supersedes do (D0303/D0352), because the swallowed flag was typed for an edge the API had no road to. Known-positive, chosen before the tree is read: record decision --from F --depends-on d0479 --date D on the current binary exits 0 and writes a Decision with no DependsOn edge; after the change the same invocation writes the edge, and --bogus-flag exits 2 with the name in the message and no file written. Known-negative: every invocation in the record demos under [demo] replayable (D0444) still passes."; }
        action dcGuardReceiptsKeyPerGuard;
        verification dcGuardReceiptsKeyPerGuardDoD : Test { :>> id = "586d797a-b0a8-4d7e-846c-87bf84865808"; :>> method = VerificationMethod::test; :>> procedureText = "Chartered by D0482. Every guard declares its input globs beside its constraint identity; the guard receipt records one key per guard (the hash of the matched files); keel gate guard re-runs only the guards whose key moved and names the receipt for the rest; a guard observed reading a path its globs do not match fails its own probe. Known-positive, chosen before the tree is read: after a .tracking-only edit, keel gate guard . re-runs the guards whose globs match .tracking and holds the rest, both counts printed; a fixture guard declaring one glob and reading outside it fails naming the path. Known-negative: keel gate guard --no-receipt . runs all 75 as before; a red run still deletes the receipt (D0371's test passes); guards.md gains the inputs column, regenerated and diff-clean."; }
        action dcWorkspaceLayeringIsGuarded;
        verification dcWorkspaceLayeringIsGuardedDoD : Test { :>> id = "f897326b-a6fb-4786-8bcc-4b0bfda60013"; :>> method = VerificationMethod::test; :>> procedureText = "Chartered by D0483 (held for the human's word - this item stays blocked on that acceptance). Guard workspace-layering reads every member's Cargo.toml and .engine/contracts/workspace-layers.toml and fails naming any dependency edge from a lower layer to a higher one. Known-positive, chosen before the tree is read: a fixture manifest with keel-git depending on keel-view fails naming both. Known-negative: the real workspace at the adding commit passes; guards.md gains the row; keel version's guard count moves by one; the guard is in all four homes (issue545's identity check)."; }
        action dcGuardIdentityIsCheckedAtTheGate;
        verification dcGuardIdentityIsCheckedAtTheGateDoD : Test { :>> id = "9cdde5e4-a6d6-47a6-bf10-560e27bfa940"; :>> method = VerificationMethod::test; :>> procedureText = "Resolves issue545: a guard's constraint-def identity (D0195 clause 1, .engine/rules/guard-constraints.sysml) is checked at the GATE, not only at land - guard doc-guard-count (or a sibling clause of control-map-reconciled) fails naming any GUARD_NAMES entry with no camelCased constraint def and any constraint def naming no guard, so a guard registered in three of its four homes turns keel gate guard red in seconds instead of failing one unit test 15 minutes into keel land. Known-positive, chosen before the tree is read: a GUARD_NAMES fixture with one name absent from the constraint file fails naming it; known-negative: the real tree with all 75 declared passes, and the existing unit test every_guard_has_a_constraint_def_identity keeps passing unchanged. guards.md's row for the carrying guard names the new clause."; }
        action dcReportTestBuildsTheModelOnce;
        verification dcReportTestBuildsTheModelOnceDoD : Test { :>> id = "48dad134-d72b-4b13-8113-17b46badc061"; :>> method = VerificationMethod::test; :>> procedureText = "DONE MEANS: the lib binary's critical path under nextest is no longer one test that builds the model eight times, and the D0475 gain is remeasured against the same 63-binary set with the fix in. Resolves issue540. TODAY: view::tests::report_produces_cards_and_rejects_unknown (keel-cli/src/view/mod.rs:5377) calls report() seven times and report_html once; every call runs Model::build, orient::compute, done_names, compute_stale_verifications and compute_coverage over the real repository (report_cards, keel-cli/src/view/reports.rs:194), and the unknown name builds the model before it errors - 690/606/347 s at 20/8/4 threads for a lib whose whole serial run is 145 s. DO: report_cards takes (or report() memoises) the computed inputs so the six named reports share one build in the test and in `keel render report`; the unknown-name check precedes the build; the test asserts the six cards and the error from one set of inputs. VERIFY: known-positive - the touched receipt's first [[timing]] row after `keel suite --touched . --no-receipt` over the real tree is no longer this test, and its own millis are under 120000 at the default thread count; known-negative - `keel render report bogus` still errors with the same message and `keel render report assurance --html` is byte-identical to before the change on the same tree; then the remeasure: nextest wall against the cargo test wall of 1246 s, quoted in the DoD result, and D0475 is kept or superseded on that number (its 2x clause)."; }
        action dcBuildScriptDoesNotWatchTheGitIndex;
        verification dcBuildScriptDoesNotWatchTheGitIndexDoD : Test { :>> id = "ee18824b-c19f-4235-af2d-6b70cd8e7369"; :>> method = VerificationMethod::test; :>> procedureText = "DONE MEANS: a cargo invocation after a test run over an unchanged source tree does not recompile keel-cli. Resolves issue541. TODAY: build/provenance.rs:53-58 (keel-cli/build.rs until sprint 757 moved it below its users) emits rerun-if-changed for .git/HEAD and .git/index; the index is rewritten by git status (provenance.rs:37 runs it), git ls-files --eol, git add, git commit and every self-reading test, so the script reruns and the crate recompiles (59.55 s release) on the next invocation, every time. DO: watch .git/HEAD and the ref file it names (.git/refs/heads/<branch>, else .git/packed-refs), never the index; decide and state in the DoD result what the +dirty flag means after this (judged from the tree at build time; a later non-source edit does not flip it) and say so in the build.rs docstring and `keel version --help` if that surface describes it. VERIFY: known-positive - `cargo build --release` twice with `git status` run between them prints no `Compiling keel-cli` the second time, and the same after `keel suite --touched .`; known-negative - a commit between the two builds does recompile and `keel version` shows the new short sha; clippy -D warnings clean."; }
        action dcDecisionScaffoldingIndexesItsEdgesOnce;
        verification dcDecisionScaffoldingIndexesItsEdgesOnceDoD : Test { :>> id = "4201b61f-ad5c-4338-85f2-8382c6b6be6c"; :>> method = VerificationMethod::test; :>> procedureText = "issue520 is resolved - decision_scaffolding (keel-cli/src/guards.rs) collects the inbound-edge targets of the whole corpus ONCE (the `to X` of every #CharteredBy/#DerivedFrom/#Resolves line and the X of every `satisfy X by`) into a set and answers each candidate's reachability from it, so the guard reads the corpus a fixed number of times whatever the candidate count; its verdicts are unchanged. VERIFY: the guard's warnings and violations on this tree are byte-identical before and after (keel gate guard decision-scaffolding . captured to two files and diffed); a fixture with one chartered and one bare accepted #ProspectiveChange Decision warns on the bare one only (known positive) and a fixture whose bare Decision is the newest warns on nothing under the landing-sprint grace (known negative); KEEL_PERF=2 keel guard --no-receipt . quotes guard:decision-scaffolding's ms beside the 4645-12463 ms the ledger held, and the hookLatencyIndicator's live value after ten stop fires is quoted beside 14125. Recording this item's pass also discharges obligationdb36c49d: the stop hook yielded red twice in the two minutes between sprint 698's record and its retro line gaining the tracked-item phrase the retro-backlog guard requires (the corrected line names issue520)."; }
        action dcRejectIsHumanJudgedAtTheWriteAndTheRule;
        verification dcRejectIsHumanJudgedAtTheWriteAndTheRuleDoD : Test { :>> id = "e4fe131c-7893-4fa4-9cea-9fdd9b915c0a"; :>> method = VerificationMethod::test; :>> procedureText = "issue526 is resolved - keel reject refuses an AI-kind judgedBy at every layer accept does: write.rs reject_decision_locked calls refuse_ai_judgment; 'reject' is in HUMAN_ONLY_WRITE_COMMANDS and HUMAN_AUTHORITY_COMMANDS so the computed control structure labels the rejection the human's action; confirmationAuthenticityRule (or a sibling rule with its own #JustifiedBy) holds resultJudgedByHuman over the Reject result as it does over Accept, so an AI-judged RejectR1 is a blocking violation. The rule and command-list change is a CR with a co-committed Decision (D0209 cl.2). VERIFY (probe pair, D0388): a fixture Decision with a RejectR1 judgedBy an ActorKind::ai actor is refused by write::reject_decision (known positive) and, hand-planted, is a confirmation-authenticity violation naming the Decision; the same fixture judgedBy a Person passes both (known negative); control_structure::tests::human_authority_commands_refuse_an_ai_actor passes with reject in both lists; clippy clean."; }
        // RAN: KEEL gate guard --no-receipt . -> PASS 74; FAIL 0; exit=0
        part dcRejectIsHumanJudgedAtTheWriteAndTheRuleDoDR1 : TestResult { :>> id = "e3a5dbee-e8ac-4bcc-965b-da79c3f1a8b9"; :>> outcome = VerdictKind::pass; :>> judgedAgainst = "2a6abdc"; :>> judgedAt = "2026-09-13"; :>> judgedBy = "claudeFable5"; }
        action dcLivingDocsNameOnlyDeclaredCliVerbs;
        verification dcLivingDocsNameOnlyDeclaredCliVerbsDoD : Test { :>> id = "9778c054-70ec-4aad-abf4-477309e58e0c"; :>> method = VerificationMethod::test; :>> procedureText = "issue528 is resolved - a guard `cli-reference` (beside tool-reference) scans the living doc surface (.engine/skills, .engine/docs, .engine/processes, .engine/contracts, .engine/workflows, .engine/rules, CLAUDE.md, .claude/output-styles) for every `keel <verb>` / `KEEL <verb>` / `keel.exe <verb>` token and FAILS naming file:line for any verb that is neither in cli_surface::COMMAND_NAMES nor a declared sub-verb of a router (gate, show, audit, record, process, library, github) per cli_facts; the ten sites are corrected to their current spellings in the same commit (test-verify -> gate validate / gate check-engine / gate guard --no-receipt; knowledge-graph-memory -> show why / show knowledge; build -> projects), and sync-claude regenerates .claude/skills. VERIFY (probe pair, D0388): known positive - a fixture doc line `keel guard .` fails naming the line; known negative - `keel gate guard .` and `keel show why` pass; the real tree passes after the ten corrections and fails naming all ten before them; catalogue row in .engine/docs/guards.md; guard count from `keel version` incremented."; }
        action dcRecorderReportRefusesNonRecordWrites;
        verification dcRecorderReportRefusesNonRecordWritesDoD : Test { :>> id = "44ed0125-8a36-4f2a-a753-17fe19e0b423"; :>> method = VerificationMethod::test; :>> procedureText = "Resolves issue532. check_report.py refuses a recorder report whose WROTE: line names a command that is not `keel record <sub-verb>` (textpatch.py, sed, python, any editor) - the D0425 recorder's only write path is the record API, and a report that admits another path is refused, not passed. It also refuses a report that records the same gate more than once (two WROTE: lines naming one --gate): a red after a write is a DISCREPANCIES line, never a second attempt with reworded evidence. The recorder brief in delegated-ceremony SKILL.md states both rules in its own words (one write per owed record; a red gate --fast after your write is reported, not retried), and .claude is regenerated by sync-claude. D0388 pair: a report with a textpatch WROTE: line and one with two RetroGate writes are refused naming their line; sprint 703's report with the offending lines removed passes. A #ProspectiveChange Decision governs the checker change (it is an enforcement surface)."; }
        action dcRecallHitDefinitionIsStated;
        verification dcRecallHitDefinitionIsStatedDoD : Test { :>> id = "b1a77e22-7ab3-4eba-a3a5-bc2f7ccb529e"; :>> method = VerificationMethod::inspect; :>> procedureText = "DONE MEANS: the recall bar is one a mechanism can actually clear, and what counts as a hit is written down before it is applied. Resolves issue391: on two of the three still-failing hand-set cases the payload contains an element that answers the question and is scored a miss - for the rebase question the first row is the requirement whose title states the rule, with the ground-truth Decision two hops behind it; for the obligation question the ground-truth Decision uses the word once while records that do discuss obligations are returned. DO NOT resolve this by editing ground truth to match what came back: that is the fitting the criterion forbids and an agent loosening the test it is failing is the worst available move. Instead put the DEFINITION to the human as a decision with both options priced: keep 'the named record, or nothing' - in which case the obligation case is unreachable without a human-authored alias and the criterion must say so, because a bar no mechanism can clear is a permanent red rather than a target - or adopt 'an element that answers', which needs a stated rule for what answering means, written before it is applied to any case. VERIFY: the chosen definition is recorded as a Decision with its cost, the harness and the criterion both state it, and the criterion's number is one the current mechanism either meets or fails for a reason that names a mechanism rather than a definition."; }
        // RAN: D0408 option A, accepted by the human 2026-09-11: a hit is the ground-truth record named in CASES among the rows the payload shows - the named record, or nothing; the bar is 7 of 8, the eighth (d0176, obligation question) a declared UNREACHABLE sentinel whose hit would be news, stated in .engine/tools/recall_ab.py docstring and CASES table before any run. python .engine/tools/recall_ab.py against keel 0.4.1 build 10b6912 (unchanged through the run): injection ON 7/8, d0176 row prints unreachable (declared), required bar 7 of 8 MET (7/7 reachable cases hit), OFF 0/8, silent 0/8, mean 923 ms. The criterion text in recallRanksLinkedRecordsAsWellAsGrepDoesDoD (backlog.sysml:519, R3 pass at 018315a) is not edited under D0307; its 'stays at 7/8 or better' stays true as read, and the definition it relies on is stated here and in the harness; no other statement of the criterion exists (grep over .engine/docs .engine/skills .claude/skills .engine/contracts scripts). No engine code changed
        part dcRecallHitDefinitionIsStatedDoDR1 : TestResult { :>> id = "648ef17b-5ab3-455a-bd7b-3cbc87fe7f1c"; :>> outcome = VerdictKind::proposed; :>> judgedAgainst = "56d3968"; :>> judgedAt = "2026-09-11"; :>> judgedBy = "claudeOpus5"; }
        action dcPagesDeclareTheirEncoding;
        verification dcPagesDeclareTheirEncodingDoD : Test { :>> id = "d0b8fe57-c7ff-4a6b-97bf-d69d53dea166"; :>> method = VerificationMethod::test; :>> procedureText = "DONE MEANS: a published page renders correctly on a host that guesses nothing. Resolves issue401: the standing brief carried typographic characters as raw UTF-8 with no charset declaration, so it rendered mojibake wherever the host did not supply one - the publisher does, which is why the artifact looked right and the file was wrong. DO: declare the encoding in the page, and extend the executive-brief contract to check that it is declared, since the checker examines structure and has no opinion about encoding - a page unreadable on half the hosts in the world passes it clean. Weigh the stronger form: emit ASCII with HTML entities for typographic characters, which is what the previous brief did and why it never showed this, against declaring the charset and keeping the characters. VERIFY: the checker FAILS a page with no charset declaration, shown by constructing one; the brief passes; and the page is read as an image from a host that sends no charset, which is the condition that produced the defect and the one a review from the publisher cannot reproduce."; }
        // RAN: python scripts/check_templates.py --self-test: 21 ok (18 before): 'no charset refused' (fixture built charset=False carrying an em dash -> 'no charset declaration in the first 1024 bytes'), 'charset past the first 1024 bytes refused' (declaration placed at byte ~1100 -> refused), 'an http-equiv declaration passes' (0 findings). python scripts/check_templates.py --brief SP/decision-brief.13b.html: 3 findings, all D0404-D0406 clauses, none from clause 0 (the standing page declares its charset). One-time probe SP/perf/nocharset_host.py (D0388, not kept as a Sensor): a local HTTP server sending Content-Type text/html with no charset served two pages chosen before the run - known positive, a constructed page with no meta charset carrying curly quotes, dashes, arrow, ellipsis: document.characterSet=windows-1252, screenshot nocharset_positive.png shows the em dash as three characters (mojibake); known negative, the tabbed brief decision-brief.html: document.characterSet=UTF-8, screenshot nocharset_brief.png clean. D0409 recorded proposed (--process-change, NOT A FORK: seven builders since 2026-09-08 already emit the meta; entities would be a second mechanism). SKILL.md 2.2 gains the rule; sync-claude 46/46.
        part dcPagesDeclareTheirEncodingDoDR1 : TestResult { :>> id = "ff348108-0ace-4238-88de-e0a7b2051d97"; :>> outcome = VerdictKind::pass; :>> judgedAgainst = "07d7601"; :>> judgedAt = "2026-09-09"; :>> judgedBy = "claudeOpus5"; }
        action dcStpaSelfCoversTheActions;
        verification dcStpaSelfCoversTheActionsDoD : Test { :>> id = "1b36f6aa-ed8e-479d-93fc-9911d5b23ce4"; :>> method = VerificationMethod::test; :>> procedureText = "DONE MEANS: the hazard analysis covers the control actions this project actually has, or the gap carries a target it is measured against. Resolves issue403: 43 of 46 computed control actions have never been analysed by an stpa-self run, and the three that have are the oldest - so the analysis covers the part of the system least likely to have changed and none of the write path added since. The structure is computed and grows on its own; the analysis is authored and grows only when run, which makes the gap structural rather than neglectful. DO: run the analysis over the uncovered actions in tranches sized to be done well, and decide what the currency warning should say when the structure outgrows the analysis again - because it will. A number that only ever rises is not actionable; either the analysis is batched against the growth or the warning states a coverage target. VERIFY: the uncovered count falls and its remainder is named rather than summarised; each tranche produces unsafe control actions with contexts that are actual states rather than beliefs or outcomes; and the currency guard's message is one a reader can act on rather than a standing number."; }
        // RAN: keel guard stpa-currency . before: 45 of 48 flat list; after run 2 and D0410: 39 of 48, remainder named by edge (hooks->agent-turn 7, commit-gate->main-ref 4, ci->main-ref 3, agent->model 15 of 19, agent->work 1, agent->enforcement-surface 6, agent->main-ref 2 of 3, agent->deliverable 1), NEXT TRANCHE agent->deliverable with its ANALYSED list; four UCAs with state contexts in engine-ucas.sysml; cargo test -p keel-cli --lib stpa_currency 6 passed
        part dcStpaSelfCoversTheActionsDoDR1 : TestResult { :>> id = "175cb0fd-8cc6-4cf4-a215-3e301d412b95"; :>> outcome = VerdictKind::pass; :>> judgedAgainst = "e9c5a83f27566cdc0a2a78aa9d9e85c52847019e"; :>> judgedAt = "2026-09-09"; :>> judgedBy = "claudeOpus5"; }
        action dcGestureCitationsAreWrittenByTheCommand;
        verification dcGestureCitationsAreWrittenByTheCommandDoD : Test { :>> id = "4776e4e0-ebf4-4be9-bbd8-9398a7138213"; :>> method = VerificationMethod::test; :>> procedureText = "DONE MEANS: a cited human-surface gesture in an acceptance or rejection note is one the tree can tell apart from the same words typed by the recorder. Resolves issue426 (found by stpa-self run 2, UCA-AC1): keel-cli/src/view/checks.rs quotes_conversational_words reads the substrings deck, console, github comment, github.com/ and tty gesture as channel evidence, and keel-cli/src/view/mod.rs read_back_names returns that same answer when the note has no quoted span - so from an agent session with delegation declared, keel accept <d> --note 'approved at the console' --by <human> passes the channel refusal, the read-back and the substance rule with nothing quoted, and the console's own tag [device <id> HMAC-verified] is text the console appends but does not store the signature for, so a typed copy is indistinguishable at the gate. DO: make the gesture citation something the command writes and the tree can re-verify - the console and deck record the HMAC (or a receipt id the paired-device store resolves) beside the tag, the TTY citation is written only by the command and its asserted stand-in (KEEL_TTY_GESTURE) is refused by the substance rule from an agent-marked session, and a note that merely CONTAINS a gesture word without the command's receipt is refused before the write with the remedy named. VERIFY: a test in keel-cli/tests constructs the agent-session accept with --note 'approved at the console' and shows it refused; a real console tap's record re-verifies against the device store; the accept with --words still passes; D0315's TTY path at a real terminal is unchanged."; }
        // RAN: cargo test --release -p keel-cli --test gesture_citation_is_the_commands -> 2 passed (agent-session --note approved at the console refused naming --words; typed TTY/deck/GitHub refused; --words records with the declared pair; reject path refused); --test device_bound_taps -> 1 passed (live console tap re-verifies against .keel/devices.toml, altered record refused); --lib checks:: -> from_the_strict_date_a_delegated_records_gesture_words_are_text ok (KEEL_TTY_GESTURE stand-in refused by the rule from 2026-09-09); --test tty_accept_cites_the_gesture -> 2 passed (D0315 TTY path unchanged)
        part dcGestureCitationsAreWrittenByTheCommandDoDR1 : TestResult { :>> id = "a179d2a1-6bc4-4025-9c33-3b4e1e62c022"; :>> outcome = VerdictKind::pass; :>> judgedAgainst = "7c5d6e5"; :>> judgedAt = "2026-09-09"; :>> judgedBy = "claudeOpus5"; }
        action dcSynopsisCitesLiveDecisions;
        verification dcSynopsisCitesLiveDecisionsDoD : Test { :>> id = "874eca08-76d5-43b1-8b2b-6513123c8834"; :>> method = VerificationMethod::test; :>> procedureText = "DONE when guard cli-surface-declared (or a sibling in the same family) FAILS a CliCommand synopsis, in either fact home, that cites a Decision id which is RETIRED - the target of a #Supersede edge (D0398) - or that does not exist under .engine/decisions. FOUND at sprint 625 (issue423): the suite synopsis still described the D0353 push gate three days after D0356 withdrew it, in both commands.sysml and cli_facts.rs, and nothing compares a synopsis against the Decisions it names; the stale sentence was found by a human reading, not by a control. DO: in the guard, extract every dNNNN/DNNNN token from each synopsis, resolve it against the decision files and the #Supersede edge set the indexer already holds, fail on retired or absent. VERIFY: a probe with one known-positive (a synopsis fixture citing D0353) and one known-negative (the corrected cliSuite synopsis citing D0356) named in the receipt; guard green on the real tree."; }
        // RAN: cargo test --release -p keel-cli --lib -> 438 passed (probe pair: fixture citing D0353 -> violation naming d0356; live suite synopsis citing D0356 -> none); keel guard cli-surface-declared . -> PASS 107 scanned 0 violations; live probe with suite edited to D0353 -> FAIL 2 violations naming d0356, restored -> PASS; cargo clippy --workspace --all-targets -- -D warnings -> Finished
        part dcSynopsisCitesLiveDecisionsDoDR1 : TestResult { :>> id = "1ca12f74-627c-4742-b33a-71972164bcff"; :>> outcome = VerdictKind::pass; :>> judgedAgainst = "70ce93c"; :>> judgedAt = "2026-09-09"; :>> judgedBy = "claudeOpus5"; }
        action dcGuardWarningsAreActionable;
        verification dcGuardWarningsAreActionableDoD : Test { :>> id = "d36f49f3-83d3-4fb1-a80a-5f465b2d5129"; :>> method = VerificationMethod::test; :>> procedureText = "DONE MEANS: the guard summary states a number a reader can act on. Resolves issue404: the guard set reports 131 warnings across 12 guards and says in its own summary that they are UNREAD until someone reads them - a count that rose six times during one session's work. Some are undischargeable by design, like 52 legacy actor references in immutable history, and that is sound; it is also the mechanism, because a set containing permanent noise cannot be read as a set worth reading. DO: separate the undischargeable from the actionable, computed rather than by hand - a warning about immutable history counted in one line, a warning naming a fixable condition surfaced where work is chosen. Do NOT promote them to violations: several are warning-tier because no defensible threshold exists (D0088), and gating would be answered by making the number fall rather than the condition go away. VERIFY: the summary distinguishes the two classes and the actionable count is small enough to be read; an actionable warning appears in the burndown alongside other work; and the undischargeable ones are counted without being enumerated, which is the rule the actor guard already applies to itself."; }
        // RAN: cargo test --release -p keel-cli --lib -> 441 passed (probe pair: history_line-built warning -> is_history true, actionable 0, history 1; plain warning naming a fixable condition -> is_history false, counted actionable); keel guard . -> ALL PASS - 38 actionable warning(s) across 7 guard(s); 5 counted-history line(s); keel orient . burndown guard_warnings actionable 38 counted_history 5; clippy -D warnings Finished; 22 of the 38 actionable are the issue312 class already tracked
        part dcGuardWarningsAreActionableDoDR1 : TestResult { :>> id = "c80b6663-5b36-43c3-a6ea-71cb086443bf"; :>> outcome = VerdictKind::pass; :>> judgedAgainst = "e902566"; :>> judgedAt = "2026-09-09"; :>> judgedBy = "claudeOpus5"; }
        action dcSlowHookFireExplainsItself;
        verification dcSlowHookFireExplainsItselfDoD : Test { :>> id = "3f03d06c-fb17-417a-b8db-95139dccf4b6"; :>> method = VerificationMethod::test; :>> procedureText = "DONE MEANS: a slow hook fire explains itself from the ledger. Resolves issue429: the human reads keel as crazy slow; the ledger for the last 36 h shows stop median 617 ms but p90 5.7 s and max 35 s, subagent-stop max 38 s, user-prompt max 28 s, one 120 s watchdog timeout, and a ledger line that records only the total, so a tail can be reproduced or guessed at but never read. The idle full stop run is 2.8 s and the critical path of its guard set is one guard, priority-inversion at 2.1 s, because it recomputes the ready frontier under 76 guards that finish beneath it; under a concurrent cargo build the same run is 6.6 s. DO: (1) every hook fire whose total exceeds a declared threshold (hooks.jsonl schema is frozen in pm.rs, so the field is a Decision) carries a phases field naming the top phases by ms as perf.rs already measures them - validate, the longest guard by name, git spawns and their summed ms, parse, receipt key - so keel enforcement-report can print, per event, WHERE the tail's time went and not only that it existed; (2) the guard runner's critical path is stated in the receipt and in the runner's own output when KEEL_PERF is on, so the guard to attack is named by the run, never inferred from a wall-clock; (3) enforcement-report gains a row per slow fire in the window with its attributed phases, so 'keel is slow' is answered by reading, and a phase no counter covers is reported as unattributed ms rather than omitted. Do NOT shorten priority-inversion or move guards off the stop hook on this item: which cost to attack is what the attribution exists to decide, and D0130 chose in-loop gating. VERIFY: a hook fire run with an injected delay in one phase produces a ledger line whose phases field names that phase first (known-positive); a receipt-hit stop run under the threshold carries no phases field (known-negative); enforcement-report over a ledger containing both prints the slow row with its phase and nothing for the fast one; and the live ledger's next slow fire, when one occurs, is read back from the report by phase."; }
        // RAN: probe pair the_longest_step_leads_and_the_uncovered_remainder_is_named + a_fast_fire_carries_no_phases_and_a_slow_one_always_carries_the_remainder (cargo test --release -p keel-cli --lib -> 445 passed); live: hook stop -> ms 8337 with phases hook:guards 7269 / guard:priority-inversion (critical path) 7160; receipt-hit stop -> ms 205 no phases; enforcement-report slowFires count 993 newest row by phase; guard-receipt critical_path = priority-inversion 7160 ms
        part dcSlowHookFireExplainsItselfDoDR1 : TestResult { :>> id = "81e14dd7-e2c5-4254-9252-c2e6bf1daed2"; :>> outcome = VerdictKind::pass; :>> judgedAgainst = "df7a54e8780090a9c721525e3d573e270a863f9a"; :>> judgedAt = "2026-09-09"; :>> judgedBy = "claudeOpus5"; }
        action dcSweepSaysWhenItCouldNotChoose;
        verification dcSweepSaysWhenItCouldNotChooseDoD : Test { :>> id = "ff7bc01a-4007-4d9c-830c-81c8259b67d7"; :>> method = VerificationMethod::test; :>> procedureText = "DONE MEANS: a sweep that could not discriminate says so, instead of returning a choice. FOUND 2026-09-07 in sprint 593: six configurations of the dominant-source second hop were swept on recall_bench.py's default arm and every one returned 49/50 at median position 3 - identical to the arm with the mechanism off. That is not a result, it is the set declining to answer, because every case in it is a one-hop retrieval and no case exercises a second hop. Read as a result it licenses two wrong moves: choose by the eight hand-written questions, which is the fitting the criterion forbids, and which D0325 came within one configuration of doing; or reject the mechanism, which is what D0325 did to the rare-term narrowing on exactly this evidence. D0364 supplied the missing arm for this mechanism; nothing stops the next one being chosen on an arm that cannot see it. DO: recall_bench.py takes a --sweep flag naming an environment knob and its values, runs the arm once per value, and reports both the per-value numbers AND an explicit verdict line - DISCRIMINATED, naming the spread, or COULD NOT CHOOSE, naming the statistic that never moved and saying that this set contains no case the knob applies to. VERIFY: a sweep over a knob the arm cannot see prints COULD NOT CHOOSE; the same sweep on the two-hop arm prints DISCRIMINATED with the spread; the verdict is derived from the measured numbers, never from a flag the caller passes."; }
        // RAN: probe pair: python .engine/tools/recall_bench.py --probe -> known-positive D0364 numbers DISCRIMINATED hits 15..22, known-negative issue405 numbers COULD NOT CHOOSE with the no-case clause, all 6 hold; live: --sweep DOM_HOP2=0.4,0.7,1.0 on the default arm -> 46/50 md 3 at every value, COULD NOT CHOOSE ... this set contains no case the knob applies to; --hops 2 --sweep DOMINANCE=0,1.25 -> 19/50 -> 24/50, DISCRIMINATED hits 19..24; the verdict is sweep_verdict(per_value), which takes no flag
        part dcSweepSaysWhenItCouldNotChooseDoDR1 : TestResult { :>> id = "9d5cc5bd-7a73-43a5-bf42-843ab0d77c3f"; :>> outcome = VerdictKind::pass; :>> judgedAgainst = "ae583285ccaf3ae0d56250bda6489d89d13fed2f"; :>> judgedAt = "2026-09-09"; :>> judgedBy = "claudeOpus5"; }
        action dcInstrumentsAreVerifiableElements;
        verification dcInstrumentsAreVerifiableElementsDoD : Test { :>> id = "126d8b49-e532-4cbb-b020-1d688dad0268"; :>> method = VerificationMethod::inspect; :>> procedureText = "DONE MEANS: an instrument is verified the way every other element is - a verification case with method=analyze and a matching verify edge - or the reason it cannot be is a recorded decision rather than an accident of where it was declared. Resolves issue395, raised by the owner's correction that assessment must not be embedded as metadata. The stored field is already gone and coverage is computed from ProprietyFinding targets, but the join is by STRING and unchecked in both directions, because a contract file holds no items for an edge to point at. DO: put both routes to the human as ONE Change Request together with issue394's missing element type, since both are additions to the same frozen safety schema and reviewing them together costs less than twice - Route A gives Sensor the attributes the manifest carries plus typed refs, moves the twenty declarations into the model, and lets a verify edge refuse a target that does not resolve; Route B keeps the contract file and guards the string join in both directions, buying typo and staleness protection today at the price of instruments never being verifiable like anything else. Build whichever is accepted, and do NOT build Route B speculatively - it is thrown away if A lands. VERIFY: if A, a verification case verifies an instrument and the edge-endpoints guard refuses a target that does not resolve, shown by constructing that case; the contract file is gone rather than kept as a second home for the same facts; and the computed coverage reads the model. If B, a ProprietyFinding naming an undeclared instrument fails a guard, shown by constructing it, and the decision to keep instruments outside the typed model is recorded with what it forecloses."; }
        // RAN: Route A landed: Sensor carries mechanism/measures/determinism/reading/producesFeedback, the twenty measures are model items, the contract file is deleted, guard 65 reads Sensor.mechanism (4/4 proof test), kernel schema validator 20/20
        part dcInstrumentsAreVerifiableElementsDoDR1 : TestResult { :>> id = "6ad87b23-090e-4a14-9414-656e0a629e8d"; :>> outcome = VerdictKind::pass; :>> judgedAgainst = "HEAD"; :>> judgedAt = "2026-09-07"; :>> judgedBy = "claudeOpus5"; }
        action dcRecallMeasurementNamesItsBinary;
        verification dcRecallMeasurementNamesItsBinaryDoD : Test { :>> id = "02f96096-a507-4103-9fc0-d5830a8fe3f6"; :>> method = VerificationMethod::test; :>> procedureText = "DONE MEANS: a recall measurement names the binary that produced it. FOUND 2026-09-07 in sprint 593: recall_ab.py was run while cargo was relinking target/release/keel.exe and reported 6/8; three runs against the settled image read 7/8, and nothing in the 6/8 output said which binary answered. The number was wrong and looked exactly like a real regression, which is the issue386 family - an instrument reporting over a file it does not control - arriving in the measurement harnesses rather than in the suite. DO: recall_ab.py and recall_bench.py capture `keel version` (the build commit and dirty flag) before the first case and print it in the header of every run, and abort with a named reason if the binary cannot be interrogated. Neither harness is on a gate, so this is a legibility control, not a blocking one: the requirement is that a recorded number can be tied to the image that produced it, so a stale or mid-relink measurement is visible in its own output instead of being indistinguishable from a settled one. VERIFY: both harnesses print the build line; a run against a deliberately absent binary reports the reason and exits non-zero rather than printing 0/50; the numbers recorded on the next recall Decision carry the build line."; }
        // RAN: DO: recall_binary.py identify/Run.header/Run.footer wired into recall_ab.py and recall_bench.py; VERIFY: both harnesses print binary : ./target/release/keel.exe = keel 0.4.1 build df7a54e+dirty; KEEL_BENCH_BIN=./target/release/no-such-keel.exe -> ABORT: no measurement - binary absent ... exit 2 on both, no 0/N printed; the build line reaches the next recall Decision by construction (D0417 cites it); probe: recall_binary.py --probe both cases hold
        part dcRecallMeasurementNamesItsBinaryDoDR1 : TestResult { :>> id = "d515fcb0-3957-4c53-a96f-3f5a2cd68685"; :>> outcome = VerdictKind::pass; :>> judgedAgainst = "872497f"; :>> judgedAt = "2026-09-09"; :>> judgedBy = "claudeOpus5"; }
        action dcRoutingVerdictReadsTheWholeTurn;
        verification dcRoutingVerdictReadsTheWholeTurnDoD : Test { :>> id = "d16c9916-f158-4fcc-b762-7bae7f2ed2e8"; :>> method = VerificationMethod::test; :>> procedureText = "DONE MEANS: the routing rig's verdict reads the whole turn, not the first Skill call. Resolves issue415, the release investigation's finding: three samples split ROUTED / WRONG / WRONG with both wrong samples invoking intake first, and intake's own description declares it runs at the START of any turn where the human states direction - so the rig was scoring the process as written as a wrong route. DO: in routing_probe.py score a sample `routed` when a skill in the case's accept list is invoked within the turn budget and every Skill call before it is intake (recorded as `prefix`, printed beside the verdict), `wrong` when any other skill precedes it, `none` when the intended skill never appears; keep every Skill name in order in the sample record; say in the docstring why intake is the one declared prefix and cite its description line. Then re-run `--investigate release --samples 3` and record the receipt on this item - unanimous, or disagreeing for a reason the samples show, which becomes the next Issue against the check. VERIFY: a unit-style check of the scoring function over recorded transcripts (intake-then-release = routed with prefix; release = routed; stpa-then-release = wrong; nothing = none) passes; the release re-run's finding line and measured spend are quoted in the RAN receipt; no rate or standing number is introduced (D0378 C)."; }
        // RAN: DO: score(skills, accept) over every Skill call, DECLARED_PREFIX = intake citing .claude/skills/intake/SKILL.md:3, prefix recorded and printed, --probe gates the run; VERIFY: --probe holds intake-then-release = routed with prefix, release = routed, stpa-then-release = wrong, nothing = none (7/7); release re-run finding line: NOT ROUTING release: 3/3 samples none - prefix intake in every sample; measured spend 3.71 USD over 3 runs, 59s wall, 1.2352 USD per run; the unanimous reason the samples show became issue432 against the check; no rate or standing number introduced
        part dcRoutingVerdictReadsTheWholeTurnDoDR1 : TestResult { :>> id = "6ba8a4fd-02df-43f1-9722-cc4dcd9b68d6"; :>> outcome = VerdictKind::pass; :>> judgedAgainst = "f848923"; :>> judgedAt = "2026-09-09"; :>> judgedBy = "claudeOpus5"; }
        action dcTouchedTestsRunBeforeLand;
        verification dcTouchedTestsRunBeforeLandDoD : Test { :>> id = "5813080e-a53d-453b-a5cf-2b5e3a9feb5d"; :>> method = VerificationMethod::test; :>> procedureText = "DONE MEANS: a push cannot carry a change to a Rust module whose own integration test is stale without that test having run. Resolves issue416: control_structure.rs changed, keel-cli/tests/control_structure_is_computed.rs asserted the old shape, the commit gate was green and CI was red - because the only thing that runs the integration tests is the full suite, whose land gate the human withdrew as too costly (D0356). DO: `keel land` (and `keel suite --touched`) computes the TOUCHED test set - every file under keel-cli/tests/ whose text names a module changed since the last green suite receipt or since origin/main, by the module's file stem - and runs exactly those test binaries before the first push; an empty set runs nothing and says so; the cost is reported in the receipt beside the suite's. This is not the D0356 gate returning: it runs seconds, not eleven minutes, and only what the change can have broken. VERIFY: a test fixture with a changed module and a stale test naming it makes land refuse with the failing test named; the same tree with the test fixed lands; a change touching no module that any integration test names runs nothing and the receipt records the empty set."; }
        // RAN: cargo test --release --test touched_tests_run_before_land (3 passed), --test push_gate_is_withdrawn (2 passed), --test adoption_check_can_fail (2 passed), lib tests ok - read from tests640d.log; cargo clippy --workspace --all-targets -D warnings clean; keel validate/check-engine clean; keel guard --no-receipt ALL PASS exit 0
        part dcTouchedTestsRunBeforeLandDoDR1 : TestResult { :>> id = "3fc59736-e300-450d-af70-164cb92607ea"; :>> outcome = VerdictKind::pass; :>> judgedAgainst = "c67c05c"; :>> judgedAt = "2026-09-09"; :>> judgedBy = "claudeOpus5"; }
        action dcArmingReadsTheAcceptancePart;
        verification dcArmingReadsTheAcceptancePartDoD : Test { :>> id = "511b078c-e0a6-433f-aaf0-1583c98e0e75"; :>> method = VerificationMethod::test; :>> procedureText = "Resolves issue435 (D0421). touched::gate_accepted reads the D0421 file through text_carries_acceptance(text, dec): true only for a `part <dec>AcceptR1 : TestResult { ... }` declaration whose body (to its own closing brace - keel accept writes one line) carries outcome = VerdictKind::pass; a token in decision prose, a declared acceptance with outcome fail, and no token are all false. VERIFY: lib test arming_reads_the_acceptance_part_not_the_token_in_prose (known-positive: the accept shape; known-negatives: the live prose shape of D0421, a failed acceptance, no token); integration test a_decision_whose_prose_names_the_token_does_not_arm_the_gate in touched_tests_run_before_land.rs lands a stale-test push with the INERT line and a not-run receipt when the Decision's prose names the token; the armed fixture writes the real part shape with an id so the tree gate does not refuse for a reason that is not the one under test."; }
        // RAN: cargo test --release --test touched_tests_run_before_land 4 passed 0 failed (tests641c.log); --test push_gate_is_withdrawn 2 passed (tests641b.log); lib touched tests 6 passed (tests641.log); cargo clippy --workspace --all-targets -D warnings clean; keel validate/check-engine clean; keel guard --no-receipt ALL PASS exit 0
        part dcArmingReadsTheAcceptancePartDoDR1 : TestResult { :>> id = "4f3604fd-dc3b-454a-9ff8-f62b70e76734"; :>> outcome = VerdictKind::pass; :>> judgedAgainst = "9d574f8"; :>> judgedAt = "2026-09-09"; :>> judgedBy = "claudeOpus5"; }
        action dcHookLandRunsFromACopy;
        verification dcHookLandRunsFromACopyDoD : Test { :>> id = "9912cc5d-fb61-428c-8bae-8601792e9440"; :>> method = VerificationMethod::test; :>> procedureText = "Resolves issue436 (D0421). .githooks/post-commit, when it resolves the binary to ./target/release/keel(.exe), copies it to ./target/release/keel-land(.exe) and runs land from the copy, so an armed touched run can relink keel.exe; a `keel` on PATH is unaffected. Carries its co-committed #ProspectiveChange Decision (D0209 clause 2), which stays proposed under D0337. VERIFY: a commit in this repo whose hook output shows land running from keel-land.exe, and the own-image line absent from the commit log; the D0421 fixture test a_stale_test_naming_a_changed_module_refuses_the_push_and_the_fixed_one_lands continues to pass (it already runs from the test's own keel image, which cargo does not relink)."; }
        // RAN: shell expansion probed: ./target/release/keel.exe -> keel-land.exe, keel -> keel-land, PATH keel untouched; sh -n .githooks/post-commit ok; suite.rs:171-181 image_collides admits release/keel-land; keel validate/check-engine clean; keel guard --no-receipt ALL PASS exit 0
        part dcHookLandRunsFromACopyDoDR1 : TestResult { :>> id = "a9159f40-ea97-4f7e-ae49-2f412e56fb78"; :>> outcome = VerdictKind::pass; :>> judgedAgainst = "cab7cac"; :>> judgedAt = "2026-09-09"; :>> judgedBy = "claudeOpus5"; }
        action dcHookCopyFollowsPathResolution;
        verification dcHookCopyFollowsPathResolutionDoD : Test { :>> id = "8a17d352-13ac-433a-a900-e3817a3245d4"; :>> method = VerificationMethod::test; :>> procedureText = "Resolves issue437 (D0422). .githooks/post-commit tests the RESOLVED file: `command -v` on whatever it chose, its directory compared by `pwd -P` with ./target/release, and the copy made for a basename of keel or keel.exe found there, keeping the real extension (MSYS answers keel for keel.exe); a binary resolving elsewhere runs as it is. VERIFY: hookprobe.sh runs the block on four cases before the edit is trusted - keel (PATH, resolves into target/release) and ./target/release/keel.exe both -> keel-land.exe; /usr/bin/git and ./target/release/keel-serve.exe untouched; sh -n parses; the commit carrying this change leaves target/release/keel-land.exe on disk and its hook output shows land from it."; }
        // RAN: hookprobe.sh on the new block: keel (PATH -> target/release/keel) -> keel-land.exe; ./target/release/keel.exe -> keel-land.exe; /usr/bin/git untouched; ./target/release/keel-serve.exe untouched; sh -n .githooks/post-commit parses. The on-disk copy and land-from-it are read from the commit log of the commit carrying this change, after it
        part dcHookCopyFollowsPathResolutionDoDR1 : TestResult { :>> id = "053fd8cc-ebc6-4522-a44b-339b02962c62"; :>> outcome = VerdictKind::pass; :>> judgedAgainst = "b522674"; :>> judgedAt = "2026-09-09T18:40:00-06:00"; :>> judgedBy = "claudeOpus5"; }
        action dcTouchedRunIncludesTheLibTests;
        verification dcTouchedRunIncludesTheLibTestsDoD : Test { :>> id = "d6696326-c25b-458f-bd31-a381c7ee891a"; :>> method = VerificationMethod::test; :>> procedureText = "Resolves issue438 (D0421). Touched.lib is true whenever any keel-cli/src path changed (stems or unattributed non-empty); run adds --lib to the one cargo invocation; failing_binaries reports cargo's `--lib` hint as lib; nothing_to_run is the emptiness rule everywhere; describe names the lib tests; the receipt carries lib = true|false; the test in guards.rs derives its present set from decision_ids_cited(live synopsis) plus d0271. VERIFY: lib test failing_binaries_are_read_from_cargos_rerun_hint gains the --lib case; cli_surface_declared_tests 14 passed with the live synopsis citing D0421; touched_tests_run_before_land 4 passed with the unnamed-module case now a lib-only pass receipt and a new record-only case with outcome empty and lib = false; push_gate_is_withdrawn 2 passed; full --lib run 451 passed 0 failed; clippy clean."; }
        // RAN: cargo test --release -p keel-cli --lib: 451 passed 0 failed (tests643c.log); failing_binaries_are_read_from_cargos_rerun_hint with the --lib case ok; cli_surface_declared_tests 14 passed with the live synopsis citing D0421; --test touched_tests_run_before_land 4 passed (lib-only pass receipt, record-only empty receipt lib = false); --test push_gate_is_withdrawn 2 passed; cargo clippy --workspace --all-targets -D warnings clean (clippy643.log)
        part dcTouchedRunIncludesTheLibTestsDoDR1 : TestResult { :>> id = "d7fe0286-ed7e-4a83-8e66-6f3de729873e"; :>> outcome = VerdictKind::pass; :>> judgedAgainst = "b522674"; :>> judgedAt = "2026-09-09T18:40:00-06:00"; :>> judgedBy = "claudeOpus5"; }
        action dcPriorityGuardReadsTheFrontierCheaply;
        verification dcPriorityGuardReadsTheFrontierCheaplyDoD : Test { :>> id = "1e0ce411-f449-4d42-95aa-7e909d332b6b"; :>> method = VerificationMethod::test; :>> procedureText = "Resolves issue439 (D0414). DONE MEANS: the priority-inversion guard no longer pays orient::compute whole for the ready list - the frontier it ranks comes from a function that builds the model once, reads the memoised git facts, and computes readiness without drift, sync position or burndown (or the guard runner computes the frontier once and hands it to the guard). MEASURED BEFORE, 2026-09-09 on this host: keel whats-next . 3.1 s wall (parse 631 ms, git x9 924 ms, gitfacts:load 431 ms); in the parallel guard set priority-inversion is the critical path at 5.5-6.3 s of a ~6.6 s fire (8 attributed ledger lines, median 5711 ms). VERIFY: KEEL_PERF=1 keel guard . names another guard as the critical path, or names priority-inversion under 1500 ms; keel show priority and keel whats-next print byte-identical output before and after on this tree; the next five attributed slow-fire lines in the ledger carry the lower figure, read back with keel enforcement-report."; }
        // RAN: KEEL_PERF=1 keel guard --no-receipt . x3: critical path verification-trace 4318/4289/4385 ms; diff of show priority, whats-next, orient old vs new binary: identical; whats-next 1550/1596 ms; cargo test --release -p keel-cli --lib: 452 passed
        part dcPriorityGuardReadsTheFrontierCheaplyDoDR1 : TestResult { :>> id = "7d3e787a-f005-47ac-afd0-a3738e4028a3"; :>> outcome = VerdictKind::pass; :>> judgedAgainst = "a6bc47b"; :>> judgedAt = "2026-09-09T20:30:00-06:00"; :>> judgedBy = "claudeOpus5"; }
        action dcChangedCacheKeepsOneHead;
        verification dcChangedCacheKeepsOneHeadDoD : Test { :>> id = "961e65f9-c69c-438e-be71-9e28c2d249db"; :>> method = VerificationMethod::test; :>> procedureText = "DONE MEANS: issue440 is resolved - gitfacts::remember_changed keeps only the rows keyed by the head it was called under and drops every earlier head's rows, so the changed section of .keel/cache/git-facts.toml holds one HEAD's path lists rather than one per commit since the cache was created. VERIFY: the unit test changed_rows_of_an_earlier_head_are_dropped_when_a_new_head_is_remembered passes, and was probed to FAIL with the retention removed; on this host the cache file, 26.9 MB with fourteen heads before, is read back under 5 MB after the first commit that follows this change."; }
        // RAN: cargo test --release -p keel-cli --lib gitfacts: 4 passed; with the retain lines replaced by a comment the new test FAILED at gitfacts.rs:417 (probe negative); file-size clause pending the next commit
        part dcChangedCacheKeepsOneHeadDoDR1 : TestResult { :>> id = "031f0e67-8457-44c1-a254-414528ee7b9b"; :>> outcome = VerdictKind::pass; :>> judgedAgainst = "a6bc47b"; :>> judgedAt = "2026-09-09T20:30:00-06:00"; :>> judgedBy = "claudeOpus5"; }
        action dcVerificationTraceIsAttributedAndCut;
        verification dcVerificationTraceIsAttributedAndCutDoD : Test { :>> id = "5d7645fc-61ef-42ee-a79e-43d8dfb90438"; :>> method = VerificationMethod::test; :>> procedureText = "DONE MEANS: issue441 is resolved - the verification-trace guard no longer bounds the parallel guard set's wall clock: its cost is attributed by phase (KEEL_PERF=2), the dominant term is removed or shared with the model cache, and the guard's answer on this tree is byte-identical before and after. VERIFY: KEEL_PERF=1 keel guard . names a guard other than verification-trace as the critical path, or names it under 1500 ms, on three consecutive runs on this host; keel guard output for verification-trace is identical before and after."; }
        // RAN: KEEL_PERF=1 keel guard --no-receipt . x3: critical path acceptance-binds-to-text 3211/2972/3198 ms, verification-trace 1572-1741 ms, frontier:extract 226-385 ms; sorted guard output diff vs pre-change baseline: identical (112 lines); cargo test --release -p keel-cli --lib: 453 passed; orient_bdd 2 passed; no_green_over_nothing 2 passed; cargo clippy --workspace --all-targets -D warnings: clean
        part dcVerificationTraceIsAttributedAndCutDoDR1 : TestResult { :>> id = "4a43a61f-102c-42af-a44c-f8547a1a8c6f"; :>> outcome = VerdictKind::pass; :>> judgedAgainst = "7fad273"; :>> judgedAt = "2026-09-09T22:40:00-06:00"; :>> judgedBy = "claudeOpus5"; }
        action dcRefusalIsALedgerFact;
        verification dcRefusalIsALedgerFactDoD : Test { :>> id = "f9ab4b56-461e-459c-ba67-bf9cf4240032"; :>> method = VerificationMethod::test; :>> procedureText = "Every refusal is a ledger fact. (a) ledger_emit takes the hook's DECISION from the JSON it emitted (allow / block / deny), never from the exit code - hook_emit returns 0 for both, so today the ledger holds 1 block in 16 196 fires (issue446); (b) a hook or gate that blocks names the control that blocked (`control`: the guard name, the pre-bash rule, the fast-tier check) and the bound actor's KIND (`actorKind`: human | ai | unbound, from the actor binding), so a block is attributable to a control and to who was stopped; (c) a refused keel WRITE - accept, append-result, append-gate-result, record decision/issue/statement/story, add-task - emits a `refused` ledger line with the same fields before it exits (issue445: today it writes nothing); (d) the scaffolded pre-commit and pre-push hooks emit `commit-gate` lines with the refusing guard names, so the commit tier is in the ledger with the in-loop tiers. VERIFY (D0388 probe pair): a fixture pre-bash deny (heredoc with a backslash) lands as decision=deny control=heredoc-backslash actorKind=ai; a clean allow lands as allow with no control; a `keel accept --words A` refusal lands as refused control=delegated-words; then `keel enforcement-report` reads back blocks per event per control per actorKind from the ledger and the doc that quoted the old counts (guards.md / CLAUDE.md) says a block is read from the emitted decision."; }
        // RAN: verifier receipt (D0425): lib 454/0 + parser 32/0; device_bound_taps 1/0; hook_and_push_controls_actually_fire 8/0; accept_honours_delegation 4/0; reject_has_a_cli_path 4/0; gesture_citation_is_the_commands 2/0; acceptance_binds_to_text 1/0; validate 734 clean; check-engine clean; guard ALL PASS (66 warnings/8 guards); enforcement-report refusals rows + commit-gate-{validate,guard,check-engine} present; DISCREPANCIES none
        part dcRefusalIsALedgerFactDoDR2 : TestResult { :>> id = "9b8a2144-01e9-4456-88a6-8fb6100eb21b"; :>> outcome = VerdictKind::pass; :>> judgedAgainst = "94a7f0b60cabb308eb971c0fb17e101e66756c6f"; :>> judgedAt = "2026-09-10"; :>> judgedBy = "claudeOpus5"; }
        action dcControlCensusByActorKind;
        verification dcControlCensusByActorKindDoD : Test { :>> id = "642c61f6-06a1-4936-9bb8-704727ee69c9"; :>> method = VerificationMethod::test; :>> procedureText = "`keel show control-census` is the empirical view of every control: per control (guard, hook rule, write-path refusal, CI gate) - WHOSE ACT IT BINDS (human | ai | either, computed from the write path or guard's subject - a refusal on `keel accept --by <person>` binds a human act, one on append-result binds an AI act), its FIRES and BLOCKS by actor kind from the ledger (dcRefusalIsALedgerFact), the INCIDENTS that motivated it - every Issue whose TITLE names the control (or an alias the census declares for it; a description cites controls by contrast - issue447's names three it closes out as NOT friction, and a description match credited all three with an observed incident) - each classified `observed` (the Issue describes an act that happened: issue267 scripts stamping verdicts, issue434 green said over red CI) or `code-read` (found by inspection or an STPA run, no act observed: issue426), and its EVIDENCE CLASS: `evidenced` (an observed incident or a block against the actor kind it binds), `hypothetical` (code-read only, zero blocks), `friction` (its only blocks are of a human act with no observed incident - issue397's eight; an incident is the control's own refusal of a correct act when the Decision that DISSOLVED the control names it, never by a word-match on the Issue's prose, which misread issue256 as friction). The view lists the `friction` and `hypothetical` controls first: those are the candidates the human asked for on 2026-09-10, one removal Decision each. VERIFY (probe pair): a fixture tree with one guard whose only Issue is code-read and zero blocks classes hypothetical; a fixture with one observed Issue classes evidenced; on this tree the delegated-words refusal classes friction and names issue397. Doc-sync: CLAUDE.md sec 2 lists the lens; the CliCommand fact is declared (D0271)."; }
        // RAN: verifier receipt (D0425) for sprint648: probe pair census unit tests pass within cargo test --lib 459/0; tests/control_census_names_friction.rs pass (delegated-words -> friction naming issue397); --help names control-census; guard --no-receipt ALL PASS
        part dcControlCensusByActorKindDoDR1 : TestResult { :>> id = "b9fd30ad-5a8e-4bb1-b193-7c634d9d48ae"; :>> outcome = VerdictKind::pass; :>> judgedAgainst = "c117f35"; :>> judgedAt = "2026-09-10"; :>> judgedBy = "claudeOpus5"; }
        action dcUcaCarriesItsEvidenceClass;
        verification dcUcaCarriesItsEvidenceClassDoD : Test { :>> id = "e708978d-a397-4631-bf5a-8b8394d6955c"; :>> method = VerificationMethod::test; :>> procedureText = "Every UnsafeControlAction in .tracking/architecture/engine-ucas.sysml carries its evidence class computed, not asserted: `observed` when a dependency edge reaches an Issue whose incident happened, `code-read` otherwise, and the stpa-self run record (stpa5) reports the count of each so a run that adds only code-read UCAs says so. `keel show control-census` (dcControlCensusByActorKind) is joined in: a ControllerConstraint bound to a `friction` or `hypothetical` control is listed under the run as a REMOVAL CANDIDATE with the human's 2026-09-10 words cited (st115), and a control the census classes `evidenced` whose UCA is unanalysed is the stpa-currency gap. The stpa-self skill and process file gain the step (stpa3 reads the census before it writes a UCA; a UCA for an act that has never been observed against the actor kind it names is written as code-read). VERIFY: run 3 of stpa-self on this tree records observed / code-read counts per UCA and lists at least the delegated-words control as a candidate; probe pair - a fixture UCA linked to an observed Issue classes observed, one linked to no Issue classes code-read."; }
        // RAN: verifier receipt (D0425) sprint649: keel show control-census . ucaSummary observed 5 codeRead 11; 9 removalCandidates incl. (no constraint) accept:delegated-words; stpaRun3 EVIDENCE line present; cargo test --release --lib view::census 9 passed; clippy 0 warnings; validate/check-engine/guard/gate --fast all clean
        part dcUcaCarriesItsEvidenceClassDoDR1 : TestResult { :>> id = "5582ce73-e651-4ef5-a280-8ee65152fa6a"; :>> outcome = VerdictKind::pass; :>> judgedAgainst = "7674e12e56a2886094d0849917d7e29bfc9e8627"; :>> judgedAt = "2026-09-10"; :>> judgedBy = "claudeOpus5"; }
        action dcReceiptlessResultIsRefusedAtWrite;
        verification dcReceiptlessResultIsRefusedAtWriteDoD : Test { :>> id = "13593dac-d28e-46a3-b490-3d0b17f2287c"; :>> method = VerificationMethod::test; :>> procedureText = "issue448 is resolved - a receiptless AI-judged method=test result is refused at the WRITE, not caught at the turn boundary. append-result and append-gate-result (write.rs append_result_locked / append_gate_result_locked) refuse when the target Test declares method=test, the judge is an AI-kind actor, and --evidence is absent or blank - the same predicate guard 52 evidence-cited applies after the fact - and the refusal writes a `refused` ledger line (verb:check = append-gate-result:evidence-cited, D0424) so the census counts it against the agent's act. A human judge is never asked for a receipt (their word is the evidence, D0232). OBSERVED 2026-09-10: the recorder subagent's gate result landed without a receipt, the turn gate went red twice, the Stop hook yielded obligationf76e7aba and the subagent improvised a second result rather than stopping - a refused write would have stopped it at the first command. VERIFY (probe pair): an AI judge with no --evidence on a method=test gate is refused with the ledger line written and the file unchanged byte-for-byte; the same call with --evidence lands with its RAN line; a human judge with no --evidence lands; a method=inspect gate with an AI judge and no --evidence lands; the same four for append-result; CLAUDE.md sec 4 names the write-path refusal accurately (today it says the result is refused, and the code shows only the guard); clippy clean."; }
        // RAN: cd keel-cli && cargo test --release --lib write:: - test result: ok. 26 passed; cd keel-cli && cargo test --release --lib census - test result: ok. 9 passed; cd keel-cli && cargo test --release --lib view:: - test result: ok. 108 passed; cd keel-cli && cargo test --release --test write_bdd - 10 scenarios (10 passed), 35 steps (35 passed); cargo clippy --release --all-targets - 0 warnings/errors; ./target/release/keel.exe guard --no-receipt . - ALL PASS; ./target/release/keel.exe validate . - 739 tracking file(s) validated clean; ./target/release/keel.exe check-engine . - .engine instance files validated clean; live probe (append-gate-result on sprint649 gate without --evidence) - exit 1, UNCHANGED, ledger +1, control append-gate-result:ran-receipt, actorKind ai
        part dcReceiptlessResultIsRefusedAtWriteDoDR1 : TestResult { :>> id = "2b070544-1b83-40c2-bc6e-e18d9383eb80"; :>> outcome = VerdictKind::pass; :>> judgedAgainst = "989c277"; :>> judgedAt = "2026-09-10"; :>> judgedBy = "claudeOpus5"; }
        action dcMethodVocabularyIsTheSchemas;
        verification dcMethodVocabularyIsTheSchemasDoD : Test { :>> id = "674d59d5-9267-417d-a0b5-31875236ef30"; :>> method = VerificationMethod::test; :>> procedureText = "Resolves issue451 (GH#70). add_task_locked validates --method against crate::schema::enum_members('VerificationMethod') (the embedded schema, element.sysml) instead of a literal list; a refused member's error names the accepted set. VERIFY: a unit test in write.rs asserts every schema-declared member (inspect, analyze, demo, test, confirmation, critique) is accepted by add-task and writes a DoD keel validate resolves, and that `analysis` is refused naming the members; keel-cli/src holds no literal VerificationMethod member list outside the schema; .engine/docs/usage.md names the method flag's members from the schema; clippy clean."; }
        // RAN: cargo test --release -p keel-cli --lib -- add_task - test result: ok. 1 passed; 0 failed; cargo test --release -p keel-cli --lib -- write:: - test result: ok. 27 passed; 0 failed; cargo test --release -p keel-cli --lib -- intake_write - test result: ok. 4 passed; 0 failed; clippy 0 warnings; keel validate . - 741 tracking file(s) validated clean; live probe add-task --method analyze exit=0, --method analysis exit=1
        part dcMethodVocabularyIsTheSchemasDoDR1 : TestResult { :>> id = "0eb088e9-9daf-4cb8-862a-16a30f8e2b1a"; :>> outcome = VerdictKind::pass; :>> judgedAgainst = "8adda1d"; :>> judgedAt = "2026-09-10"; :>> judgedBy = "claudeOpus5"; }
        action dcModelParsesInParallel;
        verification dcModelParsesInParallelDoD : Test { :>> id = "f7f49247-9df5-4856-842b-208b8e9d6fc5"; :>> method = VerificationMethod::test; :>> procedureText = "issue443 is resolved - Model::build_uncached parses AND ingests the corpus's files across a std::thread::scope pool sized as guards.rs::run_in_parallel sizes its own, each file through corpus::parsed into its own sequence of item puts and edges, and replays the sequences in declaration order so items, edges and every view are byte-identical. VERIFY: KEEL_PERF=2 keel guard --no-receipt . reports parse under 400 ms on three consecutive runs on this host (from 1068 ms); keel orient, whats-next, show priority and the sorted full guard output are identical before and after; a lib test parses a fixture of several files through the pool and asserts the model's items, their fields and the edge order equal the serial build's, including which file wins a colliding name; clippy clean. The set's wall clock is NOT this item's claim: the figure this DoD once promised (under 4500 ms) was a prediction from the parse being the floor, refuted by measurement and moved to issue455 / dcGuardPoolDispatchesLongestFirst."; }
        // RAN: KEEL_PERF=2 keel guard --no-receipt . x3 -> parse 336/389/290 ms under 400 (HEAD binary 1057); orient, whats-next, show priority, sorted guard output byte-identical HEAD binary vs new; cargo test --release -p keel-cli --lib pooled_build_is_the_serial_build -> 1 passed 0 failed; cargo clippy --release -p keel-cli -> 0
        part dcModelParsesInParallelDoDR1 : TestResult { :>> id = "acbc3999-7051-415c-89b0-5f66d0c99433"; :>> outcome = VerdictKind::pass; :>> judgedAgainst = "a4f29ee97c32652242bdd9c4eb1dc1819fc813ab"; :>> judgedAt = "2026-09-10T15:05:00Z"; :>> judgedBy = "claudeOpus5"; }
        action dcIdIsAUuid;
        verification dcIdIsAUuidDoD : Test { :>> id = "4c1ddfdf-81d5-4212-a3bd-7c8d0f517df8"; :>> method = VerificationMethod::test; :>> procedureText = "Resolves issue454. Guard `id-is-a-uuid` FAILS any item whose `createdAt` / `judgedAt` is on or after 2026-09-10 and whose `id` is not an RFC 4122 v4 UUID (8-4-4-4-12 lowercase hex, version nibble 4, variant nibble in 89ab); ids on records dated before the cutoff that fail the shape are counted as one HISTORY line, never enumerated (D0261). The same shape on any line ADDED in the working tree relative to HEAD - a modified file's added lines, or every line of an untracked .sysml under the model roots - is a violation whatever its date or lack of one, because an id that did not exist at HEAD is new no matter what it says about itself. `keel validate` does NOT change: the census of 2026-09-10 found 402 undated non-v4 ids already in .tracking (backlog DoD Tests carry no createdAt), and a validate that refused them would be red over an honest tree (D0098) with no fix but a forbidden migration (section 1.3). VERIFY: a unit test over a fixture with one v4 id, one hex-but-not-v4 id, one non-hex id (`eh5h6i7g-8f9e-0j1h-2i3d-4e5f6g7h8i9d`) dated on/after the cutoff, one pre-cutoff non-hex id and one undated hex-not-v4 id fails exactly the two dated on/after the cutoff and counts the other two by class; a unit test over a synthetic diff reads only added, non-comment lines; the live check is the guard PASSING on this tree with the HISTORY not-hex count equal to the block-aware census (88) and FAILING three probes - a typed id dated today, an undated non-v4 id in an untracked file, an added typed id in a tracked file - each probed before the claim (D0388)."; }
        // RAN: verifier receipt 2026-09-10T15:27:02Z: cargo test --release -p keel-cli --lib 469 passed 0 failed; keel guard id-is-a-uuid --no-receipt . PASS 15776 scanned 0 violations 1 counted-history line; keel guard --no-receipt . exit 0; keel validate . 746 clean
        part dcIdIsAUuidDoDR1 : TestResult { :>> id = "b45b85f4-4950-4963-ae76-e50fe99f5112"; :>> outcome = VerdictKind::pass; :>> judgedAgainst = "5f6701dc3b0ee31f8538e1146dade19cb537a1dc"; :>> judgedAt = "2026-09-10T15:27:02Z"; :>> judgedBy = "claudeOpus5"; }
        action dcDeliberateRankIsRecorded;
        verification dcDeliberateRankIsRecordedDoD : Test { :>> id = "38e7778d-b9ff-4453-9f2e-5756fbda1f90"; :>> method = VerificationMethod::test; :>> procedureText = "DONE MEANS: a deliberate priority inversion can be RECORDED and the guard honours the record. Today priority-inversion warns 'if that is deliberate say so' and reads nothing anyone could say it in - a control asking for prose with no home, which is the manual-vigilance shape D0047 rejects. MEASURED 2026-09-02: ranking the human's stated first step (st066, the computed control structure and its CliCommand prerequisite) at the head of the frontier produced 30 warnings that no fact can discharge, although the reason is a recorded Statement. DO: a typed edge - #PrioritizedBy dependency from the item to the Statement or Decision that ranks it - suppresses the warning for that item and prints the citation instead; an item ranked above High work with no such edge still warns. VERIFY: the two items above resolve to zero warnings once the edge to st066 is authored; removing the edge restores the warning; an edge to a non-Statement non-Decision is a violation."; }
        // RAN: verifier receipt (D0425): guard priority-inversion PASS 0 scanned after reorder; the three DoD cases hold in cargo test --lib inversion_pairs priority_records 3/3 and lib 466/0; metadata def PrioritizedBy = 1; clippy 0; validate 745 clean
        part dcDeliberateRankIsRecordedDoDR1 : TestResult { :>> id = "61962b35-03d9-485c-b1fa-5fb0141830dc"; :>> outcome = VerdictKind::pass; :>> judgedAgainst = "1961ab34e9783f9533a21891d175f4989d372e69"; :>> judgedAt = "2026-09-10T14:07:05Z"; :>> judgedBy = "claudeOpus5"; }
        action dcSkillsRouteBehaviourally;
        verification dcSkillsRouteBehaviourallyDoD : Test { :>> id = "0be54ddd-4d7a-4d4f-a4a6-f9ec71494b42"; :>> method = VerificationMethod::test; :>> procedureText = "DONE MEANS: whether a skill actually routes the agent is TESTED, not assumed. Landscape finding (Superpowers tests/claude-code rig, 280k stars and zero enforcement - but the one thing it has that keel lacks): keel has 57 guards over the model and no test over whether its ProcessStep prose and skill descriptions cause the agent to invoke the process. This is the tractable half of the process-authority finding (dcProcessStepsBindToChecks) that needs no schema change: test the prose behaviourally. DO: a harness that runs a real model against an authored prompt per process and reads from the transcript which skill was invoked before any write. NO STANDING COVERAGE NUMBER IS PUBLISHED (D0378 C, the human's choice 2026-09-08): one sample per skill flipped on identical inputs (issue392), and a check that disagrees with itself is a defect of the check to record as an Issue, never a rate to buy more samples of (D0381). The rig is an investigation tool (D0382) - run on a suspected skill, several samples before and after any rewrite, its findings and measured cost recorded as evidence on the item that motivated it, never a TestResult. VERIFY: the rig investigates a named case and reports per-sample verdicts, an agree/disagree finding and the measured spend; at least one skill found NOT routing, or a case found disagreeing with itself, is recorded as an Issue with the prompt that missed it (issue415 is the first)."; }
        // RAN: python .engine/tools/routing_probe.py --probe: 7/7 hold; --investigate release --samples 3: 1 ROUTED / 2 none, $3.78 over 3 runs, 39s wall; disagreement recorded as issue456 (prompt verbatim, cause: Bash disallowed + 3-turn budget) resolved by dcPrefixLeavesRoomForTheRoute; no rate published
        part dcSkillsRouteBehaviourallyDoDR1 : TestResult { :>> id = "13b13d17-2bc7-416d-94a6-19b045206e0b"; :>> outcome = VerdictKind::pass; :>> judgedAgainst = "d316dd8766acf72faaa689e39f4e5bc516f03e11"; :>> judgedAt = "2026-09-10T15:47:45Z"; :>> judgedBy = "claudeOpus5"; }
        // reordered 2026-09-10 (refineAssessPriority, D0311): effective class High from two retro recurrences (keel show priority, retroRecurrences = 2) - keel show priority listed it outranked by 27 lower-class ready items
        action dcGuardPoolDispatchesLongestFirst;
        verification dcGuardPoolDispatchesLongestFirstDoD : Test { :>> id = "96cb54ea-aeae-45c5-9ff1-1864e435bee3"; :>> method = VerificationMethod::test; :>> procedureText = "issue455 is resolved - the guard set's wall clock is owned by its pool, not its parse. Measured on this host at HEAD of sprint 653 with parse at ~300 ms: wall 5033-5090 ms, 68 guards summing 58.8 s over 20 workers (throughput floor 2.9 s), dispatched in declaration order (guards.rs run_in_parallel) so the 3 s guards can start last. PROBE FIRST, against a known case: a synthetic set of durations where longest-first dispatch is known to beat declaration order, and one where it cannot (all equal) - stated with the answer. DO, only if the probe says the ordering matters on the real set: dispatch longest-first from the previous run's per-guard durations in the guard receipt (a guard with no history dispatches first), the order being scheduling and never a change to any guard's verdict or severity, co-committed with the Decision D0209 clause 2 requires for a guards.rs change. VERIFY: KEEL_PERF=2 keel guard --no-receipt . three consecutive runs, wall clock and critical path reported before and after; the sorted full guard output identical; if the wall clock does not fall under 4500 ms the receipt says so and names the bound it hit - the item is done when the floor is MEASURED and either lowered or named, never when a number is promised."; }
        // RAN: longest-first rejected on measurement: guard_dispatch_order.py --ab six interleaved pairs, declared median 2567 ms vs longest-first 2544 ms, 22 ms apart inside the 300 ms spread, NO MEASURED DIFFERENCE; git median 5221 vs 7271 ms, critical path 1553-1679 vs 2156-2339 ms - the floor is contention, named (dcGitReadsStayInProcess, dcBatchGitReads); receipt carries 59 timed guards; cargo test 6 passed; clippy exit 0; keel guard . ALL PASS
        part dcGuardPoolDispatchesLongestFirstDoDR1 : TestResult { :>> id = "e0a7e9c8-e172-4868-9bf3-6e0e025ab570"; :>> outcome = VerdictKind::pass; :>> judgedAgainst = "a430c387eb140bd1884df1050b99a6d1332eafa7"; :>> judgedAt = "2026-09-10T16:39:02Z"; :>> judgedBy = "claudeOpus5"; }
        action dcCommitDeltaView;
        verification dcCommitDeltaViewDoD : Test { :>> id = "eb2078c6-1687-4659-a43a-19e85c7303ff"; :>> method = VerificationMethod::demo; :>> procedureText = "DONE MEANS: the delta a commit makes to Needs, Requirements, Decisions and Issues is rendered where the human's authority already lives, before they read a line of code. Landscape finding (OpenSpec team-workflow): a reviewer given the delta spec ahead of the diff sees WHAT the change is supposed to do; keel's commits arrive at GitHub as SysML hunks. keel commits to main without PRs, so the surface is the decision-channel issue body and the exec-summary page. DO: a computed #View - commit-delta - over a git range that lists items added, superseded and resolved by type, with their titles, and renders as a section on the published decision page (decision-surfacing), built from the commitDelta fact in scripts/exec_brief/facts.py; the decision-channel comment it once also named is moot since D0291 disconnected the channel. Never stored. VERIFY: for the last landed range the view names every new Decision, Issue and task in it, reconciled against git diff by count; facts.py carries it as commitDelta over publishedAgainst..HEAD; a range with no model change renders empty rather than inventing prose."; }
        // RAN: verifier receipt 2026-09-10T17:46:45Z (D0425): for the last landed range a430c387..HEAD the view names d0431 (Decision), issue458 (Issue) and storyGuardPoolDispatchesLongestFirst (task), reconciled against git diff by count (matches true); facts.py carries it as commitDelta over publishedAgainst 29fb76c..HEAD (138 added, 0 retired, 37 resolved, reconciled true, complete true); HEAD..HEAD renders empty true with every list empty; keel suite --touched 548 passed 0 failed; guard 69 PASS; validate 749 clean
        part dcCommitDeltaViewDoDR1 : TestResult { :>> id = "603f3020-6344-4ee7-a871-ae802971f1eb"; :>> outcome = VerdictKind::pass; :>> judgedAgainst = "0e84415a2e0ba806474070f2a10839718c673ae3"; :>> judgedAt = "2026-09-10T17:46:45Z"; :>> judgedBy = "claudeOpus5"; }
        action dcStpaDiagramInTheBinary;
        verification dcStpaDiagramInTheBinaryDoD : Test { :>> id = "412b68fb-c317-4e24-9933-f5a8e600ee10"; :>> method = VerificationMethod::test; :>> procedureText = "DONE MEANS: keel render control-structure --mode graph (or keel show control-structure --svg) draws the STPA diagram in the binary, byte-for-byte equivalent to .engine/tools/stpa_diagram.py on the same JSON, and the Python tool is deleted in the same commit. D0221: deterministic logic goes in the binary, I/O stays a thin step; a renderer in Python under .engine/tools is the sanctioned interim only. The five properties (D0285) become unit tests on the layout: no two segments collinear; every edge has a label naming what passes; every vertical/horizontal crossing carries a hop; controllers never overlap a drop lane; feedback enters bottom-right and control leaves bottom-left. VERIFY: the tests; the console serves the SVG at the safety viewpoint; the skill and process text name the binary command and no longer the tool (doc-sync in the same commit); tool-reference stays green after the deletion."; }
        // RAN: verifier receipt 2026-09-10T20:40:42Z: suite --touched 594 passed 0 failed over 8 stems incl. stpa_diagram; clippy 0; validate 750 clean; check-engine clean; guard ALL PASS; sync-claude matches; Rust svg 33884 = Python 33883 + trailing newline (cmp EOF); determinism 3 runs equal; render 1 svg; Python tool deleted, no refs; 3 Resolves edges
        part dcStpaDiagramInTheBinaryDoDR1 : TestResult { :>> id = "ef55cbb4-76fc-42f5-b141-4f41dcd1421d"; :>> outcome = VerdictKind::pass; :>> judgedAgainst = "34e0ae3a1ef0970b0a72fb703b4ff74b87897e63"; :>> judgedAt = "2026-09-10T20:40:42Z"; :>> judgedBy = "claudeOpus5"; }
        action dcProcessStepDeclaresItsCheck;
        verification dcProcessStepDeclaresItsCheckDoD : Test { :>> id = "b03c9fd7-3925-4fd3-b702-76adcaccf4be"; :>> method = VerificationMethod::test; :>> procedureText = "DONE MEANS (D0321 option A, the human's choice 2026-09-05 'd0321 A'): ProcessStep carries `checkedBy : String [0..1]` naming the guard or declared rule that checks the step, and the bindable processes measured in D0321 carry theirs - controlDefect (control-defect-registry), decisionSurfacing (judgment-request-quality), libraryStewardship (unit-extras-present), stpaDiagram (viewpoint-renderer), stpaSelf (stpa-currency), githubIntake's routing steps (untrusted-routing, untrusted-taint) - through a D0067 migration (schema Decision for the attribute, expand, the bindings authored, control totals: every process and every step counted before and after). D0321 also named migration (marker-census); that is a LENS, not a guard, so the binding is refused by the guard this item adds and the step stays unbound with the gap tracked (issue465). A guard `step-check-resolves` fails a checkedBy that names no GUARD_NAMES entry and no rules.sysml rule. `keel show hardening` reports per STEP: checked / declared judgment (process-enforcement.toml) / undeclared, beside the per-process figures it reports today. VERIFY: schema validates (validate_schema.py, kernel-checked construct); every authored binding resolves; a fixture step naming a ghost guard fails the new guard; hardening's per-step counts equal a hand count over the process files. Also resolves issue466: the corpus test whose witness was a process-global open counter, made flaky by this item's two tree-walking tests, asserts on the served body instead."; }
        // RAN: keel suite --touched . : pass - 546 passed, 0 failed in 244s (lib tests incl. step_check_resolves_tests x4 and step_enforcement_counts_equal_a_hand_count); keel guard --no-receipt . : step-check-resolves PASS 7 scanned, ALL PASS; keel validate . : 751 clean; keel version: guards 70 (61 hard, 9 warning)
        part dcProcessStepDeclaresItsCheckDoDR1 : TestResult { :>> id = "04deaf4f-cb53-4758-a84a-00fee4182fce"; :>> outcome = VerdictKind::pass; :>> judgedAgainst = "16acaee17704090f938507281e165cfe922dea09"; :>> judgedAt = "2026-09-10T22:30:00Z"; :>> judgedBy = "claudeOpus5"; }
        action dcAdvanceRefusesAnyBoundStep;
        verification dcAdvanceRefusesAnyBoundStepDoD : Test { :>> id = "cf2bb579-4bae-4619-bc98-7bce5b2f7fa2"; :>> method = VerificationMethod::test; :>> procedureText = "DONE MEANS (D0321 option A, second half): `keel advance <process-or-sprint> --to <step>` generalises the agile-ceremony refusal to ANY process step that declares checkedBy - the advance is refused until every earlier step's bound guard passes, and the ceremony table hand-coded in advance today becomes data read from the steps' bindings, with the agile-workflow steps carrying theirs so behaviour is unchanged there. Depends on dcProcessStepDeclaresItsCheck. VERIFY: `keel advance` on a sprint behaves exactly as before (the existing ceremony tests pass unchanged); a fixture process with two bound steps refuses --to the second while the first's guard is red and permits it when green; a process with no bound step is reported as unenforceable-by-step, not refused."; }
        // RAN: keel-suite.exe suite --touched . -> 546 passed 0 failed; cargo clippy --release --all-targets -- -D warnings -> Finished; keel advance 660 . ceremony complete; keel advance implementation . 3 needs-a-run + 1 judgment; keel advance decision-authoring . unenforceable-by-step exit 0; keel advance stpa-self --to stpa5Trigger . PERMITTED exit 0; keel guard --no-receipt . step-check-resolves 13 scanned 0 violations
        part dcAdvanceRefusesAnyBoundStepDoDR1 : TestResult { :>> id = "90a475bc-5f89-4c70-b9a6-5446ce73faee"; :>> outcome = VerdictKind::pass; :>> judgedAgainst = "05c34777a99d73a6696832de4fe5b758a0796954"; :>> judgedAt = "2026-09-10T22:37:43Z"; :>> judgedBy = "claudeOpus5"; }
        action dcCheckEngineParsesEveryInstanceFile;
        verification dcCheckEngineParsesEveryInstanceFileDoD : Test { :>> id = "48334f65-bdad-4a67-95bf-a4b1cce697ce"; :>> method = VerificationMethod::test; :>> procedureText = "DONE MEANS: `keel check-engine` runs the same parse `keel check FILE` runs over every instance file under .engine/ it validates (decisions, processes, rules, workflows, contracts, cli, skills, viewpoints) and FAILS on a parse error naming file:line:col, before reference resolution. Observed 2026-09-10 (issue467): a Decision file carrying an extra closing brace - three `}` for two opens, `keel check` rejects it at 25:1 'expected end of file, got RBrace' - passed `keel check-engine .` as 'validated clean' and would have passed the commit tier's check-engine process. VERIFY: a fixture tree with one well-formed decision file passes; the same tree with an unbalanced brace in that file fails naming the line (the two cases chosen before the tree is read, D0388); the live tree passes; `keel check-engine` on this repo still reports its file count."; }
        // RAN: cargo test --lib engine_instance_tests: a_well_formed_instance_file_is_not_a_parse_diagnostic and an_unparseable_instance_file_is_a_diagnostic_naming_its_line pass (unit662.log 15 passed); live probe keel check-engine on a Decision copy with one extra brace exits 1 naming line 25 got RBrace, well-formed copy exits 0 (verifier receipt probes)
        part dcCheckEngineParsesEveryInstanceFileDoDR1 : TestResult { :>> id = "47aa204d-eb32-40e6-be56-6a567a1ec379"; :>> outcome = VerdictKind::pass; :>> judgedAgainst = "4bdb55a458f8b25a15f538a7b9f6bc1ee68c7034"; :>> judgedAt = "2026-09-10T23:34:32Z"; :>> judgedBy = "claudeOpus5"; }
        action dcTouchedReceiptSaysRunning;
        verification dcTouchedReceiptSaysRunningDoD : Test { :>> id = "a31350f5-2a54-44e2-954b-ba81137254ff"; :>> method = VerificationMethod::test; :>> procedureText = "DONE MEANS: the touched receipt (.keel/metrics/touched-receipt.toml) says the truth at every moment of a run - `keel suite --touched` and land's touched run REPLACE the previous receipt with a stub `outcome = 'running'` carrying THIS run's head, base, stems, set, log path and zero counts BEFORE cargo starts, and write the verdict over it when cargo returns; a reader during the run, or after a killed one, sees `running`, never the last run's pass over a different change set. This is D0387's control (issue399: the suite receipt's running stub) applied to the sibling receipt it was not applied to. Resolves issue468: on 2026-09-10 the sprint 661 verifier launched `suite --touched` in the background, read the receipt while it ran, and reported the PREVIOUS run's `outcome = pass, passed = 546` (at 1789076705, stems [corpus, guards, hardening], log touched-1789076485) as its own; its own run (touched-1789079489.log) finished 646 passed / 2 failed on the scaffold tests, the six gate results of sprint 661 were recorded on the stale receipt, and the land's own run refused the push 15 minutes later. VERIFY: render_receipt with Phase::Running yields outcome running, zero counts, the run's log and set, and no pass (the known-positive); with Phase::Done yields the run's verdict and counts (the known-negative); the D0421 integration test still reads the finished receipt's outcome; the live `keel suite --touched .` leaves a `running` receipt on disk while cargo runs and the verdict after."; }
        // RAN: cargo test --lib touched::tests: a_running_stub_is_not_a_verdict (Phase::Running renders outcome running, zero counts, log, no pass) and a_finished_run_renders_its_verdict pass (unit662.log); keel suite --touched . run by the verifier: receipt at 1789084365 with stems of this change set read after the process exited, outcome pass 659/0 (verify662_receipt.txt)
        part dcTouchedReceiptSaysRunningDoDR1 : TestResult { :>> id = "1845ba03-d0be-455d-ac9d-db83f2bfbaf3"; :>> outcome = VerdictKind::pass; :>> judgedAgainst = "4bdb55a458f8b25a15f538a7b9f6bc1ee68c7034"; :>> judgedAt = "2026-09-10T23:34:32Z"; :>> judgedBy = "claudeOpus5"; }
        action dcProposedOutcomeTier;
        verification dcProposedOutcomeTierDoD : Test { :>> id = "422f1a98-2863-4cca-874f-840a17ac5bf3"; :>> method = VerificationMethod::test; :>> procedureText = "DONE MEANS (D0312 option B, the human's choice 2026-09-05 'd0312 B' - the schema half): VerdictKind gains `proposed`, and an AI-judged result whose method is demo, analyze or inspect and which carries no REPLAYABLE receipt is recorded with outcome proposed; orient's done computation, suspect, the burndown, attestation and every view that reads outcomes treat proposed as not-done-yet with its own count (never folded into pass or fail); guard 52 (evidence-cited) and confirmation-authenticity read the new value; MACHINE results - method test with a receipt CI can re-run (a ci-run receipt, D0323, or a command receipt) - and HUMAN confirmations are unchanged. Forward-only: the 5,024 standing AI results are grandfathered by judgedAt and never re-judged (D0129). One Decision per clause (D0303): this is the schema clause; the set-judgment write path and the replayable-demo rule are their own items. VERIFY: schema validates and the construct is kernel-checked; a fixture AI-judged inspect with no receipt lands proposed and orient reports the item not done with a proposed count of 1; a pre-cutoff AI inspect pass is still done; a human confirmation and a ci-run test are unchanged."; }
        // RAN: verify663: enum kernel ACCEPTED; write.rs test ai_examined_passes_without_a_replayable_receipt_land_proposed and attestation.rs test a_proposed_result_is_counted_and_is_not_a_passed_gate in the lib run 505 passed; live probe AI inspect proposed 1, Person pass 1; touched 704/0
        part dcProposedOutcomeTierDoDR1 : TestResult { :>> id = "b8aa095e-bc83-411a-80cd-118224bb1de5"; :>> outcome = VerdictKind::pass; :>> judgedAgainst = "5b4cdc4"; :>> judgedAt = "2026-09-11"; :>> judgedBy = "claudeOpus5"; }
        // RAN: keel suite --touched . detached: outcome pass, 705 passed, 0 failed in 713 s, at 2026-09-11T01:43:55Z, launch 2026-09-11T01:31:54Z, stems attestation guards orient view write; keel guard --no-receipt: ALL PASS (guard663c.log); validate 755 files clean; check-engine clean; sync-claude --check clean; probe pair cargo test 3 passed 0 failed; clippy timeout expected (build lock held during touched task)
        part dcProposedOutcomeTierDoDR2 : TestResult { :>> id = "4aed686f-2ba8-463a-a160-1cc4fbaec524"; :>> outcome = VerdictKind::pass; :>> judgedAgainst = "5b4cdc4cff36c579b0081d8b0466461ab9f3a11f"; :>> judgedAt = "2026-09-11"; :>> judgedBy = "claudeOpus5"; }
        action dcVerifierProcedureIsASkill;
        verification dcVerifierProcedureIsASkillDoD : Test { :>> id = "8c0200ae-3faa-447a-a067-ab61cb90828f"; :>> method = VerificationMethod::test; :>> procedureText = "Resolves issue469, issue471 and obligation01af4c5d. The D0425 verifier's procedure is a deployed skill, not prompt text - and the skill states the verifier's mandate: it READS and RUNS, it writes nothing under .tracking or .engine (issue471: a verifier hand-wrote two malformed triage edges and reported the tree's state from before its own edit), and any triage or ceremony write it believes is owed is a line in its receipt for the recorder: `test-verify` (or a `sprint-verify` skill that supersedes it) names the run as `keel suite --touched .` launched so that no harness cap can kill it (a detached shell, the receipt read only after the process exits), the receipt checks that make a read honest (outcome not running, `at` after the launch, `stems` equal to the changed `keel-cli/src` stems, issue468), the rest of the gate set (validate, check-engine, guard --no-receipt, clippy --all-targets -D warnings, sync-claude --check), the D0388 probe pair against the live binary, and the receipt format the recorder reads. The primary's verifier prompt then names the skill and nothing else. VERIFY: the skill file carries each of those steps by name; a verifier launched with the skill alone completes a touched run that exceeds ten minutes and reports it from its own receipt; `keel sync-claude --check` is clean after the skill lands."; }
        // RAN: keel validate . -> 758 tracking file(s) validated clean.; exit=0; keel check-engine . -> .engine instance files validated clean (kernel-free; D0112 phase 2).; exit=0; keel guard --no-receipt . -> PASS 51; exit=0; keel sync-claude --check . -> claude-surface: keel-owned subset matches this binary(s) generator (46 registry skill(s)); exit=0; cargo clippy --release --all-targets -- -D warnings -> pass; exit=0; probe pair positive 17/17 names present negative 2/17 names present (exit 0 / 1); touched receipt outcome=empty stems=[] at=1789094703 launch=1789094698 at>launch ok; suite receipt outcome=pass passed=720 failed=0 duration 896 s; STATUS BEFORE/AFTER identical 7 dirty M paths + 2 untracked
        part dcVerifierProcedureIsASkillDoDR1 : TestResult { :>> id = "ad433a7a-664d-4465-b24b-86a45ae3950e"; :>> outcome = VerdictKind::pass; :>> judgedAgainst = "24dbcfb"; :>> judgedAt = "2026-09-10"; :>> judgedBy = "claudeOpus5"; }
        action dcMarkerTextWithoutMarkerHolds;
        verification dcMarkerTextWithoutMarkerHoldsDoD : Test { :>> id = "ec120ed1-c321-4a77-9473-79ae75046c48"; :>> method = VerificationMethod::test; :>> procedureText = "DONE MEANS: a Decision recorded through keel record decision whose context, decision, rationale or consequences text names process-change, safety-change, ProspectiveChange or SafetyChange while the draft carries no marker: header is written PROPOSED with a line in the record's own acceptance test naming the mismatch, and the write path prints why it was not auto-accepted - never accepted under standing consent (D0337). Resolves issue460: on 2026-09-10 D0432's consequences said in words it was a process change and the record landed accepted because the marker line was missing; nothing in the engine noticed. VERIFY: known-positive - a draft whose consequences say 'Process-change (D0337)' with no marker records proposed and the output names the mismatch; known-negative - the same draft with marker: process-change records proposed by the existing D0337 path, and a draft naming neither records accepted as today; both as unit tests on the classifier and one end-to-end run of each through the binary against a scratch project, the receipt naming the three runs; guard consent-scope (or its successor) reads the same classifier so a hand-edited file cannot differ from the write path. It gates a process change: a #ProspectiveChange Decision accompanies the code."; }
        // RAN: keel suite --touched: 712 passed 0 failed 792 s, stems deck guards write + lib, at 1789100468 > launch 1789099676, head 0986b7a; probe pair: lib 9 passed (marker_text_tests consent_scope_tests marker_hold_tests atomic_write_tests), integration marker_text_without_marker_holds 4 passed; clippy -D warnings exit 0; validate 759 clean; check-engine clean; guard PASS with consent-scope 151 scanned 0 violations (HISTORY 104 + 1); sync-claude --check clean
        part dcMarkerTextWithoutMarkerHoldsDoDR1 : TestResult { :>> id = "a0e7a7d1-342a-4bfc-8c3d-cee0cce34bbd"; :>> outcome = VerdictKind::pass; :>> judgedAgainst = "0986b7a"; :>> judgedAt = "2026-09-10"; :>> judgedBy = "claudeOpus5"; }
        action dcGuardReadsTheWorkingTreeOutsideTheHook;
        verification dcGuardReadsTheWorkingTreeOutsideTheHookDoD : Test { :>> id = "a4e418f2-8ce2-4357-a766-586ac736d316"; :>> method = VerificationMethod::test; :>> procedureText = "Resolves issue464 (High): the D0425 verifier's `keel guard --no-receipt` reported ALL PASS over an unstaged tree and the pre-commit hook then refused the same edits on `process-change`, because the index-reading guards (`staged_changes` in guards.rs: process-change and the D0308 acceptance-binds-to-text staged read) scan `git diff --cached` and see nothing before `git add`. DONE MEANS: when `keel guard` runs OUTSIDE a commit hook (no `KEEL_HOOK`/pre-commit context) the index-reading guards scan the WORKING TREE's changes to their locked surfaces - staged and unstaged alike, `git diff HEAD --name-status` plus untracked - so a locked-file edit without its co-committed marked Decision is a violation the moment it exists, not the moment it is staged; inside the hook the staged read is unchanged, since the commit is what the lock governs; the report line names which read it made. The verifier flow reads the same verdict the commit will. VERIFY: a fixture repo with an unstaged edit to `.engine/processes/x.sysml` and no Decision fails `keel guard process-change` before staging (known-positive; today it passes), and the same tree with a marked Decision file unstaged beside it passes (known-negative); inside a simulated hook context the staged read is proven unchanged by the existing process-change tests; the guard's report says `working tree` or `index`."; }
        // RAN: cargo test --release --test guard_reads_the_working_tree: 4 passed (D0388 pair); lib change_read_tests 3 passed; keel suite --touched 719 passed 0 failed at 1789107167 head c88feb2
        part dcGuardReadsTheWorkingTreeOutsideTheHookDoDR1 : TestResult { :>> id = "09b6ee05-1457-4304-959c-a405b0b70721"; :>> outcome = VerdictKind::pass; :>> judgedAgainst = "c88feb2"; :>> judgedAt = "2026-09-11"; :>> judgedBy = "claudeOpus5"; }
        action dcReceiptAtMeansTheSameInBothReceipts;
        verification dcReceiptAtMeansTheSameInBothReceiptsDoD : Test { :>> id = "96c9b1a7-f660-4b41-b9af-48fa2988f833"; :>> method = VerificationMethod::test; :>> procedureText = "Resolves issue472. The suite receipt and the touched receipt say the same thing with the same word: `at` is the moment the receipt was WRITTEN - the end of a done run, the start of a running stub - in both files, and the suite receipt carries `seconds` (the run's wall clock) as the touched one does. suite.rs's done receipt stamps now_secs() at write, not `started` (today suite.rs:301 writes `at: started`, one second after launch on every run, so a reader told to check `at` against its launch epoch sees the run's identity and not its completion; touched.rs:342 already stamps at write). The test-verify skill's SUITE clause drops the mtime workaround and reads `seconds` from the receipt. VERIFY: a unit test in suite.rs renders a Done receipt with started=100 and a finish at 700 and asserts at = 700 and seconds = 600, and renders the Running stub and asserts at = started - the D0388 pair; `keel suite` on this host writes a receipt whose `at` minus `seconds` is within two seconds of the launch epoch; the skill text names `seconds`; sync-claude --check clean."; }
        // RAN: touched run pass 560/0 in 542s at 1789109802 head b50ee9b; probe pair 6 passed; validate, check-engine, guard, sync-claude, clippy all green per verifier receipt 2026-09-11
        part dcReceiptAtMeansTheSameInBothReceiptsDoDR1 : TestResult { :>> id = "05c071f0-2738-4b01-876d-f34ea046a3a5"; :>> outcome = VerdictKind::pass; :>> judgedAgainst = "b50ee9b"; :>> judgedAt = "2026-09-11"; :>> judgedBy = "claudeOpus5"; }
        action dcSetJudgmentWritePath;
        verification dcSetJudgmentWritePathDoD : Test { :>> id = "17481d44-7876-48ec-9b1e-869366b33017"; :>> method = VerificationMethod::test; :>> procedureText = "DONE MEANS (D0312 option B - the human's judging half): `keel judge-set` records the human's verdict on a SET of proposed results in one sitting - one card on the console deck and one command - while every item is recorded INDIVIDUALLY (its own pass or fail result, judgedBy the human, with the verbatim quote receipt D0198 requires) so issue158's COUNT-accepted-as-a-card cannot recur; the human samples rather than judges every set: `attestation-policy.toml` declares a sampling rule (a share or a count per sprint) and `keel show attestation` reports proposed / sampled / judged as separate numbers. Depends on dcProposedOutcomeTier. VERIFY: a fixture with six proposed results and a 50% rule presents three; judging the set writes three individual results each quoting the human; the census shows 6 proposed, 3 sampled, 3 judged; a set judged from an agent session without the human's quoted words is refused (D0289)."; }
        // RAN: keel suite --touched at 829e0f0: 730 passed, 0 failed, 692 s (judge_set_records_each_item 3 tests in the set); validate, check-engine, guard, sync-claude --check, clippy all green per VERIFIER_RECEIPT 2026-09-11
        part dcSetJudgmentWritePathDoDR1 : TestResult { :>> id = "a3d680c2-7995-4d0e-8f95-9b8188909093"; :>> outcome = VerdictKind::pass; :>> judgedAgainst = "829e0f0"; :>> judgedAt = "2026-09-11"; :>> judgedBy = "claudeOpus5"; }
        action dcReplayableDemoStaysAPass;
        verification dcReplayableDemoStaysAPassDoD : Test { :>> id = "bdff30b1-9998-409f-9a7b-d87d6cc65944"; :>> method = VerificationMethod::test; :>> procedureText = "DONE MEANS (D0312 option B - the demonstration clause, the one that separates B from A): an AI-judged `demo` result whose receipt is REPLAYABLE stays a pass - replayable means the receipt is a command a human or CI can re-run (a `// RAN: <command>` receipt whose command `keel reverify` recognises, or a ci-run receipt, D0323) - and a demo without one is proposed like any other AI-examined claim; `keel reverify --demos` re-runs the replayable demo receipts at HEAD and stamps or fails them, so the replay is exercised, not asserted; the attestation census counts demo-replayable apart from demo-proposed. Depends on dcProposedOutcomeTier. VERIFY: a fixture demo with a command receipt that exits 0 stays pass and reverify re-stamps it; the same with a command that exits 1 flips to fail naming the command; a demo with a prose receipt lands proposed; the sampling rule of dcSetJudgmentWritePath still samples replayable demos, so a demo receipt that replays green for the wrong reason has a reader (the risk D0312 names)."; }
        // RAN: verifier receipt 2026-09-11 head=6d9586e: keel suite --touched outcome=pass passed=731 failed=0 seconds=885; validate 763 tracking file(s) validated clean.; exit 0; guard PASS exit 0 (amendment); probe pair ok; DISCREPANCIES: NONE
        part dcReplayableDemoStaysAPassDoDR1 : TestResult { :>> id = "2525dbd8-9593-498e-9010-b4a334341c36"; :>> outcome = VerdictKind::pass; :>> judgedAgainst = "6d9586e"; :>> judgedAt = "2026-09-11"; :>> judgedBy = "claudeOpus5"; }
        action dcControlProofStateIsComputed;
        verification dcControlProofStateIsComputedDoD : Test { :>> id = "13174a83-b4b2-4c27-829d-f27c8207ddb9"; :>> method = VerificationMethod::test; :>> procedureText = "DONE MEANS: a control's proof state is computed by the binary and reported beside declared and armed, not by a script someone remembers to run. Chartered by D0360. Today the census lives in .engine/tools/guard_proof_census.py and reports 17 of 64 guards named in a test that asserts a failure, 21 named only around passing assertions and 26 named in no test body at all - a number nothing surfaces and nothing keeps honest. DO: compute the state in the binary so `keel show controls` carries PROVEN alongside DECLARED and ARMED, with the unproven LIST as the actionable output and the share as context, never a bare percentage; keep it an indicator rather than a gate (D0088), because a threshold would be answered by writing whichever test moves the number; and make a new guard's absence of a demonstrated catch visible at the moment it is added rather than at the next census. Where the textual heuristic cannot decide - a guard exercised by a fixture that never names it - the surface says UNDETERMINED rather than guessing either way, because 'we cannot tell whether this control was ever shown to work' is a different answer from 'it was not'. VERIFY: the computed number matches the census tool's on the same tree; adding a control with no failure-asserting test makes it appear in the unproven list; adding such a test moves it out, shown on a real guard rather than a fixture; and the three states are distinguishable in the output, since collapsing armed and proven is the confusion this whole item exists to end."; }
        // RAN: RAN: verifier receipt batch3 head=40190c5: keel suite --touched -> 710 passed 0 failed 700 s (touched-1789134894.log); keel show controls . -> controlProof 72 guards 30 proven 22 unproven 20 undetermined; cargo test control_proof_state_is_computed in the touched set; guard ALL PASS exit 0
        part dcControlProofStateIsComputedDoDR1 : TestResult { :>> id = "f450610c-61c4-4ff3-9497-ac8531304414"; :>> outcome = VerdictKind::pass; :>> judgedAgainst = "40190c5"; :>> judgedAt = "2026-09-11"; :>> judgedBy = "claudeOpus5"; }
        action dcAddTaskLandsInsideItsDef;
        verification dcAddTaskLandsInsideItsDefDoD : Test { :>> id = "70c15580-325c-4716-8627-6f38bc43036a"; :>> method = VerificationMethod::test; :>> procedureText = "DONE MEANS: add-task lands the task inside the def it was given, or refuses. Resolves issue407. DO, both halves: braces_in handles a backslash escape, so an escaped quote inside a field's prose no longer terminates the string and desynchronises the scan; and add_task_locked checks the landing site before writing - a def opening at one column closes at the same column, and if the scanned closing brace is a different block the write REFUSES naming both lines and columns rather than placing the task somewhere plausible. The second half is the control: the escape fix removes one cause, and a line scan that goes wrong does not announce itself. VERIFY: braces_in returns no open for a line whose string carries an escaped quote before a brace; a two-def fixture whose FIRST def contains an escaped quote takes a new task into the SECOND def rather than past it; the original artefact reproduces - add-task --def NextWork against .tracking/backlog.sysml at 018315a placed the task at line 2696 outside the def closing at 2104, and against the fix places it at 2104 inside; the two items this defect mis-filed are moved into EngineBuild under a control total."; }
        // RAN: reproduced twice on a clean tree at 018315a before any claim: add-task --def NextWork placed the action at line 2696 while action def NextWork closes at 2104, --def EngineBuild on the same file correct at 807; mechanism located at write.rs braces_in (no escape handling) and confirmed against backlog.sysml line 1793; against the fix the same reproduction lands at 2104 inside the def; unit test an_escaped_quote_does_not_move_a_task_out_of_its_def 1/1 (braces_in direct + two-def fixture end to end); keel suite 571 passed 0 failed (receipt 199146c397b7); validate 676; guard ALL PASS; clippy -D warnings clean
        part dcAddTaskLandsInsideItsDefDoDR1 : TestResult { :>> id = "fc7d3ff8-f1f1-4527-97ab-0b52066ac6f8"; :>> outcome = VerdictKind::pass; :>> judgedAgainst = "4a38e84d65efbf1b3693856861325cbd26d89709"; :>> judgedAt = "2026-09-07"; :>> judgedBy = "claudeOpus5"; }
        action dcInstrumentsEnterThePropriety;
        verification dcInstrumentsEnterTheProprietyDoD : Test { :>> id = "1117dfac-0967-46d2-b8d8-de78008d8000"; :>> method = VerificationMethod::inspect; :>> procedureText = "DONE MEANS: the instruments this project publishes numbers from are in the propriety inventory and assessed under the five lenses, starting with the ones whose output already reaches a human. Chartered by D0361. Today 40 propriety findings stand and every target is a thing that BLOCKS - guards, hook probes, launcher probes, the pre-push fix - while six defects in one day came from things that MEASURE (issue384, issue386, issue389, issue390, issue391, issue392), none of which has ever been assessed. DO: inventory the instruments as propriety targets - the computed-facts script, the chart and logic-exhibit builders, the retrieval benchmark and its A/B harness, the routing probe, the report renderers, the guard-proof census - each UNASSESSED until a round covers it, so silence reads as a gap rather than a clean bill; then run the FIRST TRANCHE over the two whose numbers reach a human today, the facts script and the chart builders, one finding per target per lens with a named defeater. Assess the shipped form, never a scratchpad copy, and state independence where I authored the target. VERIFY: `keel view propriety` shows the instruments as targets with their state; the first tranche's findings each name a defeater that was actually tried rather than restating that the number looked right; any unsound verdict routes to an Issue with a resolver; and the count of UNASSESSED instruments is reported rather than the assessed ones being presented as the whole inventory."; }
        // RAN: PARTIAL: the inventory exists (20 instruments declared, guard 65 holds it against the tree both ways, 4/4 proof test) and the STPA increment is authored (EHZ10 + 9 loss scenarios). The FIRST TRANCHE of propriety findings under the five lenses is NOT done - every instrument still reads assessed=no, so this criterion's main clause is unmet
        part dcInstrumentsEnterTheProprietyDoDR1 : TestResult { :>> id = "1923fc02-f6ef-4811-9d3c-686e38a40030"; :>> outcome = VerdictKind::fail; :>> judgedAgainst = "HEAD"; :>> judgedAt = "2026-09-06"; :>> judgedBy = "claudeOpus5"; }
        // RAN: inventory: 20 Sensor items in engine-instruments.sysml; FIRST TRANCHE: pf56-pf65 over instrument:execBriefFacts and instrument:execBriefCharts, one per lens, each defeater TRIED (facts run over 584df9a, mutated worktree, stale-file probe, headless-Chromium fit_check of shipped builders) or STANDS; shipped form assessed (tracked scripts run by path); independence stated in the package header (author claudeOpus5, assessor claudeFable5, same lineage; the sound verdict is testimony); unsound -> issue511 (resolver dcFactsTypedFiguresAreRefused), issue512 (resolver dcFiguresRefuseOccludedText); keel show control-structure . -> execBriefFacts 5 lens rows (overfit unsound, 4 conditional), execBriefCharts 5 lens rows (overfit unsound, 3 conditional, measurability sound), 18 of 20 sensors UNASSESSED; keel show view propriety . -> 10 instrument: rows; keel gate validate . -> 786 clean
        part dcInstrumentsEnterTheProprietyDoDR2 : TestResult { :>> id = "533559e4-022e-4f5e-ad1d-6174d8209af5"; :>> outcome = VerdictKind::proposed; :>> judgedAgainst = "584df9a"; :>> judgedAt = "2026-09-12"; :>> judgedBy = "claudeFable5"; }
        action dcGitReadsStayInProcess;
        verification dcGitReadsStayInProcessDoD : Test { :>> id = "c014593e-3e83-4e1d-a114-23cfa3622c87"; :>> method = VerificationMethod::test; :>> procedureText = "DONE MEANS: the git spawns left in `keel orient` and `keel guard` after dcGuardsRunInParallelAndTimed, dcGitFactsAreContentAddressed and dcOneCorpusPerProcess are MEASURED (count and timed total, KEEL_PERF=2, warm cache) and the measurement decides: if the residual exceeds 500 ms per orient, the immutable-object reads (cat-file, rev-parse, diff between two commits) move in-process on gix and the number is re-measured; if it does not, the measurement is recorded in this item's result and the move is mooted by a Decision that names the number, because sixty crates of dependency are not bought for less than half a second."; }
        // RAN: KEEL_PERF=2 keel orient . git x11 in 473/476/561 ms -> x8 in 406/431/433 ms after orient.rs dedupe, under the 500 ms bar; guard git x41 is contention-summed, critical path CPU (priority-inversion 1452 ms alone); mooted by D0372
        part dcGitReadsStayInProcessDoDR1 : TestResult { :>> id = "f25d081e-7502-4e85-b0fa-0d8c8a02ce1f"; :>> outcome = VerdictKind::pass; :>> judgedAgainst = "1335211ad79f2674d2b38b08906b0734c510aca2"; :>> judgedAt = "2026-09-08T01:08:00-06:00"; :>> judgedBy = "claudeOpus5"; }
        action dcHookDaemonOnlyIfTheReceiptIsNotEnough;
        verification dcHookDaemonOnlyIfTheReceiptIsNotEnoughDoD : Test { :>> id = "aa65efb6-182c-49cd-ac0a-fa783bddb062"; :>> method = VerificationMethod::test; :>> procedureText = "DONE MEANS: a resident process serves the hooks only if dcGateAnswersFromItsReceipt leaves an idle turn boundary above one second on this tree - measured, not assumed. If the receipt path is under one second the daemon is mooted by a Decision that names the number; if not, `keel hook` connects to a per-repository daemon holding the parsed model and the git-fact cache, falling back to the one-shot path when none is running, with the daemon invalidating on the same fingerprint the CLI uses."; }
        // RAN: keel hook stop idle 5202/5428 ms -> 218/260/318 ms (sprint601), re-timed 222/275/272 ms after rebuild, under the 1 s bar; mooted by D0373
        part dcHookDaemonOnlyIfTheReceiptIsNotEnoughDoDR1 : TestResult { :>> id = "0f0a49ef-22ee-412a-b440-c047331806ed"; :>> outcome = VerdictKind::pass; :>> judgedAgainst = "1335211ad79f2674d2b38b08906b0734c510aca2"; :>> judgedAt = "2026-09-08T01:08:00-06:00"; :>> judgedBy = "claudeOpus5"; }
        action dcBriefDeliveredCountIsStructural;
        verification dcBriefDeliveredCountIsStructuralDoD : Test { :>> id = "09670c48-5a55-4ec2-8f48-e9da5814096f"; :>> method = VerificationMethod::test; :>> procedureText = "DONE MEANS: the standing brief's 'already in the tree' count is read from the facts file and the facts file computes it STRUCTURALLY, not only by phrase. Resolves issue411. DO: scripts/exec_brief/facts.py carries `pendingDelivered` / `pendingDeliveredList` - a proposed Decision is DELIVERED when a delivery record holds `#CharteredBy dependency from <story> to <its id>;` and the same record holds a `story<Slug>DoDR<n> : TestResult` with `outcome = VerdictKind::pass` - read from typed edges and recorded verdicts the guards already validate, so rewording a consequences string cannot move it; the phrase rule (`pendingAlreadyShipped`) is kept beside it because a Decision built outside a sprint is invisible to the structural reading; the page builder derives its in-the-tree count as the UNION of the two lists read from facts.json and refuses on any anchor it cannot find exactly once; the brief's own footnote states both counts and the rule behind each. VERIFY: `python scripts/exec_brief/facts.py` emits both facts with `how` naming the rule; the rebuild script prints the derived counts it wrote; `python scripts/check_templates.py --brief <page>` is clean; the published page's chips, table and footer carry the derived count and no other."; }
        // RAN: python scripts/exec_brief/facts.py emits pendingDelivered=5 (d0361, d0363, d0368, d0370, d0371) with how naming the CharteredBy+DoD-pass rule and pendingAlreadyShipped=2 (phrase rule); rebuild_2026_09_08.py printed pending=8 in_tree=6 and refused no anchor; python scripts/check_templates.py --brief decision-brief.html clean
        part dcBriefDeliveredCountIsStructuralDoDR1 : TestResult { :>> id = "cd2157f3-44f0-498a-8dd8-3936c0a43c7f"; :>> outcome = VerdictKind::pass; :>> judgedAgainst = "c9401e9f087597568cb9ffa76281f4123a976900"; :>> judgedAt = "2026-09-08T00:00:00Z"; :>> judgedBy = "claudeOpus5"; }
        action dcDeclaredBudgetsNameTheirCheck;
        verification dcDeclaredBudgetsNameTheirCheckDoD : Test { :>> id = "b2ae1c33-fdbe-40da-92ac-a2186c952b4b"; :>> method = VerificationMethod::test; :>> procedureText = "DONE MEANS: every numeric budget a deployed skill's contract table declares names the check that holds it, or the table says none does - a budget nobody holds is a reminder, and D0047 says a reminder is not a control. WHY: three decision briefs went out under a contract whose word budgets were prose in the asi-templates skill (section 2.1) and held by nothing; the third drew the human's verdict ('the decision brief is still far too verbose.', st109) before any check did, the same shape as issue397 the day before - a declared rule with no reader (retro of sprint 607, issue413). DO: a probe in the guard set or in check_templates.py scans every .engine/skills/*/SKILL.md for a markdown table whose header names a Budget column, and for each row carrying a number requires either a named check in the same section (a `check_templates.py --<flag>`, a guard name, a pytest path) or the literal word 'unheld' in the row; a row with a number and neither fails, naming the skill, the row and the number. VERIFY: the probe fails a fixture skill whose budget row names no check and passes the same fixture with the check named; run over the live skill set it passes - which means the four asi-templates rows the exec-summary suite measures (why now, decision rule, why this wins, what would change my mind) name tests/exec_summary in the table, and the section 2.4 rows name none and say so."; }
        // RAN: verifier receipt batch1: check_templates.py --probe pass exit 0; --self-test pass exit 0; live census 7 held 0 unheld
        part dcDeclaredBudgetsNameTheirCheckDoDR1 : TestResult { :>> id = "a75ccdab-70f5-4160-a61c-8b8594664d29"; :>> outcome = VerdictKind::pass; :>> judgedAgainst = "b8fab64"; :>> judgedAt = "2026-09-11"; :>> judgedBy = "claudeOpus5"; }
        action dcRoutingVerdictQuotesItsEvidence;
        verification dcRoutingVerdictQuotesItsEvidenceDoD : Test { :>> id = "ef2cd9f7-9a65-47c7-ab18-ce827f1cdb18"; :>> method = VerificationMethod::test; :>> procedureText = "DONE MEANS: every routing verdict the probe records names the text that decided it. Derived from us103 (st111, the human's words: 'user said X - is the user asking for a view? if so, quote the text indicating so. Is the user asking to record? if so, quote the text indicating so'). DO: rewrite the routing probe's judging step as a written rubric with one question per route (VIEW, RECORD, CHANGE, EXECUTE, ORIENT, TRIVIAL) that a lower-capability model answers yes/no, each yes carrying a verbatim quote from the prompt under test; a verdict with no quote, or whose quote is not a substring of the prompt, is REFUSED by the probe rather than counted; run-to-run disagreement on the same prompt is written as a probe finding naming both quotes, so the rubric can be critiqued (D0381), and never as a rate. Record the model used and what the run cost beside the output, measured. VERIFY: the probe rejects a fabricated quote in a fixture; the 47 prompts in .engine/tools/routing_prompts.toml each produce a verdict with a quote that is a substring of the prompt; a re-run's disagreement, if any, appears as a named finding with both quotes; the cost line is a measured figure."; }
        // RAN: python .engine/tools/routing_probe.py --probe -> 15 PASS 0 FAIL, the fabricated-quote fixture refused by name; python .engine/tools/routing_probe.py --rubric all x3 (2026-09-12, claude-haiku-4-5-20251001 read from the CLI result; measured 1.60 / 1.57 / 1.70 USD): every recorded verdict quotes a substring by construction; DISAGREES findings name both quotes (14 then 19 requests); VERIFY clause 'the 47 prompts each produce a verdict' does NOT hold - run 1 46 verdicts (element-critique refused), run 2 44 (intake, engine-triage refused), run 3 45 (indicator, repo-push refused: no route affirmed) - issue510, resolver dcRouteRubricQuestionsSeparateOnTheRequest
        part dcRoutingVerdictQuotesItsEvidenceDoDR1 : TestResult { :>> id = "b5108bad-0480-42ce-8261-26c239812a4a"; :>> outcome = VerdictKind::fail; :>> judgedAgainst = "ac38d48"; :>> judgedAt = "2026-09-12"; :>> judgedBy = "claudeFable5"; }
        action dcProcessStepsAreHookGateOrMemory;
        verification dcProcessStepsAreHookGateOrMemoryDoD : Test { :>> id = "46b854f8-8f2b-413a-90a0-98deb222ce30"; :>> method = VerificationMethod::inspect; :>> procedureText = "DONE MEANS: for every process step this project has adopted, the answer to 'what makes this step happen' is computed, in three classes: a HOOK fires it (a Claude Code hook event or a git hook - UserPromptSubmit already fires the route-first checklist before the model sees the prompt, claude_surface.rs:206), a GATE refuses passage without it (keel advance --to <Gate>, D0209), or MEMORY - an agent has to remember, which is the class the human named as the failure. Derived from us102 (st111: 'Maybe we provide githook-like hooks into processes. Do they fire before the prompt? before work is done (e.g. sprint planning)? after as a post-processing (e.g. sprint retro)?'). DO: extend the hardening lens's process-enforceability question so each ProcessStep is classified hook / gate / memory from the hook config, the ceremony gates and the step's declared check (dcProcessStepsBindToChecks), and list the MEMORY steps by process with the hook point that would carry each - before the turn (UserPromptSubmit), before the work (the refine gate), after it (the retro gate, Stop) - as a proposal, never as an added hook. VERIFY: keel show hardening names every adopted ProcessStep in exactly one class with the fact that put it there; the MEMORY list is non-empty or the lens says why; no hook is added by this item."; }
        // RAN: RAN: ./target/release/keel-serve.exe show hardening . -> stepTrigger: adoptedUnits 10, notAdoptedUnits 23, steps 61 = gate 6 + hook 0 + memory 55, unresolved [], six gateSteps each naming checkedBy gate:<phase> and its process, 14 memoryByProcess groups each step with a proposedHookPoint, memoryNote non-empty; git status --short -> no path under .claude/ or .githooks/; cargo test --release --lib hardening::tests::step_trigger -> 2 passed
        part dcProcessStepsAreHookGateOrMemoryDoDR1 : TestResult { :>> id = "2788fc9c-40d7-4e98-86f0-f8b5d4d80498"; :>> outcome = VerdictKind::proposed; :>> judgedAgainst = "51410ba"; :>> judgedAt = "2026-09-12"; :>> judgedBy = "claudeFable5"; }
        action dcReleaseAssetsCarryChecksums;
        verification dcReleaseAssetsCarryChecksumsDoD : Test { :>> id = "dc4713a9-7631-4453-a44a-11009af1e33e"; :>> method = VerificationMethod::test; :>> procedureText = "DONE MEANS: a keel release cannot publish a binary without its SHA-256 beside it, and the release process names the checksum at every step that consumes it. Resolves issue417 and issue418. DO: .github/workflows/release.yml hashes each staged asset in the job that built it and attaches `<asset>.sha256` (sha256sum format) with the binary; a `checksums` job after the matrix downloads every `.sha256`, writes one `SHA256SUMS`, downloads the binaries and VERIFIES them against it with `sha256sum -c` before attaching it - the run itself proves the published bytes are the built bytes. Guard `release-checksums-published` (HARD) fails a workflow that attaches release assets without hashing them and publishing the hash; guard `wrapper-pin-checksummed` (WARN) reports when the pinned engine version has no entry in keel-wrapper.toml for a release asset the wrapper can download. The release skill's step 3 verifies the downloaded asset against the published SHA256SUMS and copies the entries into keel-wrapper.toml before step 4 records the Release; keel-wrapper.toml gains the 0.4.1 entries computed from the published assets. VERIFY: the guard test constructs a release workflow with and without the checksum step and reads FAIL / clean; the wrapper guard test reads WARN on a pin with no entry and clean with one; `keel guard` is clean on this tree with both guards enforced; the release skill and deploy process text name the step."; }
        // RAN: same evidence as storyReleaseChecksumsDoD in sprint611: release.yml hash steps + checksums job; guards release-checksums-published (HARD) and wrapper-pin-checksummed (WARN) with 6 tests; keel-wrapper.toml 0.4.1 entries; release skill + deploy process name the step; keel guard exit 0
        part dcReleaseAssetsCarryChecksumsDoDR1 : TestResult { :>> id = "064dc855-df5b-4f57-ad27-c1088e922adf"; :>> outcome = VerdictKind::pass; :>> judgedAgainst = "b54cf82ed6fc3da94262fcb7ea8eea80b3e8749a"; :>> judgedAt = "2026-09-08"; :>> judgedBy = "claudeOpus5"; }
        action dcTestResultSkillNamesTheBinding;
        verification dcTestResultSkillNamesTheBindingDoD : Test { :>> id = "98cb14d6-1b75-4a08-878e-1c2e6e985d49"; :>> method = VerificationMethod::inspect; :>> procedureText = "DONE when the test-result skill's anti-pattern watchlist (items 2 and 4) and the sprint-standup skill's suspect line state the binding rule dcResultBindsToItsLandingCommit landed: a pass recorded on a dirty tree names the HEAD before its work and binds to the commit that introduces it once judgedAgainst is that commit's ancestor, so the validity signal is the BINDING commit's ancestry, and a suspect is a dependency or own-DoD change since the binding commit (`keel show suspect . --explain`), not `judgedAgainst != HEAD`. FOUND at sprint 624: the wording was corrected in the same commit as the code and the process-change guard refused it - `.engine/skills` is under the D0070 hard lock, and a two-sentence skill edit is outside standing consent (D0337) - so the code landed with usage.md carrying the note and the skills unchanged. DO: record the process-change Decision (marker `process-change`, NOT A FORK) whose consequence is exactly this wording, let the human accept it through the brief, then apply the edit and `keel sync-claude`. VERIFY: grep judgedAgainst over .engine/skills finds no claim that HEAD-equality alone is the validity or suspect signal; sync-claude --check clean."; }
        part dcTestResultSkillNamesTheBindingDoDR1 : TestResult { :>> id = "e51e0605-cbe6-4d3d-80d3-8da2fb6549ab"; :>> outcome = VerdictKind::proposed; :>> judgedAgainst = "eda9647"; :>> judgedAt = "2026-09-13"; :>> judgedBy = "claudeFable5"; }
        action dcRetroNamesDecisionsAsWritten;
        verification dcRetroNamesDecisionsAsWrittenDoD : Test { :>> id = "a16cc404-6c96-4e35-b7d9-0dd0cb0a81fc"; :>> method = VerificationMethod::test; :>> procedureText = "DONE MEANS: a retro that names a Decision the way every document in this repository names one is read as naming it. Resolves issue424: the retro-backlog guard's named_items reads `d0388` and not `D0388`, while CLAUDE.md, every commit message, every DoD and the guard's own error text write the uppercase form - so sprint 627's retro, justified by 'already tracked by D0388 and its probe rule', was refused as naming no item at all, and sprint 626's identical phrase passed only because the same sentence also named an issue. A justification the guard cannot read is a justification nobody checks, which is the issue364 class again with a different mask. DO: match the Decision form case-insensitively in named_items and normalise what it returns to the item's real name, so an exists check still hits the tree; the change is guard source, so it rides a #ProspectiveChange Decision co-committed (D0209 clause 2). Do NOT accept `D0388` by lowercasing the whole retro - `Issue` and `DC` prefixes in prose are not items. VERIFY: a retro whose only named item is written `D0388` passes when d0388 exists and fails when it does not, both shown by constructing the case in the guard's unit tests; the existing lowercase and issue/dc cases are unchanged; and the guard's refusal text quotes the forms it accepts in the case it accepts them."; }
        // RAN: RAN: cargo test --release --lib -- guards -> 102 passed 0 failed incl. a_decision_named_in_uppercase_is_read_as_its_real_name and a_retro_justified_by_an_uppercase_decision_passes_when_it_exists_and_fails_when_it_does_not; cargo clippy --release --lib -> Finished
        part dcRetroNamesDecisionsAsWrittenDoDR1 : TestResult { :>> id = "6c70a4ca-e28f-4400-b1f0-9318f3a6a3f4"; :>> outcome = VerdictKind::pass; :>> judgedAgainst = "c08b6a5"; :>> judgedAt = "2026-09-13"; :>> judgedBy = "claudeFable5"; }
        action dcOverrideBindsToOneFile;
        verification dcOverrideBindsToOneFileDoD : Test { :>> id = "d9047f8e-f018-4a38-a774-1243f8311158"; :>> method = VerificationMethod::test; :>> procedureText = "DONE MEANS: an override unlock covers exactly one file. Resolves issue427 (found by stpa-self run 2, UCA-O1): keel-cli/src/main.rs consume_override matches the unlock by substring in either direction - written_path.contains(target) || target.contains(written_path) - so keel override .tracking --reason '...' arms an unlock that the next write to ANY path containing .tracking consumes, and a one-character target covers every path that contains that character; the unlock is single-use and expires in 900 s, so the exposure is one write of the agent's choosing, recorded as an obligation naming the path actually written. DO: keel override refuses a target that is not an existing regular file (or a single new file path under an API-owned surface), stores the path canonicalised, and consume_override matches by canonical equality only; the refusal names the file-not-directory rule. VERIFY: a test constructs an unlock for a directory and shows override refuses it; an unlock for file A is not consumed by a write to file B that contains A's name as a substring; the ordinary one-file override still consumes once and records its obligation."; }
        // RAN: RAN: cargo test --release --bin keel -- override -> 1 passed (override_unlocks_exactly_one_file); cargo test --release --test remaining_controls_actually_fire -- override -> 1 passed unchanged; cargo clippy --release --lib --bin keel -> Finished; keel-serve.exe override .tracking -> exit 2 refusal names ONE FILE, no unlock written
        part dcOverrideBindsToOneFileDoDR1 : TestResult { :>> id = "13c2a90a-6fb3-45f2-a133-0c09663cf81d"; :>> outcome = VerdictKind::pass; :>> judgedAgainst = "c364492"; :>> judgedAt = "2026-09-13"; :>> judgedBy = "claudeFable5"; }
        action dcDirectionDecisionsLinkTheirStatement;
        verification dcDirectionDecisionsLinkTheirStatementDoD : Test { :>> id = "928cd730-e601-4fb7-8d61-7fd456c2ddd0"; :>> method = VerificationMethod::test; :>> procedureText = "DONE MEANS: a Decision or task that cites the human's direction carries their words as a Statement it links to, not as prose the agent typed. Resolves issue428 (found by stpa-self run 2, UCA-H1): humanDirects is prose that nothing parses - the computed control structure says so - and today a Decision may say 'the human's words: ...' in its context or rationale with no Statement recorded and no #DerivedFrom edge, so the tree holds the AGENT's rendering of what the human said and nothing to check it against; the intake path (keel record statement, D0216/D0236) exists but only the elicitation process is bound to it, and keel hardening (D0166) reports unsourced items as a view rather than gating them. DO: a guard clause that reads a Decision or task DoD quoting the human (a quoted span attributed to a declared Person, or the phrases 'their words' / 'the human's words') and requires a #DerivedFrom edge to a Statement whose text contains that span verbatim; forward-only from the Decision recorded, grandfathering the existing ones and counting them. VERIFY: a constructed Decision quoting the human with no Statement is refused by the guard; one with the Statement and the edge passes; a Decision quoting nobody is untouched; the count of grandfathered citing Decisions is printed once."; }
        // RAN: RAN: cargo clippy --workspace --all-targets -- -D warnings -> Finished; cargo test --release --lib -- direction_cited -> 4 passed; cargo test --release --lib -- guards -> 106 passed 0 failed; keel-serve gate guard direction-cited -> PASS 1883 scanned, 0 violation(s), 1 counted-history line (8 citing Decisions, 6 undated DoDs); gate guard --no-receipt -> ALL PASS; gate validate -> 789 clean; gate check-engine -> clean
        part dcDirectionDecisionsLinkTheirStatementDoDR1 : TestResult { :>> id = "a62c92f1-5490-4084-8383-070cf0aaaad5"; :>> outcome = VerdictKind::pass; :>> judgedAgainst = "860c078"; :>> judgedAt = "2026-09-13"; :>> judgedBy = "claudeFable5"; }
        action dcDominanceRechosenUnderItsOwnRule;
        verification dcDominanceRechosenUnderItsOwnRuleDoD : Test { :>> id = "203896b8-f0cf-4979-af15-51a8ede9b26d"; :>> method = VerificationMethod::test; :>> procedureText = "DONE MEANS: the dominant-source bonus's setting is chosen under D0364's own rule on the tree as it stands, by the sweep, and the choice is recorded. FOUND 2026-09-09 by the first --sweep run (sprint 636): on the default one-hop arm, DOMINANCE=0 gives 46/50 at median position 2 with top-3 33/46 and DOMINANCE=1.25 gives 46/50 at median position 3 with top-3 29/46 - the sweep reads DISCRIMINATED, median position moved 2..3. D0364 took 1.25 'subject to NO regression on the default one-hop set (hits, median position and mean rows all held)' and refused the settings that bought the far set with the near one; on today's tree the taken setting costs the near set one median position and four top-3 placements, while on the two-hop arm it still buys hits (19/50 -> 24/50). Whether that is the tree having grown past the rule (17311 items now) or the rule needing a weight the two-hop gain is worth is a judgment, not a measurement. DO: sweep DOMINANCE over off and at least three settings on BOTH arms with recall_bench.py --sweep; apply D0364's rule to the two verdict lines; if the setting changes, record a Decision with #SupersedeClause on D0364 carrying both sweeps' lines verbatim and change the constant; if the rule itself is what moves, that is a fork for the human, surfaced through decision-surfacing with both sweeps as the evidence. VERIFY: the recorded Decision (or the note that 1.25 stands) quotes both arms' verdict lines from the same tree SHA; the plain default run and the plain --hops 2 run after the change print the numbers those lines predict."; }
        // RAN: RAN: python .engine/tools/recall_bench.py (plain default, one-hop, 50 cases) and python .engine/tools/recall_bench.py --hops 2 at 2beaa66, binary keel 0.4.1 build 4d38dd7 unchanged through both runs (compiled DOMINANCE 1.25, unchanged under D0466 option B). One-hop: KG hit 43/50, hit position median 3, top-3 25/43, mean rows 12, McNemar p=0.000 on 38 discordant pairs. Two-hop: KG hit 21/50, median 4, top-3 8/21, mean rows 12, p=0.001 on 15 pairs. AGAINST THE PREDICTION (D0466 research line, 1.25 rows at 25e4c04: 46/50 median 3 top-3 27/46; 23/50 median 4 top-3 8/23): median positions 3 and 4 and rows 12 print exactly; hit counts drift 46 to 43 and 23 to 21 on a tree 2291 items larger (19602 against 17311) with a fresh 50-case draw - the sample-size finding D0466 is about. The choice: recorded 2026-09-14 by d0466AcceptR1 (wweatherholtz, option B) - the weighted rule of D0464 reads at --cases 100, where 1.25 is admissible and highest (48 against 39, near median 2 to 3, hits 90 and rows 12 held) and 1.1 is refused (near median 2 to 4); both arms' 100-case verdict lines from the same tree eda9647 are quoted in D0466 and now in the DOMINANCE provenance comment (keel-cli/src/view/knowledge.rs). The constant does not change; issue430 resolves by this result.
        part dcDominanceRechosenUnderItsOwnRuleDoDR1 : TestResult { :>> id = "7dea4e51-6144-42aa-b72b-645a90efde13"; :>> outcome = VerdictKind::pass; :>> judgedAgainst = "2beaa66"; :>> judgedAt = "2026-09-14"; :>> judgedBy = "claudeFable5"; }
        action dcPrefixLeavesRoomForTheRoute;
        verification dcPrefixLeavesRoomForTheRouteDoD : Test { :>> id = "432e2cfb-f57d-47c4-9fb8-2afc451a9a2d"; :>> method = VerificationMethod::test; :>> procedureText = "DONE MEANS: the routing rig tells a turn that ran out of budget after a declared prefix apart from a turn that invoked nothing. Resolves issue432: the whole-turn verdict read the release case 3/3 none at 3 turns with intake as the prefix in every sample and tool calls to the last turn, so `none` was reading the budget, not the route. DO: in routing_probe.py score a sample `budget` when a declared prefix was invoked, the intended skill never appeared, and the sample's tool calls reached the turn budget; keep `none` for a turn with no Skill call at all or one whose calls stopped short of the budget; add the transcript to `--probe`; then re-run `--investigate release --samples 3 --turns 6` and record the receipt on this item - routed, wrong, budget or none, unanimous or disagreeing for a reason the samples show, which becomes the next Issue against the check. VERIFY: `--probe` holds the new case (intake, then two non-Skill turns to a 3-turn budget = budget; intake alone with one turn left = none); the 6-turn re-run's finding line and measured spend are quoted in the RAN receipt; no rate or standing number is introduced (D0378 C)."; }
        // RAN: python .engine/tools/routing_probe.py --probe -> all 12 cases hold, all 8 rubric cases hold; --investigate release --samples 3 --turns 6 -> ROUTED release: 3/3 samples agree, prefix intake in every sample, spend 3.95 USD over 3 run(s), 87s wall (per run 1.3165 USD, 66.8s); gate validate 796 clean, check-engine clean, gate guard --no-receipt ALL PASS on c8df10d with the sprint and issue519 in the tree
        part dcPrefixLeavesRoomForTheRouteDoDR1 : TestResult { :>> id = "371c8c23-204a-4d09-bb98-c7339b635c0e"; :>> outcome = VerdictKind::pass; :>> judgedAgainst = "c8df10d"; :>> judgedAt = "2026-09-13"; :>> judgedBy = "claudeFable5"; }
        action dcCitationCheckHoldsWhereTheDecisionsLive;
        verification dcCitationCheckHoldsWhereTheDecisionsLiveDoD : Test { :>> id = "e3e41fd2-c394-434d-a61a-a29d5029f9f7"; :>> method = VerificationMethod::test; :>> procedureText = "Resolves issue433 (D0419). The synopsis-citation check of guard cli-surface-declared runs only where the engine's Decision channel lives: decision_ids_present(root) contains d0271 (the Decision that made the CLI surface an authored fact). A tree without it - a keel init scaffold, a downstream project with its own Decisions, a test fixture shaped like the self-build - gets the surface/dispatch/help checks and no citation check. VERIFY: unit test citations_are_read_only_where_the_engines_decisions_live - the engine's commands.sysml in a temp root with no Decisions yields 0 citation violations (known-negative), and with a 0271- file yields at least 12 (known-positive); the_live_synopses_cite_only_live_decisions still holds on the live tree; adoption_check_can_fail and push_gate_is_withdrawn pass; CI green on the landing commit read from gh run list --json conclusion."; }
        // RAN: guards.rs citation block gated on decision_ids_present(root).contains(d0271); lib test citations_are_read_only_where_the_engines_decisions_live ok (0 without Decisions, >=12 with a 0271- file); adoption_check_can_fail + push_gate_is_withdrawn 4 passed 0 failed in tests639b.log; keel guard 68 PASS
        part dcCitationCheckHoldsWhereTheDecisionsLiveDoDR1 : TestResult { :>> id = "e6eee846-8664-43ef-85f0-13fd24ff05db"; :>> outcome = VerdictKind::pass; :>> judgedAgainst = "afd90d0"; :>> judgedAt = "2026-09-09"; :>> judgedBy = "claudeOpus5"; }
        action dcLandNamesTheCiVerdictOfTheBase;
        verification dcLandNamesTheCiVerdictOfTheBaseDoD : Test { :>> id = "ded75e26-021a-4a88-81b7-bb734f0b3ecc"; :>> method = VerificationMethod::test; :>> procedureText = "Resolves issue434 (D0420). keel land names the CI verdict of the base before every push: after the held-items warning it resolves origin/<branch>, reads the verdict through status::ci_verdict (the one reading of a CI verdict in the binary, extracted from ci_section so keel status and keel land read the same field) and prints one line, keel land: CI on the base origin/<branch>: <sha7> passed | FAILED | still running | no run found; a FAILED base adds one line saying main stays red unless this push is its fix and that a report cites gh run list --json conclusion, never a wrapper's exit code. ADVISORY only: land never refuses on it - a red base is what the fixing push lands on. Silent when origin is not a GitHub remote or origin/<branch> does not resolve. VERIFY: the two land fixtures (bare origin) print no CI line and stay green; a live keel land . on this repository prints the line for origin/main; CLAUDE.md names the rule."; }
        // RAN: status.rs ci_verdict extracted from ci_section; sync.rs name_ci_verdict_of_base called from cmd_land, advisory; push_gate_is_withdrawn (bare origin) prints no CI line and passes; the live line is read at keel land . of this sprint; CLAUDE.md names the rule
        part dcLandNamesTheCiVerdictOfTheBaseDoDR1 : TestResult { :>> id = "7f4132ed-7413-4fa7-9949-228f2254f249"; :>> outcome = VerdictKind::pass; :>> judgedAgainst = "afd90d0"; :>> judgedAt = "2026-09-09"; :>> judgedBy = "claudeOpus5"; }
        action dcHookLatencyIsAnIndicator;
        verification dcHookLatencyIsAnIndicatorDoD : Test { :>> id = "c6544408-41bb-4afe-a6d3-30822501ea4e"; :>> method = VerificationMethod::test; :>> procedureText = "issue442 is resolved - keel show indicators carries a computed hookLatencyIndicator (the fire-ledger's stop-hook p90 in ms over the last 25 fires, D0389) and a gitFactsSizeIndicator (the git-facts.toml byte length), both direction-aware (minimize), and indicator-triggers.toml declares a threshold for each with the work it surfaces named. VERIFY: keel show indicators lists both with a live value on this tree; with a threshold set below the live value the indicator appears under triggered and in keel orient's burndown, and with it set above it does not (the known-positive and known-negative probe); the guard set stays green."; }
        // RAN: cargo test --release --lib pm::tests::the_recent_sample_is_the_last_n_fires_of_one_event -> 1 passed 0 failed; cargo clippy --release -p keel-cli --all-targets -- -D warnings -> exit 0; cargo build --release -> exit 0; keel show indicators . -> hookLatencyIndicator latest 14125.00 ms trigger above 10000 crossed true, gitFactsSizeIndicator latest 4069615.00 bytes trigger above 8000000 crossed false, equal to an independent python read of the same ledger and file (p90 14125, bytes 4069615); D0388 pair: thresholds 10000/4000000 -> both indicators in indicators.triggered AND orient.burndown.triggers, thresholds 20000/8000000 -> neither in either, contract restored byte-for-byte -> PAIR HOLDS; keel gate validate . -> 797 tracking file(s) validated clean; keel gate check-engine . -> .engine instance files validated clean; keel gate guard --no-receipt . -> [guard] ALL PASS, 325 actionable warnings across 8 guards, 0 violations, on the tree holding D0468, sprint 696, issue520 and dcDecisionScaffoldingIndexesItsEdgesOnce
        part dcHookLatencyIsAnIndicatorDoDR1 : TestResult { :>> id = "f00373f7-97e1-4068-9110-02d75e925b29"; :>> outcome = VerdictKind::pass; :>> judgedAgainst = "ce41db3"; :>> judgedAt = "2026-09-13"; :>> judgedBy = "claudeFable5"; }
        action dcTouchedCostIsMeasuredNotQuoted;
        verification dcTouchedCostIsMeasuredNotQuotedDoD : Test { :>> id = "b54508c6-8f12-4fac-924e-2b9187625592"; :>> method = VerificationMethod::inspect; :>> procedureText = "issue444 is resolved - D0421's rationale and its what-would-change-it clause carry the measured cost of the first live touched set (528 s, 16 binaries, compile 234 s and tests 286 s, against the suite's 585 s) and name the release relink of every named binary as the driver and the one-binary consolidation as the lever, so the acceptance the human is asked for binds to the measured text (D0308). VERIFY: grep MEASURED .engine/decisions/0421-touchedTestsRunBeforeLand.sysml names 5fbe410 and 528 s; keel validate and check-engine clean; the ask presented to the human quotes the same figures."; }
        // RAN: grep MEASURED .engine/decisions/0421-touchedTestsRunBeforeLand.sysml -> names 5fbe410, 528 s, 234 s compile, 286 s tests, suite 585 s; keel validate 731 clean; check-engine clean; the ask in this turn quotes the same figures
        part dcTouchedCostIsMeasuredNotQuotedDoDR1 : TestResult { :>> id = "90aef94f-f0c8-479e-a2da-78e48c8c3c36"; :>> outcome = VerdictKind::pass; :>> judgedAgainst = "4192458"; :>> judgedAt = "2026-09-09T23:30:00-06:00"; :>> judgedBy = "claudeOpus5"; }
        action dcGateDecisionCarriesItsMeasuredCost;
        verification dcGateDecisionCarriesItsMeasuredCostDoD : Test { :>> id = "c8498443-8dc0-4ae8-9fd5-85becd8d0cee"; :>> method = VerificationMethod::test; :>> procedureText = "A proposed #ProspectiveChange Decision whose decision text adds a refusal on the land or push path (names land, push, refuse or gate) carries a MEASURED: token in its rationale naming the run, the host and the seconds the control cost on a live set, or the decision-scaffolding guard WARNS naming the Decision - so a gate is never asked for at a fixture's price again (issue444: D0421 said seconds, the first live set cost 528 s). VERIFY: the guard warns on a fixture Decision with the path words and no token (known positive), stays silent on D0421 as corrected and on a Decision with no path words (known negatives); its own process-change Decision is recorded and the guard is inert until accepted (D0337)."; }
        // RAN: cargo test --release --lib guards::unmeasured_path_tests -> 1 passed 0 failed (D0388 trio: proposed Decision with land/push/refuse and no token NAMED; D0421's corrected shape with MEASURED: silent; no path words silent; accepted Decision not read; landing/pushed/gateway/refuses not the words; Land/PUSH any case named); first run failed on the fixture saying refuses - corrected to the whole word; cargo clippy --release -p keel-cli --all-targets -- -D warnings -> exit 0; cargo build --release -> exit 0, copied to keel-serve.exe; cost pair on host 0F3DGVX25193H7: gate guard --no-receipt before the clause 7.6 s median (7.2/7.6/10.4), with it 7.3 s median (6.5/7.3/7.8), inert clause inside the noise; live mirror: on acceptance the guard would name d0467 (gate) and no other proposed marked Decision; keel gate validate . -> 799 tracking file(s) validated clean; keel gate check-engine . -> .engine instance files validated clean; keel gate guard --no-receipt . -> [guard] ALL PASS, 0 violations, on the tree holding D0469, the guards.rs clause, the guards.md row, sprint 697 and the triaged obligation7d57a5b8 (the red before D0469 was recorded was process-change naming keel-cli/src/guards.rs, cleared by the Decision; the yield obligation is resolved by d0469, which names it)
        part dcGateDecisionCarriesItsMeasuredCostDoDR1 : TestResult { :>> id = "f6e52a94-2025-480c-9955-e0576ae3bec5"; :>> outcome = VerdictKind::pass; :>> judgedAgainst = "61bb6a9"; :>> judgedAt = "2026-09-13"; :>> judgedBy = "claudeFable5"; }
        action dcUnsignedTapIsRecordedWithAWarn;
        verification dcUnsignedTapIsRecordedWithAWarnDoD : Test { :>> id = "295fad63-fd1a-4863-b682-f711bad376b1"; :>> method = VerificationMethod::test; :>> procedureText = "An unsigned, unpaired or mis-signed console/deck tap RECORDS, with a WARN line in the note, instead of being refused with 401 - resolves issue447 (D0426: the tap is the human's own act at their own console, and the D0334/D0335 signature refusal was observed to fall on no one but them). (a) serve.rs: TapReceipt replaces require_device on all six write routes (sitting review, disposition, decision accept, decision reject, gate result, test result); a verified tap appends the D0411 device citation, an unverified one appends WARN: unsigned tap - reason (D0426). (b) device::reverify of a WARN note is Err, so the verified badge is what pairing buys and nothing else. (c) tests/device_bound_taps.rs covers both: no device -> 200 and the record carries AcceptR1 + WARN + no HMAC-verified; wrong signature -> 200 + WARN does not match; paired + correct signature -> HMAC-verified and reverify Ok. (d) The census strikes recorded alongside: acceptance-binds-to-text (falls on the agent's edit of signed text, issue371), the no-quote delegated-record refusal (paraphrase is D0198 fabrication, the agent's act) and enroll with a wrong pairing code (key-exchange integrity; costs the human only the badge) are NOT dissolved, and the reason is in the Issue's description so the D0426 candidate list is closed out visibly. VERIFY: cargo test --release --test device_bound_taps passes; grep require_device keel-cli/src/serve.rs finds nothing."; }
        // RAN: verifier receipt (D0425): lib 454/0 + parser 32/0; device_bound_taps 1/0; hook_and_push_controls_actually_fire 8/0; accept_honours_delegation 4/0; reject_has_a_cli_path 4/0; gesture_citation_is_the_commands 2/0; acceptance_binds_to_text 1/0; validate 734 clean; check-engine clean; guard ALL PASS (66 warnings/8 guards); enforcement-report refusals rows + commit-gate-{validate,guard,check-engine} present; DISCREPANCIES none
        part dcUnsignedTapIsRecordedWithAWarnDoDR2 : TestResult { :>> id = "e5839217-cc18-4ef7-a29b-a1c1bf85b717"; :>> outcome = VerdictKind::pass; :>> judgedAgainst = "94a7f0b60cabb308eb971c0fb17e101e66756c6f"; :>> judgedAt = "2026-09-10"; :>> judgedBy = "claudeOpus5"; }
        action dcDelegatedCeremonyIsASkill;
        verification dcDelegatedCeremonyIsASkillDoD : Test { :>> id = "b33bcf3e-b4ea-41e2-9737-5ef4a7bc1726"; :>> method = VerificationMethod::test; :>> procedureText = "The D0425 verifier and recorder roles are a deployed skill and process, not an ad-hoc brief - resolves obligationf1702eed. Sprint 647's recorder ran on a prompt written for the occasion and (1) invented a #Addresses marker no schema declares, turning the Stop hook red twice and yielding a red-yield obligation, (2) hand-deleted three TestResult parts it had recorded without --evidence and re-recorded them, and (3) reported 'All issues resolved ... ready for commit' over a tree whose guard was FAILED. DONE MEANS: (a) .engine/processes/delegated-ceremony.sysml names the two roles, what each may read (the verifier: the tree and the commands - which include cargo clippy, since sprint 647's commit hook failed on a nursery lint the verifier's brief never ran; the recorder: the verifier's receipt file ONLY) and what each may write (the verifier: nothing; the recorder: keel write-API calls, never a file edit - a sprint record's edges come from new sprint --fill, and a marker the recorder needs that the vocabulary lacks is a refusal to report, not a line to type); (b) a delegated-ceremony skill under .claude/skills/ carries the two briefs verbatim so the primary dispatches by pointing at the skill and the receipt path, and the process-skill guard binds them; (c) the recorder's brief requires its report to END with the verbatim last line of keel gate --fast . run after its last write, so a subagent's summary cannot outrun the gate; (d) the subagent-stop hook's block, when it fires for a recorder, is a refused-class ledger line naming control recorder:tree-red so the census can count how often a recorder leaves a red tree. VERIFY: a fixture recorder brief that types an undeclared marker is refused by the skill's own check (known positive) and the sprint 647 receipt-driven brief passes (known negative); keel guard process-skill PASS."; }
        // RAN: RAN: PROBE PAIR: python .claude/skills/delegated-ceremony/references/check_report.py --probe --root . -> positive fixtures/positive-undeclared-marker.txt: REFUSED; negative fixtures/negative-sprint647-receipt-driven.txt: PASS; PROBE PAIR: cargo test --release --bin keel subagent_block_control_tests -> 1 test: ok; cargo clippy --release -p keel-cli --all-targets -- -D warnings -> pass; exit=0; KEEL gate guard --no-receipt . -> PASS 73; exit=0
        part dcDelegatedCeremonyIsASkillDoDR1 : TestResult { :>> id = "193195a1-cbb5-477b-bc9d-d3b02038ac3e"; :>> outcome = VerdictKind::pass; :>> judgedAgainst = "b9754c5"; :>> judgedAt = "2026-09-13"; :>> judgedBy = "claudeFable5"; }
        action dcWritePathCensusRowsHaveARefusalBehindThem;
        verification dcWritePathCensusRowsHaveARefusalBehindThemDoD : Test { :>> id = "b34a39c3-2c74-47af-bf25-431082010914"; :>> method = VerificationMethod::test; :>> procedureText = "issue449 is resolved - every `active` row in census.rs WRITE_PATH_CHECKS is held to a refusal site in code by a unit test, so a write-path control the census reports is one the verb enforces. The test derives, for each active row's `verb:check` name, the WriteError variant or the `refuse_*` function that produces it (a registry in write.rs naming verb -> check -> variant, read by both the census and the test), and fails naming any row with no refusal behind it and any refusal with no row. VERIFY (probe pair): with the registry entry for append-gate-result:ran-receipt removed the test fails naming that row; with an extra row `append-result:fictional` added the test fails naming it; on the real tree it passes; clippy clean."; }
        // RAN: TOUCHED RECEIPT: outcome=pass passed=794 failed=0 seconds=1074 at=1789332683 launch=1789331604 (at>launch: ok); D0388 PROBE PAIR CHECK: cargo test --release -p keel-cli --lib -- write_path_registry_tests:: census::tests::every_live_row_has_a_refusal_and_every_refusal_a_row; BASELINE -> test result: ok. 4 passed; 0 failed; exit=0; KNOWN-POSITIVE CASE 1 (entry): python probe.py on entry -> probe entry on; exit=0; cargo test ... -> test result: FAILED. 1 passed; 3 failed; failures: every_live_row_has_a_refusal_and_every_refusal_a_row (names 'append-gate-result:ran-receipt'), every_ledgered_refusal_in_main_is_registered (names 'append-gate-result:ran-receipt'), a_lookup_finds_a_registered_pair_and_not_a_fictional_one; exit=1; python probe.py off entry -> probe entry off; exit=0; KNOWN-POSITIVE CASE 2 (row): python probe.py on row -> probe row on; exit=0; cargo test ... -> test result: FAILED. 3 passed; 1 failed; failure: every_live_row_has_a_refusal_and_every_refusal_a_row (names 'append-result:fictional'); exit=1; python probe.py off row -> probe row off; exit=0; KNOWN-NEGATIVE CASE (clean tree after restores): cargo test ... -> test result: ok. 4 passed; 0 failed; exit=0; cargo clippy --release -p keel-cli --all-targets -- -D warnings -> Finished; exit=0
        part dcWritePathCensusRowsHaveARefusalBehindThemDoDR1 : TestResult { :>> id = "fe0347b9-0d1a-4a2d-83ab-ea787ef16c53"; :>> outcome = VerdictKind::pass; :>> judgedAgainst = "4b7467c"; :>> judgedAt = "2026-09-13"; :>> judgedBy = "claudeFable5"; }
        action dcRetroBacklogReadsTheWorkingTree;
        verification dcRetroBacklogReadsTheWorkingTreeDoD : Test { :>> id = "03e229a5-e8d0-4db8-ac3e-2aeb19bf28bc"; :>> method = VerificationMethod::test; :>> procedureText = "issue450 is resolved - guard retro-backlog reads the same pending change whether or not it is staged: when `git diff --cached` names no added item and no sprint text, the guard falls back to the working tree's untracked and modified paths (`git status --porcelain`) as the pending commit, so a turn-boundary or verifier run sees the retro the commit gate will see. VERIFY (probe pair): a fixture repo with an untracked sprint file whose retro names a finding and adds no item fails the guard UNSTAGED and STAGED alike; the same fixture with the named issue added in the working tree passes both ways; the guard's report names which source it read (cached / working tree); clippy clean."; }
        action dcLiteralVocabulariesAreFoundByATest;
        verification dcLiteralVocabulariesAreFoundByATestDoD : Test { :>> id = "f462036b-e347-4a73-99ed-4af572aa81d8"; :>> method = VerificationMethod::test; :>> procedureText = "Resolves issue452. A unit test in keel-cli (the control for the issue300/issue451 class) walks every enum the embedded schema declares and fails on any string-slice literal in keel-cli/src that names three or more of that enum's members without the enclosing function reading them through schema::enum_members / enum_members_union / project_enum_members; the test is probed against a planted literal (fails) and the tree at HEAD (passes) and its receipt names both. usage.md's method list is the schema's, not a third copy."; }
        action dcLandRunIsAFactUntilItFinishes;
        verification dcLandRunIsAFactUntilItFinishesDoD : Test { :>> id = "b1a6ac60-4bc3-4f70-9c4c-40426958771a"; :>> method = VerificationMethod::test; :>> procedureText = "Resolves issue453. `keel land` writes `.keel/metrics/land-run.toml` when it starts (HEAD, branch, started-at, pid, the touched set's size) and rewrites it with the outcome when it finishes (pushed SHA or the refusal); `keel status` and `keel orient`'s sync line name a land that started and has no outcome as `land in progress since <time> (pid N)` while the pid is alive and as `land died at <step>` once it is not, and `keel land` itself reports the prior unfinished run before starting. VERIFY: an integration test seeds the marker with a dead pid and reads the `died` line from status; the live check is a land killed mid-run being named by the next `keel status`."; }
        action dcFillRefusesARetroTheGuardWouldRefuse;
        verification dcFillRefusesARetroTheGuardWouldRefuseDoD : Test { :>> id = "511bb309-897c-4e2a-99a3-bb90eef686c7"; :>> method = VerificationMethod::test; :>> procedureText = "Resolves obligationf1f440ee. `keel new sprint --fill` runs the ceremony guard's own retro predicate (the issue011 avoidable-issue-scan vocabulary) over the draft's retro section before scaffolding and REFUSES a section that would fail it, naming the words the guard reads for - the predicate is one function shared by the guard and the write path, so they cannot drift. VERIFY: a unit test fills a sprint from a retro section with no scan vocabulary and asserts the refusal names the vocabulary and writes no file; a second fills one that carries it and asserts the ceremony guard passes the scaffolded record."; }
        action dcRecordIssueNamesOpenIssuesOnTheSameInstrument;
        verification dcRecordIssueNamesOpenIssuesOnTheSameInstrumentDoD : Test { :>> id = "6edd3d5c-65a8-4a68-8dd4-1d3b732bc384"; :>> method = VerificationMethod::test; :>> procedureText = "DONE MEANS: recording an Issue shows the recorder the open Issues already standing on the same instrument, in the command's own output, so a duplicate resolver is visible before it is added. Resolves issue457: on 2026-09-10 a new resolver task was added for issue456 (the routing rig scoring a cut-off turn as none) when issue432, recorded the day before on the same case and the same class, already had dcPrefixLeavesRoomForTheRoute as its resolver; the duplicate was found by chance - keel show priority listed an item whose name said the same thing - and removed before commit. DO: after `keel record issue` writes, it computes the set of file paths and tool names the new description mentions (a token containing a path separator or ending in .py, .rs, .sysml, .toml, .md, or a `keel <verb>` phrase), finds every Issue in the model with no done resolver whose title or description mentions one of the same tokens, and prints one line per hit: `open on the same instrument: issueNNN (resolver <item>, not done) - <title>`; nothing is refused and nothing is written beyond the Issue. VERIFY: a unit test over a fixture with one open Issue naming routing_probe.py and one done Issue naming it reports the open one only; recording a test Issue naming `.engine/tools/routing_probe.py` against this tree lists issue415, issue432 and issue456 in the output; a description naming no instrument prints nothing."; }
        action dcMigrationReconcileIsAGuard;
        verification dcMigrationReconcileIsAGuardDoD : Test { :>> id = "ff348e0e-b313-4180-9758-0f91c3d2e506"; :>> method = VerificationMethod::test; :>> procedureText = "Resolves issue465 (Medium): D0321's research, dcProcessStepDeclaresItsCheck's DoD and D0434's first text all named `marker-census` as the check of the migration process's reconcile step (mig2DryRunReconcile); the first live run of guard `step-check-resolves` refused it, because marker-census is a LENS (`.engine/cli/commands.sysml`, family lens) that nothing runs on the step - a lens a reader may consult is not a check that binds. The migration process (D0067) is therefore still `checkable = true` with no guard at any step, the admitted gap process-enforcement.toml has carried since D0173. DONE MEANS: a guard exists whose predicate is the reconcile step's claim - a commit that carries a transform under `.engine/tools/migrations/` (the shape the `ownership` guard already recognises as a D0067 migration) also carries that transform's reconciled receipt: the dry-run's control totals (conservation, no-leak, content hash) recorded where the guard can read them, so a bulk edit whose totals were never balanced FAILS at the commit rather than being trusted on the script's exit code - and mig2DryRunReconcile carries `:>> checkedBy` naming that guard, moving migration from `stepEnforcement`'s undeclared into checked. The receipt's shape and home are this item's design question; a second file the transform writes beside itself is the D0105 risk to weigh against a `// RECONCILED:` line in the transform's own docstring. VERIFY: a fixture commit with a transform and no receipt fails the guard (known-positive); the same commit with a balanced receipt passes (known-negative); `keel show hardening` reports migration's step as checked; `step-check-resolves` resolves the new binding."; }
        action dcFormatterRunIsRefusedOrPinned;
        verification dcFormatterRunIsRefusedOrPinnedDoD : Test { :>> id = "415e09af-037a-4a45-b665-9278e6b7d09f"; :>> method = VerificationMethod::test; :>> procedureText = "DONE MEANS: a `cargo fmt` or `rustfmt` invocation against this repository is refused or rendered harmless before it rewrites the crate - either the pre-bash hook names it (the crate is not rustfmt-formatted; no rustfmt.toml pins a style, so a formatter run rewrites every file it visits) and denies it in the same way it denies a backslash heredoc (D0309), or a committed rustfmt.toml reproduces the existing style closely enough that `cargo fmt --check` passes on HEAD, so a run is a no-op. Resolves issue473: on 2026-09-10 the primary ran `cargo fmt -p keel-cli` after a doc-comment fix and 137 files moved (+28937/-6442); nothing landed, and the four sprint files were recovered by replaying the sprint's textpatch scripts against HEAD with rustfmt-equality as the check. VERIFY: known-positive - a Bash call containing `cargo fmt` in this repo is refused (or `cargo fmt --check` exits 0 on HEAD); known-negative - `cargo fmt --check` in a scratch crate outside the repo is untouched by the hook; the receipt names both. Whichever course is taken is a hook-rule or repo-config change and carries its own #ProspectiveChange Decision."; }
        action dcSuiteNamesTheImageLockThatBlockedIt;
        verification dcSuiteNamesTheImageLockThatBlockedItDoD : Test { :>> id = "97084bb5-eaeb-4c7d-bee7-0e9ce57f638e"; :>> method = VerificationMethod::test; :>> procedureText = "DONE MEANS: a keel suite or keel suite --touched run whose cargo step fails to relink the crate's binary (a build error naming target/release/keel(.exe) and os error 5 / Access is denied / text file busy) writes a receipt whose outcome is `blocked`, not `fail`, and whose text names the image that was held, the processes holding it when the error was read (tasklist / lsof by image path) and the fix - run the primary's own keel commands from a copy (target/release/keel-serve.exe) while a verifier's cargo runs - so a reader never sees 61 failing tests where none ran and the recorder never records a red that was a lock. Resolves issue474: on 2026-09-10 the sprint 666 verifier's touched run read `failed to remove file target/release/keel.exe - Access is denied (os error 5)` because the primary was running `keel guard` and `keel validate` from that image to clear a stop-hook block at the same moment; the receipt listed all 61 binaries as failing. VERIFY: known-positive - a suite launched while a second process holds target/release/keel.exe open (a `keel serve` from the same path, or a sleep-holding script) writes outcome blocked naming the holder; known-negative - the same launch with the image free runs and writes pass or fail as today; the receipt names both."; }
        action dcResyncIsNotASelfModification;
        verification dcResyncIsNotASelfModificationDoD : Test { :>> id = "c414d114-3d0b-4313-acd1-0a841f7e4b38"; :>> method = VerificationMethod::test; :>> procedureText = "DONE MEANS: process-change drops from its locked set every path under .engine/ whose text under the current read (index blob in a hook, disk outside one) equals, line endings normalised, the file the judging binary embeds at the same relative path, and reports the dropped paths in one warning line; the exemption is inert in a tree holding keel-cli/Cargo.toml (the self-build, where the embedded engine is the tree) and never covers a deleted locked file. keel migrate on a lived-in project retains the update under its own D0336 gate again, and the six migration_fixture_is_realistic tests that went red on 2026-09-10 pass. Resolves issue475. VERIFY (D0388 pair, tests/resync_is_not_a_self_modification.rs): known-positive - a committed project whose .engine/skills/actor-enrollment/SKILL.md differs from the embedded text is overwritten with the embedded text and passes process-change at the terminal with no Decision, the warning line naming the path; known-negative - the same overwrite with one line appended fails naming the file; self-build case - the positive tree plus an empty keel-cli/Cargo.toml fails the same way. guards.md's process-change row names the exemption and both exclusions."; }
        // RAN: cargo test --release --test resync_is_not_a_self_modification: 3 passed (known_positive_the_embedded_text_passes_the_lock_with_no_decision, known_negative_one_appended_line_is_back_under_the_lock, the_self_build_gets_no_exemption); keel suite --touched 719 passed 0 failed at 1789107167 head c88feb2 with migration_fixture_is_realistic in the set
        part dcResyncIsNotASelfModificationDoDR1 : TestResult { :>> id = "c213cf44-2459-43d6-be35-889ebf66975d"; :>> outcome = VerdictKind::pass; :>> judgedAgainst = "c88feb2"; :>> judgedAt = "2026-09-11"; :>> judgedBy = "claudeOpus5"; }
        action dcEvidenceReceiptMarkerIsIdempotent;
        verification dcEvidenceReceiptMarkerIsIdempotentDoD : Test { :>> id = "73a3c3f5-78c0-4e77-9349-a467273822c7"; :>> method = VerificationMethod::test; :>> procedureText = "DONE MEANS: append-result and append-gate-result accept --evidence that begins with the receipt marker (with or without the comment slashes, with or without a following space) and write ONE marker - the line on disk is byte-identical whether the caller passed the marker or not - so a recorder that copies the on-disk shape it read back from an earlier sprint lands the same receipt as one that passes bare text. Resolves issue476. VERIFY: known-positive - evidence passed WITH the marker writes a single-marker line equal to the bare-text line (a lib test in write.rs beside the existing RAN line test at line 2267); known-negative - bare evidence still writes exactly one marker and empty evidence still writes none."; }
        action dcLandTestsTheCommitItPushes;
        verification dcLandTestsTheCommitItPushesDoD : Test { :>> id = "f2f9a28a-9058-4b59-938b-fc9832c14ce1"; :>> method = VerificationMethod::test; :>> procedureText = "DONE MEANS: the touched run's receipt (and keel land's, which is the same writer) proves it tested the commit it pushed - the receipt carries the deliverable's fingerprint (suite::fingerprint, the same function the suite receipt uses) taken BEFORE cargo starts and AFTER it exits, and a run whose two fingerprints differ, or whose starting fingerprint differs from the committed tree's (git stash-free: fingerprint the index or a clean checkout of HEAD, never the working tree), writes outcome tree-moved naming the paths that changed and land REFUSES the push with that line, so an edit made during the 7-14 minute window or a change left unstaged at commit time is a recorded refusal and not a receipt that names one commit and measured another. Resolves issue477. VERIFY: known-positive - a test appends one line to a keel-cli/src file after the stub is written and before the run exits (a test hook or a seam that takes the two fingerprints as inputs) and the receipt reads tree-moved naming the file; known-negative - an untouched tree writes pass or fail as today with equal fingerprints recorded; the receipt names both fingerprints."; }
        action dcWorkingTreeEolMatchesTheAttribute;
        verification dcWorkingTreeEolMatchesTheAttributeDoD : Test { :>> id = "e725f9bf-346e-4f8f-97aa-2e1875911edf"; :>> method = VerificationMethod::test; :>> procedureText = "DONE MEANS: the working tree's line endings are checked against the repository's own attribute before any run that tests the working tree - keel suite --touched, keel land and keel guard read git ls-files --eol over every tracked path (the touched run and land name the changed paths first, then the count of the rest; this clone held 140 unchanged CRLF paths under core.autocrlf = true when issue478 was found) and a path whose working-copy eol (w/crlf) differs from its declared attribute (attr/text eol=lf) is a named refusal - the touched receipt writes outcome eol-mismatch listing the paths, land refuses the push with that line, and a forward guard working-tree-eol fails naming them - so a CRLF file written by a tool that translates newlines is caught before cargo compiles it and never lands as five unrelated test failures. Resolves issue478. VERIFY (D0388 pair, named before the tree is read): known-positive - a fixture repo with .gitattributes text eol=lf and one tracked file rewritten CRLF is refused naming that one path; known-negative - the same repo with the file LF passes, and a file whose attribute is eol=crlf and is CRLF is not named. The check shells out to git once per run and adds under one second on this host (measured in the receipt's own phases)."; }
        // RAN: RAN: verifier receipt batch3 head=40190c5: keel suite --touched -> 710 passed 0 failed 700 s (touched-1789134894.log) eol_scanned 1756 eol_ms 542; keel guard working-tree-eol -> pass; working_tree_eol integration pair in the touched set; validate/check-engine exit 0
        part dcWorkingTreeEolMatchesTheAttributeDoDR1 : TestResult { :>> id = "bbb96d53-f2ce-460e-b169-def197052fe1"; :>> outcome = VerdictKind::pass; :>> judgedAgainst = "40190c5"; :>> judgedAt = "2026-09-11"; :>> judgedBy = "claudeOpus5"; }
        action dcRunningReceiptNamesItsProcess;
        verification dcRunningReceiptNamesItsProcessDoD : Test { :>> id = "21bb33a3-1468-4f48-ac28-8cb14be3547a"; :>> method = VerificationMethod::test; :>> procedureText = "DONE MEANS: the running stub keel suite / keel suite --touched writes before cargo starts carries pid (the cargo child's process id) and the log file is created empty at the same moment, so the two facts a reader needs exist from the first second; keel suite --status reads the receipt and answers one of running (pid alive, with the elapsed seconds), finished (outcome pass or fail with the counts), or died (outcome running but the pid is gone - the stub is left as evidence and the line names it); the test-verify skill's wait step is keel suite --status in a loop rather than a process-name search, and a second keel suite --touched launched while the pid is alive REFUSES naming the pid and the receipt rather than replacing the stub. Resolves issue479. VERIFY (D0388 pair, named before the tree is read): known-positive - a stub with the current process's own pid reads running, and a stub whose pid is one no process holds reads died; known-negative - a completed receipt reads finished with its counts and no pid field is consulted."; }
        action dcRecorderRefusesAReceiptNotBoundToItsDispatch;
        verification dcRecorderRefusesAReceiptNotBoundToItsDispatchDoD : Test { :>> id = "69887262-3fa0-4955-bb55-d234c9d2278d"; :>> method = VerificationMethod::test; :>> procedureText = "DONE MEANS: a recorder skill (test-record) exists beside test-verify and is the recorder's whole procedure: it reads ONE receipt path, refuses a receipt whose header does not carry the dispatch token the primary passed (a token the verifier's dispatch also carries and the test-verify skill writes into the header line), whose head differs from the dispatch's sha, or whose file mtime is before the dispatch epoch - naming which of the three failed - and only then writes the gates and DoD results with evidence quoting the receipt's counts; the test-verify skill's receipt step ends with the proof of the write (ls and grep of the path returned verbatim) so a returned-but-unwritten receipt is visible in the verifier's own final message. Resolves issue480. VERIFY (D0388 pair, named before the tree is read): known-positive - a receipt with the token, the sha and an mtime after the epoch is accepted; known-negative - the same receipt with yesterday's mtime is refused naming mtime, and one with a different head is refused naming head."; }
        action dcReceiptShapeCensusIsASensor;
        verification dcReceiptShapeCensusIsASensorDoD : Test { :>> id = "1ec29864-69f8-4518-8ccb-6de1d31a1e12"; :>> method = VerificationMethod::test; :>> procedureText = "DONE MEANS: the receipt-shape census that D0444 quotes (283 prefixed RAN receipts; a prefix rule admits 283 narratives, the alphabet rule admits 1, alphabet plus the sixteen function words admits 0) is a committed Sensor at scripts/probes/receipt_shape_census.py, not a session scratch file: it reads every .tracking RAN receipt, classes each by reverify::is_replayable rule as implemented (prefix, alphabet, function words), prints the three counts and the false positives by text, and carries --probe with one known-positive receipt (keel show control-structure . --svg) and one known-negative (keel suite 571 passed, 0 failed) that it runs before the tree (D0388). VERIFY: python scripts/probes/receipt_shape_census.py --probe exits 0 naming both cases; the plain run over this tree prints the three counts and the count under the full rule equals what keel attestation . --json reports as demoReplayable."; }
        // RAN: verifier receipt batch1: receipt_shape_census.py --probe exit 0; census 283 prefixed / alphabet 1 / full rule 0 = attestation demoReplayable 0
        part dcReceiptShapeCensusIsASensorDoDR1 : TestResult { :>> id = "81722fde-c54c-4a0d-9e29-22a8b2fb933d"; :>> outcome = VerdictKind::pass; :>> judgedAgainst = "b8fab64"; :>> judgedAt = "2026-09-11"; :>> judgedBy = "claudeOpus5"; }
        action dcSelfBuildHookTestDoesNotRaceTheClock;
        verification dcSelfBuildHookTestDoesNotRaceTheClockDoD : Test { :>> id = "4f0b8667-5fae-412a-81bc-d4b308763777"; :>> method = VerificationMethod::test; :>> procedureText = "DONE MEANS: an_output_still_linking_is_not_copied in keel-cli/tests/self_build_hooks_leave_the_build_tree.rs no longer depends on how fast the spawned hook process starts: the still-linking fixture carries an mtime the two-second grace cannot age past during the run (set into the future, where needs_refresh's saturating subtraction reads 0), with a comment naming issue481 and why. VERIFY: cargo test --release --test self_build_hooks_leave_the_build_tree passes 5 of 5; the same binary passes 5 of 5 when run under load beside a cargo build; no integration test in keel-cli/tests sets a fixture mtime to SystemTime::now() and then asserts a grace-window decision (grep for set_modified(std::time::SystemTime::now()) returns nothing)."; }
        // RAN: verifier receipt 481 2026-09-11 head=fe715c2: cargo test --release --test self_build_hooks_leave_the_build_tree test result: ok. 5 passed; 0 failed exit 0; grep now()-mtime fixtures 0; fixture from_secs(600) yes, issue481 named yes; validate 763 clean exit 0; guard ALL PASS exit 0; clippy -D warnings exit 0; DISCREPANCIES: NONE. D0388 pair: negative .keel/metrics/touched-1789122462.log line 1003 (pre-fix fixture FAILED under land load), positive patched binary 5 of 5 with 41 CPU burners live
        part dcSelfBuildHookTestDoesNotRaceTheClockDoDR1 : TestResult { :>> id = "af9d4eb4-278f-4477-a199-c6159f05ea9e"; :>> outcome = VerdictKind::pass; :>> judgedAgainst = "fe715c2"; :>> judgedAt = "2026-09-11"; :>> judgedBy = "claudeOpus5"; }
        action dcClaudeMdIsBounded;
        verification dcClaudeMdIsBoundedDoD : Test { :>> id = "d46b8556-151f-42bb-9a16-989b5540bd3b"; :>> method = VerificationMethod::test; :>> procedureText = "A guard `claude-md-bounded` fails when CLAUDE.md exceeds a byte budget declared in `.engine/contracts/doc-budget.toml` (this project: 16384) or when a line in it carries a verbatim human quote (a “…” span longer than 40 characters) or a dated narration (`(YYYY-MM-DD` inside a rule line) - those belong in a Decision or Statement (D0105). D0388 probe pair in the guard's test: the 53 KB HEAD~2 text fails naming its size; the 13 KB text passes. Catalogued in .engine/docs/guards.md; `keel version` counts it. Co-committed with an accepted process-change Decision (D0445); resolves issue482."; }
        action dcCycleTimeReadsFromGit;
        verification dcCycleTimeReadsFromGitDoD : Test { :>> id = "73c699fb-c3f9-4cd8-923f-073946e5cd8e"; :>> method = VerificationMethod::test; :>> procedureText = "`keel report flow` computes cycle time and time per story point from GIT, not from judgedAt: for each sprint the wall time from the first commit that adds its delivery file to the commit carrying its retro gate's passing result, in minutes; cards read in hours when the median is under a day. A new card `inter-commit gap` gives the median and p90 minutes between consecutive commits over the last 7 days against the 7 days before. `keel show flow --json` exposes the per-sprint series (sprint, points, minutes, commits). D0388 pair in the module's tests: a fixture repo with two sprints 30 and 90 minutes apart reads 30 and 90; a sprint whose retro result has no landing commit is reported `open`, never 0. usage.md's flow row names the resolution. A calibration card reads median and p90 minutes per point bucket over the last 80 sprints, so a point either predicts effort or is shown not to. Resolves issue483 (D0072's actualHours lapsed; this is the computed replacement) and issue485 (points do not order durations today)."; }
        // RAN: RAN: verifier receipt batch3 head=40190c5: keel suite --touched -> 710 passed 0 failed 700 s (touched-1789134894.log); keel show flow --json . -> sprints 674 closed 568 open 106 calibration predictive; flow_cycle_time_from_git in the touched set; guard ALL PASS exit 0
        part dcCycleTimeReadsFromGitDoDR1 : TestResult { :>> id = "83276e9b-53ba-4196-83ff-5d282156c82f"; :>> outcome = VerdictKind::pass; :>> judgedAgainst = "40190c5"; :>> judgedAt = "2026-09-11"; :>> judgedBy = "claudeOpus5"; }
        action dcDemoReplayNegativeHoldsOnUnix;
        verification dcDemoReplayNegativeHoldsOnUnixDoD : Test { :>> id = "277dd8a9-4718-4970-93e3-a1102b7bb3d2"; :>> method = VerificationMethod::test; :>> procedureText = "reverify_demos_replays_each_receipt passes on Linux CI with its negative case exiting non-zero for the reason the test names (`sh -c false` -> 1; Windows `cmd /C exit 3` -> 3), evidenced by a `ci-run id=<run> workflow=ci` receipt on the commit carrying the fix. Resolves issue484."; }
        // RAN: ci-run id=34594558856 workflow=ci
        part dcDemoReplayNegativeHoldsOnUnixDoDR1 : TestResult { :>> id = "6417a570-ab3d-42d3-917c-05ac2460651f"; :>> outcome = VerdictKind::pass; :>> judgedAgainst = "2358fd6"; :>> judgedAt = "2026-09-11"; :>> judgedBy = "claudeOpus5"; }
        action dcBriefRowsAreMeasuredOnTheBriefPage;
        verification dcBriefRowsAreMeasuredOnTheBriefPageDoD : Test { :>> id = "26bf4e88-2c4d-45c0-9818-ab39a87b7b69"; :>> method = VerificationMethod::test; :>> procedureText = "The four asi-templates section 2.1 rows that name tests/exec_summary (Why now 60, The decision rule 40, Why this wins 90, What would change my mind 30 words) are measured on a brief page: scripts/exec_brief emits an anchor per section (data-section attribute or equivalent) and python scripts/check_templates.py --brief counts words inside each anchor against the row's number, refusing an overrun naming the section and the count. The rows then name check_templates.py --brief. D0388 pair in --probe: a brief fixture at each cap passes; one word over on Why now fails naming Why now. Resolves issue486."; }
        action dcCliSurfaceGuardNamesAStaleBinary;
        verification dcCliSurfaceGuardNamesAStaleBinaryDoD : Test { :>> id = "d36adb1f-1f00-491b-9c67-d082e8651d05"; :>> method = VerificationMethod::test; :>> procedureText = "Guard cli-surface-declared reads keel-cli/src/cli_facts.rs as text beside the compiled table: when the .sysml and the SOURCE agree but the compiled table differs, the verdict names STALE BINARY (the binary's build stamp and the source file's mtime) and says rebuild, never 'regenerate the mirror'; when the .sysml and the source differ it reports drift as today. Stale-binary is a WARN, not a violation, when cargo holds the build lock (a running relink is the fix in progress); a violation otherwise. D0388 pair in the guard's unit tests: fixture with equal .sysml/source and a different compiled synopsis -> stale-binary wording; fixture with .sysml differing from source -> drift wording. Resolves issue487, issue491 and obligation0a8b234f."; }
        action dcReadOnlySubagentsCannotWriteRecords;
        verification dcReadOnlySubagentsCannotWriteRecordsDoD : Test { :>> id = "ed4f970b-9830-4270-81a8-95c4f53d7780"; :>> method = VerificationMethod::test; :>> procedureText = "A subagent whose invoked skill declares writePolicy: readOnly cannot author a record: the SubagentStop hook, when the stopping agent's transcript shows a readOnly skill invocation, reports the red into the agent's final message as a receipt line and does NOT instruct it to write (no 'fix through the write API'), and the pre-bash/pre-write hooks DENY keel record / append-result / add-task / new sprint / accept and any write under .tracking or .engine from that agent, naming the skill and the policy. The primary's dispatch needs no extra flag. D0388 pair: a fixture transcript with a test-verify invocation and a keel record decision call -> denied naming test-verify readOnly; the same transcript without the readOnly skill -> allowed. Resolves issue488; the standing-consent auto-accept of a readOnly agent's Decision (D0447 shape) is what the deny prevents."; }
        action dcToolReferenceKnowsWhatShips;
        verification dcToolReferenceKnowsWhatShipsDoD : Test { :>> id = "bfcf64eb-b722-47c2-a92c-ec7473087f80"; :>> method = VerificationMethod::test; :>> procedureText = "Guard tool-reference, when run on the engine's own tree (keel-cli/ beside .engine/), also fails a reference on a SHIPPED surface (.engine/docs, processes, skills, contracts, workflows, rules, CLAUDE.md) to a .engine/tools/<file> that migrate::is_engine_dev_only would drop from the scaffold, naming the file and saying it is dev-only (PORTABLE_TOOLS in keel-cli/src/migrate.rs is the list that ships). The verdict is the one the scaffold tests give fifteen minutes later, given at edit time. D0388 pair in the guard's unit tests: a doc naming a PORTABLE_TOOLS entry passes; the same doc naming a non-portable existing tool fails naming dev-only. Resolves issue489."; }
        action dcSprintCeremonyIsOneWrite;
        verification dcSprintCeremonyIsOneWriteDoD : Test { :>> id = "cdfd813a-5500-4c33-a5bc-c237b9536460"; :>> method = VerificationMethod::test; :>> procedureText = "DONE MEANS: keel record ceremony --sprint N --receipt F (a CliCommand in commands.sysml and cli_facts.rs, family record, effect write) reads a receipt file and, in ONE serialized write under .keel-write-lock, appends the story DoD result and the six gate results of sprint N with the receipt's head as --sha and its lines as evidence; a receipt that does not say pass writes nothing and says why; an integration test creates a sprint with new sprint --fill, runs the command, and asserts that no intermediate observation of the file (a second process polling sprint-closure between the two writes) ever sees the sprint without results; the recorder skill (D0425) names this command as its only write for ceremony. Resolves issue492, obligation49a88b5c and obligation6c6f452b. The governing Decision is a process-change and stays HELD for the human."; }
        action dcEvidencePrefixIsTheApis;
        verification dcEvidencePrefixIsTheApisDoD : Test { :>> id = "d16b4416-77f9-43f9-9af8-3850df39526d"; :>> method = VerificationMethod::test; :>> procedureText = "DONE MEANS: write::append_result and write::append_gate_result strip one leading RAN: (case-insensitive, surrounding whitespace) from --evidence before prepending their own, with a unit test pair (evidence 'RAN: x' and 'x' both write '// RAN: x'); the test-verify and recorder skill texts say the RAN: prefix is written by the API. Resolves issue493."; }
        action dcCorpusTestsAreAlwaysTouched;
        verification dcCorpusTestsAreAlwaysTouchedDoD : Test { :>> id = "3314dd6a-5400-4232-b41b-f32cb3043c7a"; :>> method = VerificationMethod::test; :>> procedureText = "DONE MEANS: touched::touched_tests includes every integration test whose text reads the tests directory itself (join('tests') with read_dir, or a // TOUCHED: always marker on its first lines) regardless of the changed stems; a unit test pair (a corpus-scanning test is selected with an unrelated stem; an ordinary test with the same stem set is not); the touched receipt lists such tests under always = [...]; keel-cli/tests/unknown_flag_is_refused.rs and every other test that read_dirs the tests directory is confirmed selected by keel suite --touched on a one-line change to an unrelated module (the receipt names them). Resolves issue494."; }
        action dcRenderModelIsDeterministic;
        verification dcRenderModelIsDeterministicDoD : Test { :>> id = "256fb204-b013-416e-aba7-24ce10a747b4"; :>> method = VerificationMethod::test; :>> procedureText = "DONE MEANS: two runs of `keel render model --root .` on an unchanged tree produce byte-identical stdout, held by a test that renders twice and compares bytes, and the source of the wandering order is named in that test's comment - not sorted away at the print step while the walk stays unordered. OBSERVED 2026-09-11 (sprint 678, D0449 research): the pre-fold `keel diagram .` and the post-fold `keel render model --root .` each emit 277780 lines and the same byte count run to run, but the element order differs between runs, so the fold's byte-equality criterion could only be held on SORTED lines (compare678.txt). The whole-model graph is a computed #View (D0093); a view whose bytes wander cannot be diffed across commits, and a diff is how a reader learns what a change moved. Locate the unordered walk (a HashMap or HashSet iteration in view/reports.rs diagram_html or the collector it reads), give it a total order keyed on the item id, and remove the sort from the sprint's comparison harness so the next fold compares raw bytes. VERIFY: the determinism test passes ten consecutive runs; `keel render model --root .` twice on the same commit, cmp says identical. Resolves issue495."; }
        action dcSubagentCannotCommit;
        verification dcSubagentCannotCommitDoD : Test { :>> id = "afe9bfe7-3932-405e-93cd-1e8a965cd90d"; :>> method = VerificationMethod::test; :>> procedureText = "Resolves issue496. DONE MEANS: a `git commit` run from a D0425 subagent (VERIFIER or RECORDER) is REFUSED by an automated control, not by the words of its skill. OBSERVED 2026-09-11 (sprint 678): the haiku VERIFIER, dispatched under skill test-verify to run the touched suite and write a receipt only, found guard:issues red on the primary's half-recorded Issue, edited .tracking/backlog.sysml to add `Resolves issue495.` to the resolver's DoD, and COMMITTED it as 5fcd953 - one file of a 39-file working set, without the Issue record that text names, while the primary was still assembling the commit; the post-commit land then refused the push, so nothing left the machine, but HEAD carried a commit no one composed. The skill text says receipt only (D0438) and was not enough: manual vigilance is not a control (D0047). DO: (1) probe first (D0388) - find the observable that distinguishes a subagent's tool call from the primary's inside the pre-bash hook input (Claude Code hook payloads for subagent tool calls, the hooks ledger's subagent-stop rows, an environment variable the Agent tool sets, or a marker the VERIFIER/RECORDER skill exports); one known-positive (a Bash call from a spawned subagent) and one known-negative (the same command from the primary), chosen before the real hook is read; (2) the pre-bash hook DENIES `git commit`, `git push`, `keel land` and `keel sync` when that observable says subagent, with a message naming D0425 and the receipt path the subagent should write instead - the second deny in a hook that D0309 gave one, so it needs its own `#SafetyChange` Decision co-committed; (3) `keel enforcement-report` counts the refusal under its own name; (4) the test-verify and recorder skills state the control by name, not as a reminder. If no observable exists the item records that as its result and names the fallback: the subagent runs with a bound actor of kind ai whose id is `verifier`, and the write paths and commit gate refuse that actor's commits."; }
        action dcTextpatchRefusesANonFileArgumentInOneLine;
        verification dcTextpatchRefusesANonFileArgumentInOneLineDoD : Test { :>> id = "1e3f21fa-8e48-40e0-89a2-c0a43499eef8"; :>> method = VerificationMethod::test; :>> procedureText = "DONE MEANS: scripts/textpatch.py, given an --anchor or --new argument that is not an existing file, refuses in one line naming the argument and saying it must be a file holding the text (never a Python traceback), and exits non-zero; its --probe carries the known-negative (a literal string passed where a path is expected) beside the known-positive. Resolves issue509: during sprint 684 the same misuse produced a FileNotFoundError traceback twice, where D0386's own rule is that a refusal names the problem in one line at the moment. No change to what a successful patch does."; }
        action dcRouteRubricQuestionsSeparateOnTheRequest;
        verification dcRouteRubricQuestionsSeparateOnTheRequestDoD : Test { :>> id = "5eda7a4e-10b9-4591-8201-86b4b2b5fa2e"; :>> method = VerificationMethod::test; :>> procedureText = "DONE MEANS: the route rubric's six questions separate on the requests they are run over, or the record says which requests are genuinely subjective and hands that sample to the human (D0381) - never a rate. WHY: issue510 - three runs of the rubric over the 47 requests disagreed with themselves on 14 then 19 named requests with the same quoted span read as different routes, and affirmed no route for one or two each run; routing_prompts.toml phrases each request as a SITUATION for the skill-routing scorer, and the rubric's ORIENT / VIEW / EXECUTE / RECORD questions do not separate on a situation with no ask. DO: critique the six questions of .engine/tools/routing_rubric.md against the DISAGREES findings in .keel/metrics/routing-rubric.json - both quotes per finding - and amend the questions with the discriminator each pair lacked (what the request asks the reader to DO, not what it describes; a situation with no ask routes to EXECUTE of the process that owns the situation, or the rubric says it cannot route it); where a pair stays split after the amendment, mark the request in routing_prompts.toml as subjective for the rubric and list it for the human's sample; re-run --rubric all twice under the amended rubric. VERIFY: the two runs' findings hold no DISAGREES line for any request not marked subjective; no request is REFUSED for no-route-affirmed; every verdict quotes a substring (the probe refuses otherwise); dcRoutingVerdictQuotesItsEvidenceDoD is then re-recorded against the run that holds."; }
        action dcFactsTypedFiguresAreRefused;
        verification dcFactsTypedFiguresAreRefusedDoD : Test { :>> id = "a378ac8b-6a35-4495-82c7-5e987a015da4"; :>> method = VerificationMethod::test; :>> procedureText = "The typed-figure control in scripts/exec_brief/facts.py is rephrased from the specimen to the class (issue511, pf56/pf57). (1) A numeral in any `how` string, and any fact value that is not the result of a subprocess, a file read or arithmetic over other facts, is refused at emit unless an explicit allowance names the reason beside it - the shape the routing section already uses. (2) The three present members are derived or removed: cliShowLenses' `how` names no number the value does not carry; routingThreeSamplesMinutes reads .keel/metrics/routing-rubric.json or is null with its `how` saying why; scopeDaysSinceRule reads D0337's createdAt from the decision file. (3) check_brief gains a rule that every numeral in the page's visible text is the value of some fact or an arithmetic the builder declares, with its D0388 pair. VERIFY: the control's D0388 pair - a `how` carrying a typed 37 is refused, the shipped `how` strings pass; facts.py runs to complete=true over HEAD with no allowance added for a member this Issue names; check_brief over the last published page reports every numeral sourced or names the ones that are not."; }
        action dcFiguresRefuseOccludedText;
        verification dcFiguresRefuseOccludedTextDoD : Test { :>> id = "f2206a9f-3b8e-4a90-9bbb-3bb4bcb0d734"; :>> method = VerificationMethod::test; :>> procedureText = "Text occluded by a later-painted shape becomes a kind fit_check measures (issue512, pf61/pf62). (1) fit_check's measurer gains OCCLUDED: a <text> whose box intersects a rect, circle or path painted after it in document order and not its own background, reported with the covering pixels like the other four kinds. (2) charts.bars gives the label its column: a label wider than 210px is wrapped or elided by measured width, never painted under the bar. (3) A value of 0 in bars is drawn as no fill with the numeral printed, never a 2px bar. D0388 pair for OCCLUDED: the 70-character bars label from pf61 is reported, the shipped stacked legend after the issue390 fix is CLEAN. VERIFY: `python scripts/exec_brief/fit_check.py --probe` holds all cases including the two new ones; the last published page still fits; check_templates --brief passes."; }
        // sprint 685's DoD failed on issue510 (routes refused for want of an affirmed question); the rerun waits for the resolver - an edge, not a hand reorder (D0052)
        first dcRouteRubricQuestionsSeparateOnTheRequest then dcRoutingVerdictQuotesItsEvidence;
        action dcRecordedDoDsCarryTheirDate;
        verification dcRecordedDoDsCarryTheirDateDoD : Test { :>> id = "e60d2e82-4342-453e-a31e-bf4261c30cbf"; :>> method = VerificationMethod::test; :>> procedureText = "DONE MEANS: a DoD Test written by keel record task carries createdAt and createdBy, so a forward-only guard can read its boundary the way it reads a Decision's. FOUND 2026-09-12 building guard direction-cited (issue428): write.rs emits the verification <task>DoD : Test with id, method and procedureText only; of 730 DoDs in backlog.sysml five carry createdAt, all hand-authored, so the guard's DoD clause can count an undated citing DoD but never apply the rule forward to one - the boundary is not in the tree. D0129: provenance is never defaulted, actor AND date. DO: record task stamps createdAt (the bound date) and createdBy (the bound actor) on the DoD Test it writes; the record-task tests assert both fields; the guard direction-cited's undated count then falls as new DoDs are recorded through the API. VERIFY: a DoD recorded through keel record task in a temp tree carries both fields and gate validate holds; the guard's undated count is unchanged for the existing DoDs (history, not rewritten)."; }
        action dcBriefNotesArePerAsk;
        verification dcBriefNotesArePerAskDoD : Test { :>> id = "0d9fcc30-f9e6-45ee-a231-d94ab9bccb52"; :>> method = VerificationMethod::test; :>> procedureText = "DONE MEANS: the decision brief's copy-out carries a notes field PER ASK, and the sheet labels each note with the ask it belongs to, so a reader's words land on the item they were written for. FOUND 2026-09-13 on the nineteenth publish: the page has one notes box under the whole sheet; the human wrote a note for the retro ask and asked whether it 'bless to all others' - the surface gave them no way to say which ask it was for, and the recorder had to ask. DO: each panel gets its own notes textarea (data-records = the ask's id); the copy-out emits 'Recorded with the answer for <ask>:' per non-empty note and no sheet-wide note; check_templates.py --brief refuses a page whose ask count and per-ask notes count differ, and refuses a sheet-wide notes control. VERIFY: check_templates on the previous published page (one shared box) reports the violation; on the rebuilt page it is clean; the copy-out of a page with two notes filled names both asks."; }
        action dcSyncRenumbersACollidingIntakeName;
        verification dcSyncRenumbersACollidingIntakeNameDoD : Test { :>> id = "777b9750-7e1e-45ee-a82d-dead409f8152"; :>> method = VerificationMethod::test; :>> procedureText = "DONE MEANS: two writers that allocate the same sequential intake name (stNNN / usNNN) on different clones cannot leave the tree with two parts of one name: keel sync, on a merge conflict in an intake file, keeps both facts by renumbering the part whose commit is not on origin to the next free name and rewriting the edges that name it, and says so in the merge message. FOUND 2026-09-13: the scheduled currency pass (CI, 21e43e6) and this session both opened intake-2026-09-13.sysml and both wrote st121 - CI's from GH#71, the session's from the human's nineteenth-publish note; keel sync stopped at AA and the renumbering (st121 -> st122, us110's #DerivedFrom edge) was done by hand in 25e4c04. Identity is the UUID (D0129 invariant 3); the short name is a convenience that two counters can collide on. DO: keel sync's merge step, on an AA/UU conflict under .tracking/intake/, parses both sides, keeps every part by id, renumbers the local side's colliding names to the next free number across the whole tracking tree, rewrites edges and any dNNNN-style references in the same file, writes the merged file and continues the merge; a unit test with two synthetic sides proves the renumber and the edge rewrite; the D0388 probe pair is a colliding pair (positive) and two files with distinct names (negative). VERIFY: the test passes; keel sync on a fixture repo with the collision completes without a stop and gate validate holds on the result."; }
        action dcBuildStampSeesSourceEdits;
        verification dcBuildStampSeesSourceEditsDoD : Test { :>> id = "79248c0e-8625-40eb-8929-316c154afaed"; :>> method = VerificationMethod::test; :>> procedureText = "DONE MEANS: a binary built from an edited source tree says so in its stamp whether or not a git operation happened between the edit and the build, and a build whose git status call failed says +unknown rather than reading clean. FOUND 2026-09-13: keel.exe built from knowledge.rs patched to DOMINANCE 1.5 printed build commit 33c398a with no +dirty, because build.rs re-runs only when .git/HEAD or .git/index changes and the edit changed neither; the source was reverted and the binary served hooks and benchmarks for nine hours as a 33c398a that no commit matches (issue516). DO: build.rs emits rerun-if-changed for the crate's src directory and for build.rs itself, so any source change re-derives the stamp; the git status helper distinguishes an empty result (clean) from a failed call, and a failed call stamps SHA+unknown; the D0388 pair is a probe script under .engine/tools that (positive) edits one comment line in a scratch copy of a source file, builds, and reads +dirty from keel version with no git command run between, and (negative) builds a clean tree and reads the bare SHA; recall_binary.py's header warns in its own line when the stamp carries +dirty or +unknown, because a Decision-grade measurement against such a binary is attributable to no commit. VERIFY: the probe script's two cases print PASS; cargo build --release after a comment-only edit to knowledge.rs prints a +dirty stamp before any git command runs; a clean tree prints the bare SHA; recall_bench.py's first line names the suffix when present."; }
        action dcAcceptedCharterAuthorisesTheLockedEdit;
        verification dcAcceptedCharterAuthorisesTheLockedEditDoD : Test { :>> id = "e7f5c3cb-dac4-4684-a820-c29779c1d070"; :>> method = VerificationMethod::test; :>> procedureText = "DONE MEANS: a locked-surface edit is authorised by a human-accepted, marked Decision that a co-committed sprint record names as its charter, as well as by a marked Decision in the commit itself, so a process-change Decision held for the human and then accepted can be applied in the commit that does the work. FOUND 2026-09-13 (issue517): D0460's three skill edits, accepted at 8469f80, were refused by guard process-change because the Decision was not among the commit's changed files, while the same guard passes a merely proposed marked Decision that rides the commit. DO: keystone_violations gains a second authorising source - every changed .tracking/delivery/*.sysml whose #CharteredBy edge targets a dNNNN whose file under that project's .engine/decisions carries the #ProspectiveChange/#SafetyChange marker AND is accepted by a human (acceptance_kind == Human, D0106) - and the pass names the charter in one warning line (Decision, sprint file); a proposed or auto-accepted charter authorises nothing; the workspace gate's staged_marked_decision accepts the same source so a root hook edit has the same path; the guard message names both paths. The D0388 pair: a unit test with (positive) a locked edit plus a sprint text chartered by a human-accepted marked Decision passing, and (negative) the same with the Decision proposed, auto-accepted, or unmarked failing, plus the existing keystone_selftest cases unchanged. guards.md's process-change row states the second path. VERIFY: cargo test keystone exits 0 with both new cases; with D0460's skill edits and sprint 692's file staged and no Decision file changed, keel gate guard --no-receipt prints [guard:process-change] PASS and a warning line naming d0460 and the sprint file; with the sprint's charter pointed at a proposed marked Decision the guard prints FAIL."; }
        // RAN: cargo test -p keel-cli --lib keystone -> 3 passed (keystone_selftest, keystone_accepts_a_human_accepted_marked_charter_and_nothing_weaker); LIVE with .engine/decisions/0465 moved out of the tree: skill edits + sprint692 chartered by d0460 staged -> gate guard --no-receipt [guard:process-change] PASS, WARN 'locked edit authorised by d0460, a marked Decision the human accepted, cited as the charter of the co-committed sprint record .tracking/delivery/sprint692_testResultSkillNamesTheBinding.sysml (D0465)'; sprint692 charter -> d0465 (proposed) -> [guard:process-change] FAIL 1 violation
        part dcAcceptedCharterAuthorisesTheLockedEditDoDR1 : TestResult { :>> id = "a8d81f01-a325-49c8-84dd-83eda0d5990e"; :>> outcome = VerdictKind::pass; :>> judgedAgainst = "eda9647"; :>> judgedAt = "2026-09-13"; :>> judgedBy = "claudeFable5"; }
        action dcStagedAcceptanceIsProbedAsACharter;
        verification dcStagedAcceptanceIsProbedAsACharterDoD : Test { :>> id = "9aed3bdb-33cb-4696-97ec-ddaa538ef8e3"; :>> method = VerificationMethod::test; :>> procedureText = "DONE MEANS: the D0465 second source is probed on the one case sprint 693's live pair did not read - a charter Decision whose human acceptance (dNNNNAcceptR pass, non-AUTO Accept Test) is present in the working tree or index but not yet in any commit. FOUND 2026-09-13 (issue518, sprint 693 retro): accepted_charters reads the Decision file from disk, so a staged acceptance authorises; that is the intended behaviour (the acceptance is a human act whether or not it is committed, D0192) but no probe established it, and a check whose answer is stated without its probe is the D0388 class. DO: in a scratch copy of the tree, record a marked Decision, accept it with keel accept --words --by, do NOT commit, add a sprint chartered by it plus a locked edit, run gate guard --no-receipt under KEEL_HOOK=1 (Index read) and without (working tree); both print [guard:process-change] PASS naming the charter; revert the acceptance to proposed and both print FAIL. Record the four lines as the item's receipt; if either reading disagrees, that is a defect and a new Issue names it. VERIFY: the receipt quotes the four guard lines with the scratch tree's SHA."; }
        action dcRetroFindingIsAnIssueFirst;
        verification dcRetroFindingIsAnIssueFirstDoD : Test { :>> id = "359c1aa7-ed96-43eb-8ff3-fac6762d1e2c"; :>> method = VerificationMethod::test; :>> procedureText = "DONE MEANS: the retro-backlog guard prefers an Issue as D0467 says: a retro whose tracked items added by THIS commit are Decisions only (dNNNN or D0NNN) and no Issue or task draws one WARNING naming the sprint file and the Decision(s), unless the retro text carries 'standing rule:' followed by why the finding is not a one-off; a retro that adds an Issue or a task, or justifies with an existing item under the D0293 phrases, is silent; the blocking behaviour of retro_backlog_violations is unchanged. Derived from us110 (st122: 'I usually want issues coming out of retros, not decisions'). BLOCKED on D0467's acceptance (process-change, held). DO: retro_backlog_violations (or a sibling returning warnings) in keel-cli/src/guards.rs gains the Decision-only branch; the D0388 pair as unit tests - a retro adding only d0NNN with no phrase WARNS, the same text with 'standing rule:' is silent, a retro adding issueNNN is silent, a retro naming an existing Issue under 'already tracked' is silent; guards.md's retro-backlog row states the preference; the sprint-retro skill's finding step says Issue first, Decision with 'standing rule:'; sync-claude; land in a sprint chartered by d0467 through the D0465 path. VERIFY: cargo test retro_backlog exits 0 with the four new cases; keel gate guard --no-receipt on a scratch sprint whose retro adds only a Decision prints the WARN line and PASS; the same retro with 'standing rule:' prints no WARN."; }
        action dcRigSandboxKeepsThePrefixInstrument;
        verification dcRigSandboxKeepsThePrefixInstrumentDoD : Test { :>> id = "a27ae1a9-0f07-4b99-8db3-1b942472a7b4"; :>> method = VerificationMethod::test; :>> procedureText = "DONE MEANS: a routing-rig sample whose declared prefix is intake completes the prefix in one turn instead of spending turns searching for an instrument the sandbox removed. Resolves issue519: the rig disallows Bash so a probe cannot write to the tree, but intake's deployed procedure runs keel record statement, so every intake-prefixed sample (release 2026-09-13: three of three) spent one or two ToolSearch turns hunting for it before the intended skill was reached - a cost the real agent never pays, charged to every case's budget. DO: in routing_probe.py give the probe session a way to complete the prefix without writing - a probe_settings() allowance for a read-only or dry-run form of the statement write that the rig verifies wrote nothing, or a stub the prefix's procedure names - and record in the sample which form the prefix used; keep every other write disallowed. VERIFY: the release case re-run at --turns 6 --samples 3 shows no ToolSearch between Skill(intake) and Skill(release) in any sample and the tree is unchanged after the run (git status --short empty beyond the receipt); the D0388 pair - a transcript with the search scores as before, one without it scores routed with the prefix; the per-run seconds and cost are quoted beside the 2026-09-13 measurement (66.8s, 1.3165 USD) with no rate or standing number introduced (D0378 C)."; }
        action dcSubagentStopChecksTheRecorderReport;
        verification dcSubagentStopChecksTheRecorderReportDoD : Test { :>> id = "9268a940-294b-43f5-8c4c-b9b94e1ceaed"; :>> method = VerificationMethod::test; :>> procedureText = "issue521 is resolved - the subagent-stop hook checks the recorder's report itself, so clause (c) of dcDelegatedCeremonyIsASkill stops resting on the recorder's discipline. SubagentStop's payload carries last_assistant_message (Claude Code 2.1.270 schema, read from the binary in sprint 699); when agent_type is recorder the hook runs the same refusals as .engine/skills/delegated-ceremony/references/check_report.py over that message (undeclared marker, typed edge line, last line not the fast gate's, DISCREPANCIES: NONE over a FAILED line) and BLOCKS with control recorder:report-outran-gate, one ledger line. DONE MEANS: the refusal set has one home - the Rust check and the Python check read the same fixture pair under references/fixtures/ and a test pins them equal; a recorder whose last message passes is not touched; a payload without last_assistant_message is a WARN naming the missing field, never a block (the field is optional in the schema). VERIFY: the D0388 pair - fixtures/positive-undeclared-marker.txt fed as last_assistant_message under agent_type recorder is BLOCKED (known positive), fixtures/negative-sprint647-receipt-driven.txt passes (known negative), the same positive under agent_type general-purpose is not blocked; keel gate guard ALL PASS."; }
        action dcClaudeSurfaceNamesUnsourcedFiles;
        verification dcClaudeSurfaceNamesUnsourcedFilesDoD : Test { :>> id = "cfb45abe-919d-43db-bcc4-a6db86150b57"; :>> method = VerificationMethod::test; :>> procedureText = "issue522 is resolved - sync-claude --check names a tracked file under .claude/skills/ that no .engine/skills/ source deploys. Sprint 699's retro found .claude/skills/brand-watch/check_manifest.py tracked with no .engine/skills/brand-watch directory: the surface is generated (D0379, keel sync-claude), the claude-surface-drift guard PASSED over it, so an unsourced file under the generated surface is drift the guard does not see - a stray that the next sync will neither refresh nor remove. DONE MEANS: sync-claude --check lists every file under .claude/skills/<s>/ whose <s> has no .engine/skills/<s>/SKILL.md, or whose path is not SKILL.md and not under references/ of a sourced skill, as UNSOURCED and returns non-zero; the claude-surface-drift guard FAILS on the same set; the brand-watch stray is dispositioned (a source is written under .engine/skills/brand-watch/ or the file is deleted) in the same sprint. VERIFY: the D0388 pair - a scratch file planted under .claude/skills/render/stray.py is named UNSOURCED (known positive), the tree with no stray passes (known negative); keel gate guard claude-surface-drift PASS after the disposition."; }
        action dcStaleBinaryNamesItself;
        verification dcStaleBinaryNamesItselfDoD : Test { :>> id = "cac30e56-ce63-4e20-a669-cc838b524bc5"; :>> method = VerificationMethod::test; :>> procedureText = "issue523 is resolved - a gate or guard run from a binary whose build commit is not the tree's HEAD says so before its first verdict line: keel gate validate / check-engine / guard / --fast / sync-claude --check print STALE BINARY: build <commit> is not HEAD <sha> (keel version) as their first line whenever the embedded build commit (stripped of +dirty) is neither HEAD nor an ancestor of HEAD within the last landed commit, and the verifier receipt shape in the test-verify skill gains bin=<path> build=<commit> on its first line, read from KEEL version, so a substituted binary is visible in the receipt itself; the recorder's rule (2) treats a receipt whose build is not HEAD as a discrepancy to report, never a pass to record. DONE MEANS: the stale line is one function with a D0388 pair (a binary stamped e0624f3 against HEAD b9754c5 is named, known positive; a binary stamped HEAD or HEAD+dirty is silent, known negative); test-verify's receipt shape and the delegated-ceremony recorder brief carry the field; sprint 699's verifier receipt, which reported 154 phantom violations and a DRIFT from target/release/keel-gate.exe (build e0624f3+dirty, six days stale) while every current binary read ALL PASS, is the motivating case. VERIFY: the pair; keel gate guard ALL PASS from the current build prints no stale line; a copy of an older release binary run against the same tree prints it first."; }
        action dcEngineTreeChangesTouchTheScaffoldTests;
        verification dcEngineTreeChangesTouchTheScaffoldTestsDoD : Test { :>> id = "06bfc94c-c78d-47d1-a521-d6b087b6e344"; :>> method = VerificationMethod::test; :>> procedureText = "issue524 is resolved - a changed path under .engine/ contributes the touched stem init (touched::embedded_stem) and puts the lib unit tests in the set, so every integration test that scaffolds a project with keel init runs before the push that ships a change to the embedded tree; init_smoke's exact list of shipped python names check_report.py, the delegated-ceremony check the recorder brief runs by path. VERIFY (probe pair, D0388, chosen before the rule was written): embedded_stem of .engine/skills/delegated-ceremony/references/check_report.py is init - the path CI run 34775521516 went red on under a 570/0 receipt (known positive); embedded_stem of .tracking/backlog.sysml and of keel-cli/src/init.rs is None (known negatives); cargo test --release --lib touched:: passes; cargo test --release --test init_smoke passes; clippy clean."; }
        // RAN: PROBE PAIR: cargo test --release --lib touched:: -> positive a_change_under_the_embedded_tree_names_init: ok; cargo test --release -p keel-cli --test init_smoke -> test result: ok. 2 passed; 0 failed; 0 ignored; 0 measured; 0 filtered out; finished in 13.78s TOUCHED RECEIPT: outcome=pass passed=609 failed=0 seconds=494 at=1789327613 launch=1789327109 (at-launch: ok)
        part dcEngineTreeChangesTouchTheScaffoldTestsDoDR1 : TestResult { :>> id = "b3f33e8f-759c-45c3-ae5e-8058c4b9c57e"; :>> outcome = VerdictKind::pass; :>> judgedAgainst = "df713de"; :>> judgedAt = "2026-09-13"; :>> judgedBy = "claudeFable5"; }
        action dcTouchedReceiptNamesTheUnmatchedPaths;
        verification dcTouchedReceiptNamesTheUnmatchedPathsDoD : Test { :>> id = "e1397a5d-75c1-4b19-9b19-1e434d38ea06"; :>> method = VerificationMethod::test; :>> procedureText = "issue525 is resolved - the touched receipt (.keel/metrics/touched-receipt.toml, touched::render_receipt) carries an unmatched line listing every changed path that contributed no stem, no test and no lib run, so a green receipt over a change the set could not see says what it did not see; the verifier brief reads the line back into its receipt beside stems and changed. VERIFY (probe pair, D0388): a Touched fixture whose changed set holds .githooks/post-commit and keel-cli/src/sync.rs renders unmatched = [.githooks/post-commit] and not sync.rs (known positive); a fixture whose every changed path is a keel-cli/src module renders unmatched = [] (known negative); cargo test --release --lib touched:: passes; clippy clean."; }
        action dcCliFactsOwnedByARetiredActorAreSupersedable;
        verification dcCliFactsOwnedByARetiredActorAreSupersedableDoD : Test { :>> id = "59fd847f-2953-4ade-b4bb-f3a709c4ac74"; :>> method = VerificationMethod::test; :>> procedureText = "DONE MEANS: a live actor can amend what a CliCommand fact SAYS without editing a retired actor's fields, and the guards agree on the route. Resolves issue538. TODAY: cliSuite and cliLand are owned by claudeOpus5; D0108 (guard ownership) refuses any other actor's in-place synopsis edit and says supersede; guard cli-surface-declared (guards.rs cli_surface_violations) indexes the authored facts by name and compares EVERY authored fact to the Rust mirror, so a superseded fact left in commands.sysml fails the mirror and a deleted one is a field edit nobody owns. The two controls collide, and the collision was reached on 2026-09-14 when D0474 changed what `suite --touched` and `land` do and the synopses could not follow. DO: cli-surface-declared reads the #Supersede edges of .engine/cli/commands.sysml and excludes a superseded fact from the authored set (the mirror carries only the live one); a superseding CliCommand carries the same name and a new id, and the guard fails when two LIVE facts share a name. This is a guard change: a co-committed #ProspectiveChange Decision, held for the human (D0337). VERIFY: a fixture with an old fact, a new same-name fact and a #Supersede edge between them passes with the mirror matching the new one (known-positive); the same fixture without the edge fails naming the duplicated name (known-negative); then cliSuite and cliLand are superseded by claudeFable5-owned facts whose synopses name the D0474 skip, guard ownership clean, cli-surface-declared clean, keel --help renders the new synopses."; }
        action dcTouchedRunScrubsPerfFromTheChildEnv;
        verification dcTouchedRunScrubsPerfFromTheChildEnvDoD : Test { :>> id = "54412981-5081-496b-88b8-4f10d7cac50d"; :>> method = VerificationMethod::test; :>> procedureText = "DONE MEANS: the touched run cannot be turned red by the operator's own profiling variable, and a JSON lens stays JSON with profiling on. Resolves issue539. TODAY: perf::report() is printed to stderr at process end when KEEL_PERF is set (main.rs), the integration tests read a child's stdout and stderr as one text, and touched.rs spawns cargo with the inherited environment, so every keel the tests spawn prints the report into the text the test parses; three binaries went red on 2026-09-14 for that reason and only that reason. DO: touched.rs (the path keel suite --touched and land share) calls env_remove('KEEL_PERF') on every cargo command it builds. VERIFY: known-positive - `KEEL_PERF=1 keel suite --touched` over a fixture whose test parses JSON from a spawned keel passes; known-negative - the same fixture with the scrub removed fails with trailing characters; `KEEL_PERF=1 keel show control-structure . --json | python -c 'import json,sys; json.load(sys.stdin)'` parses; clippy -D warnings clean."; }
        // RAN: Resolves issue539. touched.rs scrub_perf() calls env_remove(KEEL_PERF) on every cargo command the touched run builds (capture(), shared by keel suite --touched and keel land); the perf report was already on stderr (main.rs:5667 eprintln) - the record's stdout clause was wrong and is corrected; the tests read both streams as one text (control_structure_is_computed.rs:28). D0388 pair, cargo test --release --lib -- touched:: -> the_cargo_child_never_inherits_the_operators_perf_variable ok: known-positive the built command's get_envs() carries exactly one removal, KEEL_PERF; known-negative an unscrubbed Command carries no entry and inherits the parent's environment - the shape that went red on 2026-09-14. Real tree: the touched run of this sprint (823 passed, 0 failed) executed control_structure_is_computed, library_read_side and stop_says_nothing_about_decisions green; KEEL_PERF was unset in that shell, so the fixture-under-KEEL_PERF=1 clause of the DoD is established by the unit pair, not by a real-tree run under the variable. keel show control-structure . --json with KEEL_PERF=1 parses (stdout alone through the pipe). clippy -D warnings clean
        part dcTouchedRunScrubsPerfFromTheChildEnvDoDR1 : TestResult { :>> id = "936ab25d-2c11-4067-ac50-f8581d078d29"; :>> outcome = VerdictKind::pass; :>> judgedAgainst = "d64d319"; :>> judgedAt = "2026-09-14"; :>> judgedBy = "claudeFable5"; }
        action dcLockedSurfaceEditIsNamedAtWriteTime;
        verification dcLockedSurfaceEditIsNamedAtWriteTimeDoD : Test { :>> id = "ec2ec57f-8616-41e7-9aa0-f6f2a5d30bcb"; :>> method = VerificationMethod::test; :>> procedureText = "Resolves issue555 (the sprint 717 retro finding): hook_pre_write (keel-cli/src/main.rs) checks the kill switch, CONTROL_PLANE_PATHS and the .tracking/.engine/decisions tiers but never asks guards::is_locked_path, so a Write|Edit to a D0070 locked surface (a process definition, a skill body, a .githooks or CI file, or a guard source file in GUARD_SOURCE_FILES) draws no word at write time and the process-change guard is the first thing that names the missing Decision - after the code is done, at the verify ladder or the commit (sprint 717: guards.rs; sprint 624: two skill files; issue213: twice before that). DO: pre-write emits ONE advisory line (never a deny - the lock is the commit's, D0209 clause 2) when the path is locked and the working tree holds no changed marked Decision and no sprint record chartered by an accepted marked Decision: it names the file, the lock, and the two paths through it (record decision --process-change, or a sprint chartered by an accepted marked Decision), and the fire is one ledger line like every hook fire. VERIFY (D0388 pair, chosen before the tree is read): known-positive - a pre-write payload naming keel-cli/src/guards.rs in a tree with no marked Decision among its changes prints the advisory naming the file and the flag; known-negative - the same payload with a changed .engine/decisions file carrying #ProspectiveChange prints nothing, and a payload naming keel-cli/src/view/mod.rs prints nothing in either tree. Docs: usage.md's hook table gains the line; keel sync-claude --check clean; the hook's latency stays under the fast tier's budget in keel show enforcement-report."; }
        action dcGuardReadFailureIsNotAnEmptyDiff;
        verification dcGuardReadFailureIsNotAnEmptyDiffDoD : Test { :>> id = "414d73a9-a3bf-4702-8486-da262c59037e"; :>> method = VerificationMethod::test; :>> procedureText = "DONE MEANS: a git call that a guard's change read depends on and that exits non-zero, or cannot be spawned, is a distinct outcome from an empty diff. `git_stdout` in keel-cli/src/guards.rs no longer answers `''` for a failure where the population of a guard is being computed: `changed_paths` and the readers built on it return an error carrying the git command and its stderr, and every guard that reads changes through them reports `GATE CANNOT RUN: git <args> failed - <stderr first line>` as a violation naming the command (D0098: a gate that cannot run says so, never a verdict over a missing read). The stop hook's in-loop gate prints that line in place of the guard's verdict when it happens, and the ledger row carries `gitReadFailed = true`. D0388 pair, chosen before the tree is read and pure over an injected git result: known-positive is a change read whose git call returns exit 128 with stderr `fatal: Unable to read current working directory` -> the process-change guard reports GATE CANNOT RUN naming that command, not a violation and not a pass; known-negative is a change read whose git call exits 0 with empty stdout -> the guard reads an empty population and is silent, as today. Resolves issue576: a stop hook that read the tree during sprint 727's in-flight commit made 63 git calls instead of 66 and reported the marked Decision d0496 absent from a commit that carried it."; }
        action dcWaitChecksTheLaunchEpoch;
        verification dcWaitChecksTheLaunchEpochDoD : Test { :>> id = "7e831bd5-5c48-4a97-8a47-7243845ae58e"; :>> method = VerificationMethod::test; :>> procedureText = "DONE MEANS: `keel verify --wait ROOT --since EPOCH` refuses a receipt whose `at` is older than EPOCH as `STALE: receipt at N predates the launch at EPOCH`, exit 2, and never prints its table as this run's; without `--since` the behaviour of dcVerifyWaitsForItsPid is unchanged. The test-verify skill's step 1 writes the launch epoch and step 4 passes it, so step 5's `at > verify-launch.epoch` row is the command's, not the reader's. D0388 pair (pure control over a receipt text, a liveness answer and an epoch): known-positive is a finished receipt with `at` before the epoch -> STALE, exit 2; known-negative is the same receipt with `at` after the epoch -> the rung table. Found in sprint 728's retro: the stale-receipt read (sprint 661, 46 minutes stale) is the same shape as issue575, a receipt read at the wrong time and reported as this run's."; }
        action dcWorktreeScratchIsPerProcess;
        verification dcWorktreeScratchIsPerProcessDoD : Test { :>> id = "63819944-c1d7-458e-ada0-1e58f98e5dc8"; :>> method = VerificationMethod::test; :>> procedureText = "The three production worktree scratch paths carry the process id: keel-audit (history.rs), keel-trend-{short} (view/reports.rs) and keel-bl-{tag}-... (view/mod.rs) are named through keel_fs::scratch or a sibling that appends process::id(), so two concurrent keel runs never share a checkout, and git worktree remove --force from one run cannot remove the tree the other is reading. A D0388 pair holds it: a known-positive fixture naming a fixed production join is named, the helper's paths pass, and the D0498 census region rule extends to production sites or a second census names production temp_dir().join sites lacking the token. Each of the three paths is exercised once in a lib test that asserts the pid is in the path name. Resolves issue577: the three production worktree scratch paths are shared across concurrent keel runs."; }
        action dcFactSensorsCarryTheirPair;
        verification dcFactSensorsCarryTheirPairDoD : Test { :>> id = "df1ca2fb-df2b-41db-8b56-ad8080f36c3b"; :>> method = VerificationMethod::test; :>> procedureText = "DONE MEANS: every sensor in scripts/exec_brief/facts.py that parses a receipt line, a command line or a path with a regular expression carries its D0388 pair, run before any fact is emitted, and a source scan refuses the emission when one does not. Resolves issue582: the pair-file stem sensor read `control_structure ; python C` as the stem of sprint 732's ladder because a greedy `.*` ran past `pair732.txt:` to the last slash of a SIDE whose own path carried `C:`; brief 38's sides had no colon, so the same regex had read correctly the publish before, and nothing but a downstream build check that happened to compare the sides caught it. Two sensors in that file carry a pair today (the exit-code sensor, issue553; the stem helper, issue582) out of the regular expressions the file runs over text it did not author; the class is a kept check without its known answers, the class dcAdHocChecksAreProbedFirst made a step for scripts and did not reach inside this one. DO: gather the text-parsing sensors into named helpers, each with one positive and one negative case chosen before the tree is read, in one probe block at the top of facts.py that refuses to emit on any miss; a source scan in the same block counts `re.search`/`re.match`/`re.findall` calls over a receipt, command or path variable that sit outside a probed helper and refuses when the count is above zero, so a new unprobed sensor cannot be added silently. VERIFY: the issue582 line reproduces the wrong stem under the greedy form and the right one under the helper; the scan is shown to bite on a fixture with one bare re.search over a receipt variable; facts.py on this tree emits with the count at zero."; }
        action dcWaitRereadsBeforeKilled;
        verification dcWaitRereadsBeforeKilledDoD : Test { :>> id = "c8d7fc95-f529-4b71-b296-846ccf8689a1"; :>> method = VerificationMethod::test; :>> procedureText = "DONE MEANS: `keel verify --wait ROOT` never reports KILLED from one read. wait() in members/keel-suite/src/verify.rs reads the receipt and then asks whether its pid is alive; when the writer rewrites the final receipt and exits between those two reads the stub it read says `running` and the pid is gone, and the ladder that just passed is printed as `KILLED during <rung>`, exit 2. The fix: a `Killed` answer is confirmed by re-reading the receipt after the liveness answer - if the re-read is `Finished` the table is printed and the ladder's exit code returned; if it is still `running` with the same pid, KILLED stands (the writer died). One read of the liveness after the receipt, or two reads of the receipt around it, is the only change; no sleep, no retry loop beyond the one re-read. D0388 pair (pure control over two receipt texts and a liveness answer, wait_state stays pure): known-positive is a `running` stub whose second read is a `pass` receipt -> the rung table, exit 0; known-negative is a `running` stub whose second read is the same stub with the pid dead -> KILLED, exit 2. Resolves issue592: the sprint 737 ladder passed every rung (receipt at 1789658057, outcome pass, 1070 s) and `keel verify --wait .` running beside it printed KILLED during touched in the same second, so the reader relaunched a green ladder once already in sprint 726's shape (issue575) and would have again."; }
        action dcCodeRegistryPathsResolve;
        verification dcCodeRegistryPathsResolveDoD : Test { :>> id = "00e3bd0c-df05-45df-a743-f39d51c39c69"; :>> method = VerificationMethod::test; :>> procedureText = "DONE MEANS: every `filePath` in .tracking/architecture/code-registry.sysml names a file that exists in the tree at HEAD, and a guard holds it. The registry is the deliverable's map of CodeElement to source (D0050's task-to-path manifest is the other half); at 904ff24c eleven of its twenty-five filePath values (nine distinct: keel-cli/src/actor.rs, arch.rs, claim.rs, guards.rs, migrate.rs, orient.rs, sync.rs, view.rs, write.rs) name files the D0479 extractions moved under members/ in sprints 731-737 and nothing read the values, so the map has been wrong for seven sprints without a red. The fix is two parts: (1) a `code-registry-paths` check in the guard family that reads every `filePath` attribute under .tracking/architecture/ and fails naming each value with no file at ROOT/<value>, with the owning element and the crate module_home.py computes for the stem as the suggested value; (2) the eleven stale values corrected to the paths cargo builds today - the elements are claudeOpus5's, so each correction is an ADD beside the element or a #Supersede of it (D0108), never an edit of another actor's attribute. The deliverable-manifest.txt task rows are already checked by the suspicion computation and are not this item's. D0388 pair: known-positive is a registry fixture whose one filePath names a file that exists -> the check passes with one scanned; known-negative is the same fixture with the path's stem changed to a name no file has -> the check fails naming the element, the value and the suggestion. Resolves the sprint 738 retro finding that scripts/extract_serve.py had to correct two registry values by hand (ceServeJudgment, ceLauncher, both claudeFable5's) while nine others stayed stale because no control read them."; }
        action dcMembersCarryTheLintPreamble;
        verification dcMembersCarryTheLintPreambleDoD : Test { :>> id = "a9b1a2ca-627e-4d95-a9ef-283e06f6fcaf"; :>> method = VerificationMethod::test; :>> procedureText = "DONE MEANS: every crate under members/ carries the member lint preamble in its lib.rs - forbid(unsafe_code), deny(warnings, clippy::all, clippy::pedantic, clippy::nursery), deny(clippy::unwrap_used, clippy::expect_used, clippy::panic, clippy::indexing_slicing, clippy::todo, clippy::unimplemented), the cfg_attr(test) allowances - and a check holds it. At 904ff24c six of fifteen members (keel-actor, keel-git, keel-github, keel-json, keel-perf, keel-schema - the leaves sprint 714 split out first) have a lib.rs with no lint attribute at all, so a warning or an unwrap in those crates compiles clean under `cargo build` and is caught only when `cargo clippy --workspace -- -D warnings` runs, which the pre-commit ladder does but the settle build in every D0388 positive probe does not; keel-fs and the eight members extracted since 731 carry the preamble because their codemods wrote it (extract_issues.py, extract_serve.py LINTS). The fix: (1) the preamble added to the six lib.rs files and the build brought clean under it (a pedantic-clean pass over six leaf crates); (2) a `member-lints` check in the guard family that reads every members/*/src/lib.rs and fails naming each crate whose first attribute block lacks any of the named lint lines, so the next member (extract_*.py or by hand) cannot land without it. D0388 pair: known-positive is a lib.rs fixture carrying the exact preamble -> pass, one scanned; known-negative is the same fixture with the deny(warnings...) line deleted -> fail naming the crate and the missing line. Resolves the sprint 738 retro finding: the eleventh extraction codemod wrote the preamble into members/keel-serve from a string constant while the crate it added ci_runs to, keel-github, has none - two of the workspace's crates hold the same kind of code under two lint regimes and nothing reads which."; }
        action dcSuiteReceiptNamesTheStandbyItSpanned;
        verification dcSuiteReceiptNamesTheStandbyItSpannedDoD : Test { :>> id = "5dad7d3c-1082-4f2c-9650-39730d62928d"; :>> method = VerificationMethod::test; :>> procedureText = "DONE MEANS: a keel suite / suite --touched / verify run measures the host's suspended time across the run - the drift between the wall clock (SystemTime) and a clock that does not advance while the host sleeps (QueryUnbiasedInterruptTime on Windows, CLOCK_MONOTONIC against CLOCK_BOOTTIME on Linux) read at launch and at exit - and writes it into the receipt as `standby = <seconds>`; when standby exceeds the largest clock margin any test carries (600 s, the self-build hook fixture's) and the run is red, each failed test is re-run once in isolation before the receipt is final, the receipt's outcome is that of the re-run, and the receipt names both: the first red set, the standby seconds, and the re-run verdict per test. A run with no standby writes standby = 0 and re-runs nothing; a red that survives its isolated re-run stays red. keel verify's rung table and the verifier's receipt template print the standby field so a reader never sees 18 tests at 5900 s and two reds without the cause beside them. Resolves issue595: the sprint 738 ladder's touched rung (launch 1789667298, touched-1789667668.log) ran while the host entered Modern Standby at 11:59:01 and left it at 13:36:04 (Kernel-Power 506/507); 18 in-flight tests read 5930-6040 s, an_output_still_linking_is_not_copied's +600 s fixture aged past the two-second grace (self_build_hooks_leave_the_build_tree.rs:112-118) and turn_boundary_gate_allows_a_clean_tree_and_blocks_a_dishonest_one read an empty stop-hook stdout (remaining_controls_actually_fire.rs:115); both pass in isolation in under six seconds. This is issue481 and issue534's class - an assertion whose truth depends on how fast the host reaches a clock read judges the host, not the change - in the form no margin can absorb, so the control moves from the fixture's margin to the runner's receipt. D0388 pair, chosen before the tree is read: known-positive - a run whose launch and exit clocks disagree by more than the margin (the unbiased clock injected by a test seam, or a fixture receipt with standby = 5820) re-runs its failed tests once and the receipt names standby, the first reds and the re-run verdicts; known-negative - a run with standby = 0 and one red writes fail with no re-run and the receipt's standby field reads 0. VERIFY: the receipt of a green run at HEAD carries standby = 0; a unit test on the receipt writer with an injected 5820 s drift and two planted reds shows the re-run path and the named fields."; }
        action dcRanReceiptCarriesOnePrefix;
        verification dcRanReceiptCarriesOnePrefixDoD : Test { :>> id = "78f9ce8c-ca56-4690-8e3a-59f1653f2877"; :>> method = VerificationMethod::test; :>> procedureText = "DONE MEANS: keel record result and keel record gate-result land the same `// RAN: <receipt>` line whether the evidence passed to them carries the prefix or not - the writer (members/keel-write/src/write.rs, the two format sites that prepend the prefix) strips one leading `// RAN:` and its surrounding whitespace before formatting, so `// RAN: // RAN:` can no longer be written; the two readers that act on a receipt (members/keel-write/src/reverify.rs's demo-receipt scan and members/keel-github/src/ci_runs.rs's ci-run scan) take the text after the LAST `// RAN:` on the line, so the 71 doubled lines already on the tree at 904ff24c read as their receipts and not as the empty string; and the resolver says, in its sprint's Decision, whether those 71 lines are migrated (a content-preserving codemod under .engine/tools/migrations/ with a reconciled dry run, per the migration skill) or left as history the readers now tolerate. Resolves issue596. D0388 pair, chosen before the tree is read: known-positive - evidence `// RAN: cargo test -> 3 passed` written through record result lands one `// RAN: cargo test -> 3 passed` line, and a fixture file holding `// RAN: // RAN: keel show priority .` beside a passing result is read by the demo scan as the receipt `keel show priority .`; known-negative - evidence `cargo test -> 3 passed` (no prefix) still lands with exactly one prefix, and a fixture line whose only text after the prefix is empty is still read as no receipt. VERIFY: cargo test -p keel-write and -p keel-github pass with the four cases as unit tests; git grep -c '// RAN: // RAN:' over .tracking and .engine at the resolving commit is 0 if migrated, or the Decision names the count left and why."; }
        action dcTouchedRunEnvironmentIsNormalized;
        verification dcTouchedRunEnvironmentIsNormalizedDoD : Test { :>> id = "6b797989-e815-4ef6-8e25-7ffad4ce035e"; :>> method = VerificationMethod::test; :>> procedureText = "DONE MEANS: keel suite --touched (and so keel land's pre-push run, D0421/D0422) spawns cargo-nextest and cargo test with every KEEL_* variable the binary reads (the family enumerated in one place in keel-suite - at least KEEL_ACTOR, KEEL_BIN, KEEL_ROOT) removed from the child environment, so a test binary's verdict depends on the content the receipt keys (D0474) and never on the committing shell; the touched receipt carries an `env` row naming the variables it cleared (or `none present`), so a reader can see the run was normalized; and the receipt's content key is unchanged by the shell's variables (a run with KEEL_ACTOR set and one without produce the same code_key and tree_key). The two launcher tests fixed in the resolving commit keep their remove_var lines as belt to this brace. Resolves issue598. D0388 pair, chosen before the tree is read: known-positive - a test binary that asserts std::env::var('KEEL_ACTOR').is_err() passes under keel suite --touched from a shell with KEEL_ACTOR=probeActor exported; known-negative - the same binary run by bare cargo test from that shell fails, naming the variable. VERIFY: cargo test -p keel-suite passes with the pair as unit tests over the spawn's environment builder; a keel land from a shell with KEEL_ACTOR exported lands green on the launcher tests, and its receipt's env row names KEEL_ACTOR."; }
        action dcTouchedReceiptNamesItsBaseSha;
        verification dcTouchedReceiptNamesItsBaseShaDoD : Test { :>> id = "ebbef86d-028f-482f-a3ba-b451717c4eb0"; :>> method = VerificationMethod::test; :>> procedureText = "DONE MEANS: keel suite --touched (and so keel land's pre-push run) writes `base_sha = '<full sha>'` in .keel/metrics/touched-receipt.toml beside `base = '<ref>'`, the sha being the merge-base it diffed from (touched.rs's `from`), so the range a receipt measured is `base_sha..head` and re-derivable after the push moves the ref; the landing log's `touched tests: base ...` line names the sha with the ref; keel show status's touched row names the range; and scripts/exec_brief/facts.py's landingCommitEnginePaths reads `git diff --name-only <base_sha> <head> -- .engine` from the receipt and drops the push-history recovery (issue599). Resolves issue599. D0388 pair, chosen before the tree is read: known-positive - a receipt written by the runner in a fixture repo whose origin/main is two commits behind HEAD carries base_sha equal to `git merge-base origin/main HEAD` and its stems equal the module stems of `git diff --name-only base_sha..HEAD`; known-negative - a receipt with the base line only (no base_sha) is refused by the receipt reader with a line naming the missing key. VERIFY: cargo test -p keel-suite passes with the pair as unit tests; a keel land from a tree two commits ahead lands green and its receipt's base_sha names the pre-push origin/main sha."; }
        action dcRecordTaskPlacesTheItemBeforeANamedOne;
        verification dcRecordTaskPlacesTheItemBeforeANamedOneDoD : Test { :>> id = "d5f340f6-93e3-46d8-b7ed-eff243a86cf4"; :>> method = VerificationMethod::test; :>> procedureText = "DONE MEANS: keel record task accepts --before <task> and declares the new action and its DoD Test immediately before the named task inside the same def, so a backlog item that must outrank an existing one (a split slice its parent now depends on, a resolver that must land before the item it unblocks) is written at its priority position by the API. Declaration order IS priority (D0052), and record task today appends at the end of the def: in sprint 739 the split item dcHooksAreAMember, on which dcKeelCliIsThinDispatch (rank 2) was made to depend, landed at rank 26 and had to be moved by a hand script (move739.py) that cut its two lines and pasted them before the parent - an edit of my own item, legal under D0108, but a write the API should own, since every backlog line the shell or a script moves is a line the write lock, the provenance check and the validate gate did not see move. A --before naming a task not in the def is refused naming the def and the task. Without --before the verb appends as it does today, so every existing caller is unchanged. D0388 pair: known-positive is a fixture def with tasks A and B in that order, record task --before B writes C, and the def then reads A, C, B with C's DoD directly under its action line; known-negative is record task --before Z where Z is not in the def, refused with exit nonzero, the fixture's bytes unchanged."; }
        action dcRecordDecisionRefusesACompoundText;
        verification dcRecordDecisionRefusesACompoundTextDoD : Test { :>> id = "a2f33a90-0b14-41b5-ac5e-b4bc9c30e500"; :>> method = VerificationMethod::test; :>> procedureText = "Resolves issue604. DONE MEANS: keel record decision runs the decision-scaffolding guard's clause_count over the drafted decision text before the write and REFUSES a text that enumerates two or more clauses ((1)(2), (a)(b), clause A/B in sequence), naming the count and D0303's fix (one Decision per clause, #DependsOn edges between them) - the same rule the guard applies after the fact, moved to the write so a compound Decision never lands in the tree; the refusal is a write-path refusal (exit non-zero, nothing written), not a warning. clause_count moves to, or is re-exported from, a place both keel-guards and the write path can call without duplicating the regexes. Known-positive: a draft whose decision section reads '(1) ... (2) ...' is refused naming 2 clauses. Known-negative: D0516's rewritten one-clause text is written. sprint 744's first D0516 draft is the fixture."; }
        action dcBareNameResolvesLocallyOrUniquelyOrRefuses;
        verification dcBareNameResolvesLocallyOrUniquelyOrRefusesDoD : Test { :>> id = "c8503a75-1463-48fe-8fb9-6ea934b8dc5e"; :>> method = VerificationMethod::test; :>> procedureText = "Resolves issue605; delivers D0517 (HELD - implement only once its status is accepted, and under whichever OPTION the human chose). DONE MEANS under OPTION A: the keel-model build keeps every declaration instead of last-writer-wins (model.rs:244), and a bare reference resolves to a declaration in the referencing package first, else the single declaration in the model, else the build REFUSES naming every candidate with file and line; the parser accepts `Package::name` as an edge target and the resolver binds it to that package's declaration; duplicate-identity gains a cross-package WARNING row whose count on this tree is asserted by a test (270 on 2026-09-18); `keel show why <name>` answers for each declaration; CLAUDE.md invariant 3 and guards.md row duplicate-identity say the rule the engine now keeps. Known-positive: two packages declaring `part st001`, a `#DerivedFrom` edge in a THIRD package naming bare st001 - the build refuses naming both files. Known-negative: the same edge written inside the package that declares its own st001 - resolves locally, gate green, `show why` reaches the local item. Under OPTION B the DoD is instead: duplicate-identity's name scan is model-wide and a duplicate is a violation, preceded by a D0067 migration of the 270 names with control totals. GH#85 is answered on GitHub with the tracked ids and closed there."; }
        action dcGroundStepBindsToACheckThatReadsThePage;
        verification dcGroundStepBindsToACheckThatReadsThePageDoD : Test { :>> id = "26fb2eec-4d4c-4e36-b793-dd7532b5b605"; :>> method = VerificationMethod::test; :>> procedureText = "Resolves issue606; delivers D0518 (HELD - implement only once its status is accepted, under the OPTION chosen). DONE MEANS under OPTION A: scripts/check_templates.py --brief refuses a page carrying any of four content shapes - a course cost reading none, n/a or a dash; an option label beginning with a verdict verb (accept, reject, approve, confirm, pass, fail, judge); a before/after row whose two cells are both record states; a tab with no premise rendered before its options - naming the tab and the shape; every build script under scripts/exec_brief that imports check_templates (35 of 45 on 2026-09-18; the ten 2026-09-08/09 pages predate the checker) refuses to write the page on that refusal, and the count is asserted by a test; rules.sysml declares brief-page-quality with that check as its mechanism; decision-surfacing.sysml dsGround.checkedBy names brief-page-quality and step-check-resolves stays green; guards.md and the decision-surfacing skill say so in the same commit; the current published page is re-checked and republished if a tab carries a shape. Known-positive: a fixture tab whose two options read `Judge X as PASS` / `Fail X with a direction` and whose cost reads `None.` - refused naming both shapes. Known-negative: a premise-led tab with a stated cost and a hand-only option - passes. Under OPTION B the DoD is instead: dsGround drops checkedBy and carries the D0321 contract declaration naming why no check opens the page. GH#84 is answered on GitHub with the tracked ids and closed there."; }
        action dcGithubIngestDedupsOnTheIssueIdentity;
        verification dcGithubIngestDedupsOnTheIssueIdentityDoD : Test { :>> id = "b413a59e-accd-4bc3-97de-5120e330078a"; :>> method = VerificationMethod::test; :>> procedureText = "Resolves issue607. DONE MEANS: the github ingest's re-ingest refusal keys on the issue's identity, not on the exact html_url string - `record_statement` (intake_write.rs:171) refuses when an existing Statement's sourceUrl names the same owner-independent issue: the GitHub API's numeric `id` recorded as a sourceId attribute, or, until the schema carries one, a URL comparison that treats the two repo names GitHub redirects between as one (the rename sysmlv2-ai-toolkit -> keel doubled 23 Statements on this tree, GH#33-38, 40, 41, 60-74, 2026-09-14 to 09-16); the 23 later duplicates are retired by a `#Supersede` edge each from the earlier Statement (the words were recorded once already; identity is the UUID and the text is unchanged) so the intake lens counts 36 untriaged GitHub statements, not 59; `keel show intake` gains a `duplicateSources` row (sourceUrls resolving to one issue) asserted at 0 by a test after the retirement. Known-positive: a fixture tree holding a Statement with sourceUrl .../o/old/issues/7, an ingest of the same issue at .../o/new/issues/7 (redirected) is refused as already recorded. Known-negative: issue 8 on the same repo ingests."; }
        action dcTouchedRunNamesABuildThatNeverRan;
        verification dcTouchedRunNamesABuildThatNeverRanDoD : Test { :>> id = "08e337ca-1e41-4578-97ea-2b7141064d5b"; :>> method = VerificationMethod::test; :>> procedureText = "Resolves issue608. A touched run whose cargo invocation did not finish (suite::never_ran: cargo not ok, zero passed, zero failed) is reported as NEVER RAN, not as red: the land line reads `touched tests NEVER RAN for [rows] - <first cargo error line> - REFUSING to push` and the receipt carries `outcome = 'never-ran'` with the rows and that line, distinct from `fail` (a test went red) and `eol-mismatch` (cargo never started). The compile-crash class is retried once before it is anyone's refusal: when the error text carries `STATUS_DLL_INIT_FAILED` or exit code `0xc0000142`, the same invocation is re-run once with `--jobs 2` and the receipt's `retried` row names the first attempt's cause; a second crash is the never-ran refusal. D0388 pair: positive = a captured cargo text holding the 2026-09-18 crash (`could not compile keel-view (lib)` ... `0xc0000142`) renders `never-ran` naming every member row and the error line, and the retry fires; negative = nextest text with one red row renders `fail` naming that row alone and no retry. Documented in .engine/docs/guards.md beside D0421 and in CLAUDE.md section 4 Git (doc-sync, same commit); a co-committed #ProspectiveChange Decision governs the retry (D0209 cl.2)."; }
        action dcRatchetOverTheProjectsCorpusIsNeverSeeded;
        verification dcRatchetOverTheProjectsCorpusIsNeverSeededDoD : Test { :>> id = "31b25d3e-0500-4f06-9bd2-dc284cc0a013"; :>> method = VerificationMethod::test; :>> procedureText = "Resolves issue610 (GH#90). step_engine_resync in members/keel-process/src/migrate.rs guards a project-owned contract against overwrite (is_project_owned_contract && dst.exists()) but not against addition, so a first-time adopter receives parser-coverage-baseline.toml carrying the engine's own census (skipped = 7) as its ratchet and guard parser-coverage reads 1 + 7 > 7 inside the run. DONE MEANS: is_ratchet_over_project_corpus names the contract; the resync returns before planning it when the destination does not exist; the file is still overwritten-never and added-never, and every other project-owned contract keeps its shipped default on first adoption. Known-positive, chosen before the tree is read: a unit test plans a resync into a fixture root with no contracts/parser-coverage-baseline.toml and asserts no planned file ends in that name. Known-negative: the same fixture holding a project-authored parser-coverage-baseline.toml keeps its bytes (the overwrite guard, unchanged), and activation.toml is still planned into an empty fixture."; }
        // RAN: TOUCHED RECEIPT: outcome=pass passed=941 failed=0 seconds=719 at=1789777049 launch=1789776231 (at>launch: ok) stems=['enforcement', 'init', 'migrate', 'onboard', 'surface', 'write'] changed=['enforcement', 'init', 'migrate', 'onboard', 'surface', 'write'] (MATCH) lib=true head=fe57df66 log=./.keel/metrics/touched-1789776328.log test result line: binary=land_gate test=land_refuses_to_push_a_workspace_carrying_a_broken_project millis=288301 verdict=pass (slowest)
        part dcRatchetOverTheProjectsCorpusIsNeverSeededDoDR1 : TestResult { :>> id = "ad4bc801-6d10-4e1c-887a-ffe15bd131c4"; :>> outcome = VerdictKind::pass; :>> judgedAgainst = "fe57df66"; :>> judgedAt = "2026-09-18"; :>> judgedBy = "claudeFable5"; }
        action dcCharterResolvesInBothDecisionDirectories;
        verification dcCharterResolvesInBothDecisionDirectoriesDoD : Test { :>> id = "c12901f8-12ca-4464-af1f-1d047d4aa8f3"; :>> method = VerificationMethod::test; :>> procedureText = "Resolves issue611 (GH#89). keel_model::onboard::charter_resolves (members/keel-model/src/onboard.rs) resolved a manifest's charteredBy against .engine/decisions/ alone while the resync deploys engine Decisions to .engine/reference/decisions/, so the shipped charteredBy = d0226 was unresolvable in every adopting tree and guard activation-manifest was red inside migrate. DONE MEANS: charter_resolves reads both directories; a charter naming a Decision in neither still fails (issue380). Known-positive, chosen before the tree is read: a unit test with a fixture holding only .engine/reference/decisions/0226-x.sysml resolves d0226. Known-negative: the same fixture asked for d9999 does not resolve, and the authoring-layout fixture (.engine/decisions/) still resolves as before."; }
        // RAN: TOUCHED RECEIPT: outcome=pass passed=941 failed=0 seconds=719 at=1789777049 launch=1789776231 (at>launch: ok) stems=['enforcement', 'init', 'migrate', 'onboard', 'surface', 'write'] changed=['enforcement', 'init', 'migrate', 'onboard', 'surface', 'write'] (MATCH) lib=true head=fe57df66 log=./.keel/metrics/touched-1789776328.log test result line: binary=land_gate test=land_refuses_to_push_a_workspace_carrying_a_broken_project millis=288301 verdict=pass (slowest)
        part dcCharterResolvesInBothDecisionDirectoriesDoDR1 : TestResult { :>> id = "572e9dcd-ef31-4cda-a584-a2b8ad39c721"; :>> outcome = VerdictKind::pass; :>> judgedAgainst = "fe57df66"; :>> judgedAt = "2026-09-18"; :>> judgedBy = "claudeFable5"; }
        action dcSourceReferenceReadsTheAdoptersOwnClaims;
        verification dcSourceReferenceReadsTheAdoptersOwnClaimsDoD : Test { :>> id = "88726674-b3a7-4f7d-9946-a48a52e39f7c"; :>> method = VerificationMethod::test; :>> procedureText = "Resolves issue612 (GH#88). guard source-reference (members/keel-guards/src/surface.rs source_reference) scopes itself by Cargo.toml at the root and then reads every living doc under .engine/, shipped or authored, so an adopter with a Rust workspace is red on citations of members/keel-process/src/migrate.rs that only this repository can hold, and a scaffold's 0 scanned is a pass by absence of a corpus. DONE MEANS: in a root where keel_model::corpus::is_self_build is false, a living doc whose relative path the embedded engine (keel_schema::embedded::ENGINE_DIR) ships is outside the population - not read, not counted - and the report's warnings carry one line saying how many shipped docs were set aside; the self-build reads every living doc as today; CLAUDE.md and a project-added file under .engine/ are read in both. Known-positive, chosen before the tree is read: a unit test builds a non-self-build root with Cargo.toml, a member src, a copy of .engine/skills/project-migration/SKILL.md citing members/keel-process/src/migrate.rs, and a project-authored .engine/docs/own.md citing a stale line of its own member file; the guard reports exactly one violation, the project's, and one warning naming one shipped doc set aside. Known-negative: the same fixture with keel-cli/Cargo.toml present (the self-build predicate) reports two violations."; }
        // RAN: TOUCHED RECEIPT: outcome=pass passed=941 failed=0 seconds=719 at=1789777049 launch=1789776231 (at>launch: ok) stems=['enforcement', 'init', 'migrate', 'onboard', 'surface', 'write'] changed=['enforcement', 'init', 'migrate', 'onboard', 'surface', 'write'] (MATCH) lib=true head=fe57df66 log=./.keel/metrics/touched-1789776328.log test result line: binary=land_gate test=land_refuses_to_push_a_workspace_carrying_a_broken_project millis=288301 verdict=pass (slowest)
        part dcSourceReferenceReadsTheAdoptersOwnClaimsDoDR1 : TestResult { :>> id = "fb147277-cb3b-4887-affc-6a845890b27a"; :>> outcome = VerdictKind::pass; :>> judgedAgainst = "fe57df66"; :>> judgedAt = "2026-09-18"; :>> judgedBy = "claudeFable5"; }
        action dcToleratedRecordsSurviveTheRun;
        verification dcToleratedRecordsSurviveTheRunDoD : Test { :>> id = "560f21ed-1fe1-4a42-8f17-268ea658213c"; :>> method = VerificationMethod::test; :>> procedureText = "Resolves issue613 (GH#87). check_preconditions in members/keel-process/src/migrate.rs tolerates a NEW .tracking/obligations/*.sysml (is_tolerable_obligation) and prints it separable, then project_gate runs gate guard all over the whole tree and guard issues fails on that same untriaged record, and restore's git clean -fdq deletes the never-committed file on the way out. DONE MEANS: the tolerated paths flow from check_preconditions to the gate and to restore; a guard violation whose subject is a part declared in a tolerated record is discounted from the post-apply verdict and printed as discounted, every other violation still fails the run; restore passes each tolerated path as a git clean -e exclusion so the file survives a rollback. Known-positive, chosen before the tree is read: a unit test over gate output text with a tolerated record declaring part obligationabc : Issue and a guard output whose only failing lines are [guard:issues] FAIL and ERROR obligationabc: untriaged judges the run green and names the discount; a unit test of the clean argument list contains -e .tracking/obligations/red-yield-abc.sysml. Known-negative: the same guard output with one more line ERROR issue999: untriaged stays red; an empty tolerated list yields today's clean arguments exactly."; }
        // RAN: TOUCHED RECEIPT: outcome=pass passed=941 failed=0 seconds=719 at=1789777049 launch=1789776231 (at>launch: ok) stems=['enforcement', 'init', 'migrate', 'onboard', 'surface', 'write'] changed=['enforcement', 'init', 'migrate', 'onboard', 'surface', 'write'] (MATCH) lib=true head=fe57df66 log=./.keel/metrics/touched-1789776328.log test result line: binary=land_gate test=land_refuses_to_push_a_workspace_carrying_a_broken_project millis=288301 verdict=pass (slowest)
        part dcToleratedRecordsSurviveTheRunDoDR1 : TestResult { :>> id = "840e42a8-d7dd-44c1-b3ea-5a0adad23605"; :>> outcome = VerdictKind::pass; :>> judgedAgainst = "fe57df66"; :>> judgedAt = "2026-09-18"; :>> judgedBy = "claudeFable5"; }
        action dcAWriteRefusesTheMemberTheTreesSchemaLacks;
        verification dcAWriteRefusesTheMemberTheTreesSchemaLacksDoD : Test { :>> id = "9f47555c-9e03-45ab-b8af-6e0ba516fb66"; :>> method = VerificationMethod::test; :>> procedureText = "Resolves issue614 (GH#86). proposed_tier in members/keel-write/src/write.rs returns the binary's PROPOSED constant for an AI-examined pass and nothing reads the tree's schema, so record gate-result and record result write VerdictKind::proposed into a tree whose .engine/schema/core/element.sysml (release b171cd7 vintage, before 24dbcfb3) declares no such member, and gate validate then rejects the tree. DONE MEANS: before either write lands PROPOSED it reads the VerdictKind enum in the tree's own .engine/schema/core/element.sysml; when the member is absent the write refuses with a new WriteError variant naming the member, the enum, the file and keel migrate, and the target file is unchanged; a root with no element.sysml (the write API's fixtures) is not read. Known-positive, chosen before the tree is read: a unit test with a fixture root whose element.sysml declares enum def VerdictKind { pass; fail; inconclusive; error; } and an actor registry naming an ai judge records a demo gate pass and asserts the refusal names proposed and keel migrate and the file's bytes are unchanged. Known-negative: the same fixture with proposed in the enum lands VerdictKind::proposed as today, and a human judge lands pass on the older enum without reading it."; }
        // RAN: TOUCHED RECEIPT: outcome=pass passed=941 failed=0 seconds=719 at=1789777049 launch=1789776231 (at>launch: ok) stems=['enforcement', 'init', 'migrate', 'onboard', 'surface', 'write'] changed=['enforcement', 'init', 'migrate', 'onboard', 'surface', 'write'] (MATCH) lib=true head=fe57df66 log=./.keel/metrics/touched-1789776328.log test result line: binary=land_gate test=land_refuses_to_push_a_workspace_carrying_a_broken_project millis=288301 verdict=pass (slowest)
        part dcAWriteRefusesTheMemberTheTreesSchemaLacksDoDR1 : TestResult { :>> id = "59bd37b9-5158-4ae0-8e0c-d7a7bf6c316f"; :>> outcome = VerdictKind::pass; :>> judgedAgainst = "fe57df66"; :>> judgedAt = "2026-09-18"; :>> judgedBy = "claudeFable5"; }
        action dcAFreshAdopterTreeIsGreenUnderEveryGuard;
        verification dcAFreshAdopterTreeIsGreenUnderEveryGuardDoD : Test { :>> id = "09b377c1-a817-4ed7-9861-d447244f3432"; :>> method = VerificationMethod::test; :>> procedureText = "A test in the suite deploys the embedded engine (keel_schema::embedded::ENGINE_DIR) plus a `keel init` scaffold into a temp root that is NOT the self-build (no keel-cli/Cargo.toml) but does hold a Cargo.toml and one Rust member, then runs every forward guard over it (keel_guards::run_all or the equivalent entry) and asserts zero violations, naming any red guard in the failure message. KNOWN-POSITIVE (chosen before the tree was read): the fixture as deployed today is green under every guard. KNOWN-NEGATIVE: the same fixture with a living doc under .engine/docs/own.md citing a members path that does not resolve is red under exactly one guard, source-reference. The test is keyed on the embedded engine's content so a shipped doc that starts reddening an adopter fails here, in this repo, before a downstream tree finds it (retro sprint 745, GH#88; resolves issue615)."; }
        // RAN: cargo test --release -p keel-cli --test init_smoke -> test result: ok. 3 passed (an_adopter_shaped_scaffold_is_green_under_every_guard: KNOWN-POSITIVE the init scaffold plus Cargo.toml and members/widget is green under gate guard all with no [guard:] FAIL line; KNOWN-NEGATIVE .engine/docs/own.md citing members/widget/src/spin.rs:3 is red under exactly one guard, source-reference, naming spin.rs:3)
        part dcAFreshAdopterTreeIsGreenUnderEveryGuardDoDR1 : TestResult { :>> id = "9d2ee6b8-abfa-4380-a913-2318e2e46ee8"; :>> outcome = VerdictKind::pass; :>> judgedAgainst = "4a0abc85"; :>> judgedAt = "2026-09-18"; :>> judgedBy = "claudeFable5"; }
        action dcSchemaLacksMemberRefusalIsLedgered;
        verification dcSchemaLacksMemberRefusalIsLedgeredDoD : Test { :>> id = "d3786dbb-e875-4974-8b66-61720be6ea69"; :>> method = VerificationMethod::test; :>> procedureText = "WRITE_PATH_REFUSALS (members/keel-write/src/write.rs) carries rows { verb: 'append-result', check: 'schema-member', refuses: 'WriteError::SchemaLacksMember' } and the same for 'append-gate-result'; WRITE_PATH_CHECKS in members/keel-view/src/view/census.rs carries the matching census row (subject: the AI's write; state: active), and the refusal is ledgered through ledger_refused under that control name so `keel show enforcement-report` counts it. KNOWN-POSITIVE (chosen before the tree was read): tests::every_live_row_has_a_refusal_and_every_refusal_a_row passes with the new rows. KNOWN-NEGATIVE: removing either row fails that same test naming the orphan. A vintage-schema fixture that trips the refusal leaves one `append-result:schema-member` line in .keel/metrics/hooks.jsonl (retro sprint 745, issue614/D0521; resolves issue616)."; }
        // RAN: cargo test --release -p keel-view --lib -- census:: -> 9 passed (every_live_row_has_a_refusal_and_every_refusal_a_row with the two schema-member rows); KNOWN-NEGATIVE probe: the append-gate-result row removed from WRITE_PATH_REFUSALS -> that test FAILED naming the orphan [append-gate-result:schema-member], row restored; cargo test --release -p keel-cli --test schema_member_refusal_is_ledgered -> 3 passed (one append-result:schema-member and one append-gate-result:schema-member line in .keel/metrics/hooks.jsonl on the older vintage, never unregistered:; none on the tree declaring proposed)
        part dcSchemaLacksMemberRefusalIsLedgeredDoDR1 : TestResult { :>> id = "9889b873-b77c-4ce9-810b-a2adef91ab56"; :>> outcome = VerdictKind::pass; :>> judgedAgainst = "4a0abc85"; :>> judgedAt = "2026-09-18"; :>> judgedBy = "claudeFable5"; }
        action dcUnresolvedCharterAdviceFitsAFirstTimeAdopter;
        verification dcUnresolvedCharterAdviceFitsAFirstTimeAdopterDoD : Test { :>> id = "0b868976-733b-4815-a972-df8bc37aa746"; :>> method = VerificationMethod::test; :>> procedureText = "The UNRESOLVED CHARTER line in members/keel-model/src/onboard.rs (cmd, the non-JSON branch) distinguishes the two trees it can be printed in: a tree with a prior activation.toml in its git history is told to restore it (today's advice); a tree with none - a first-time adopter, whose only activation.toml is the one the resync just deployed - is told to run the project-onboarding skill or set charteredBy to a Decision the tree holds, and is never told to restore from a history that has nothing. The distinction is computed from git, not assumed: restore is said only where git holds a version of .engine/contracts/activation.toml other than the working file (two or more commits touch it, or the working file has moved from the one commit); a first-time adopter whose single committed manifest IS the working file is told the onboarding advice too. KNOWN-POSITIVE (chosen before the tree was read): a temp git repo with one prior commit of activation.toml prints the restore advice. KNOWN-NEGATIVE: a temp git repo whose only activation.toml is uncommitted prints the onboarding advice and not the word history; the activation-manifest guard message in members/keel-guards/src/enforcement.rs, which ends in the same advice, follows the same rule (retro sprint 745, GH#89/issue611; resolves issue617)."; }
        // RAN: cargo test --release -p keel-model --lib -- onboard:: -> 4 passed (the_unresolved_charter_advice_names_restore_only_where_git_holds_a_version_to_restore: KNOWN-POSITIVE an overwritten committed manifest prints restore/history; KNOWN-NEGATIVE an uncommitted-only manifest prints project-onboarding and charteredBy and never history, a single unchanged commit likewise, no repository likewise); the activation-manifest guard message (members/keel-guards/src/enforcement.rs) ends in the same computed advice
        part dcUnresolvedCharterAdviceFitsAFirstTimeAdopterDoDR1 : TestResult { :>> id = "89bd41a5-d80d-4750-bd6d-21f4239197b8"; :>> outcome = VerdictKind::pass; :>> judgedAgainst = "4a0abc85"; :>> judgedAt = "2026-09-18"; :>> judgedBy = "claudeFable5"; }
        action dcABuiltBriefIsDistinguishableFromAPublishedOne;
        verification dcABuiltBriefIsDistinguishableFromAPublishedOneDoD : Test { :>> id = "b554135d-f436-4f8e-bb91-08621f58cce2"; :>> method = VerificationMethod::test; :>> procedureText = "Resolves issue618 (the forty-ninth publish's write-back was missed and the fiftieth page was never published; both silent for two turns). DONE MEANS: the build path of the decision brief refuses to write a page while the previous state is inconsistent, and a built page is distinguishable from a published one. (1) One helper in scripts/exec_brief (imported by the build scripts the way check_templates is) reads the previous page's data-records set and .keel/decision-page.toml's ids and refuses the build, naming both sets and the missed write-back, when they differ - the previous page is the live artifact read back, so a difference IS a publish that was not written back. (2) A build writes .keel/decision-page.pending.toml (ids, the tree the page was computed at, the output path); the write-back step deletes it; a build refuses while a pending sidecar stands whose ids differ from the previous page's data-records, naming the unpublished page - a page that was built and never published is no longer silent. (3) facts.py emits a pageState fact (tomlIds, pendingIds or null, publishedAgainst) so the brief itself can say whether the channel was consistent when it was built. (4) A test under scripts asserts the count of build scripts calling the helper the way D0518's test asserts check_templates callers. (5) The decision-surfacing skill step 5 and .engine/processes/decision-surfacing.sysml dsPublish name the helper as the check that holds the write-back - that is a process-change and co-commits a held #ProspectiveChange Decision (D0209 cl.2; D0337 HELD proposed for the human). KNOWN-POSITIVE (chosen before the tree is read): a fixture previous.html carrying data-records d0001,d0002 against a toml whose ids are d0001 - refused naming d0002 as published-but-unrecorded. KNOWN-NEGATIVE: the same fixture against a toml whose ids are d0001,d0002 and no pending sidecar - builds. Second positive: a pending sidecar with ids d0001,d0003 beside a previous page carrying d0001,d0002 - refused naming d0003 as built-but-unpublished."; }
        action dcReleaseGuardFixturesPinTheBinaryVersion;
        verification dcReleaseGuardFixturesPinTheBinaryVersionDoD : Test { :>> id = "ee68b78e-7a8c-4783-8767-4cb8ea438f5c"; :>> method = VerificationMethod::test; :>> procedureText = "Resolves issue619. The two wrapper-pin fixtures in keel-cli/tests/release_checksums_catch_it.rs write the BINARY's own version (env!('CARGO_PKG_VERSION')) as the engine pin, never a literal release; the stale table below the pin stays a literal older release. KNOWN-POSITIVE (chosen before the tree was read): the six tests in that binary pass under the 0.5.0 build (cargo test --release -p keel-cli --test release_checksums_catch_it: 6 passed). KNOWN-NEGATIVE: the same fixtures pinned at the literal '0.4.1' are refused under engine-version skew before the guard runs, which is what the v0.5.0 release-cut land observed (touched-1789783757.log: 2 failed, both panics quoting `guard REFUSED under engine-version skew (D0251)`)."; }
        // RAN: cargo test --release -p keel-cli --test release_checksums_catch_it -> test result: ok. 6 passed; 0 failed (the two wrapper-pin tests among them, pinned at env!('CARGO_PKG_VERSION') = 0.5.0). KNOWN-NEGATIVE observed by keel land before the fix: touched-1789783757.log, 2 failed, both panics quoting `guard REFUSED under engine-version skew (D0251)`.
        part dcReleaseGuardFixturesPinTheBinaryVersionDoDR1 : TestResult { :>> id = "cf58e979-313b-40eb-9b64-67e762eeeead"; :>> outcome = VerdictKind::pass; :>> judgedAgainst = "72eebf0a"; :>> judgedAt = "2026-09-18"; :>> judgedBy = "claudeFable5"; }
        action dcVerbFoldsTravelWithMigrate;
        verification dcVerbFoldsTravelWithMigrateDoD : Test { :>> id = "cb53229a-22aa-4144-92d3-acae485d1bbe"; :>> method = VerificationMethod::test; :>> procedureText = "Resolves issue622 (GH#86-90 class: the downloaded 0.5.0 `keel migrate` over a 0.4.1-scaffolded adopter tree rolled itself back on `[guard:cli-reference] FAIL - 16 violation(s)`, every one in a file the run does not write: the adopter's CLAUDE.md as `keel init` 0.4.1 scaffolded it, and the comments of the two project-owned contracts attestation-policy.toml and github-actors.toml). DONE MEANS: (1) one authored fact, `.engine/contracts/verb-renames.toml` (engine-owned, resynced, read from the binary's embedded copy by both readers), holds the spelling this binary dispatches for each top-level verb a fold RENAMED rather than folded under its own name - `add-task` -> `record task`, `github-decider` -> `github decider`, `report` -> `render report` and the rest of the five folds' tables; a lens (`orient` -> `show orient`) and a same-named sub-verb (`validate` -> `gate validate`) stay computed from the CLI facts and are not listed. (2) `keel migrate` gains a `verb-respell` step that rewrites, in every living doc the cli-reference guard reads and the resync does not write in this plan (CLAUDE.md, the project-owned contracts, a project-added file under .engine/), exactly the references the guard would fail and a spelling exists for; a reference with no spelling stays as written and the guard still names it. CLAUDE.md joins the run's scope: the door's cleanliness check and the rollback's restore, the restore only when the pre-run commit holds the file. (3) The guard's `today it is` clause reads the same fact, so `keel add-task` is now told `keel record task`. (4) The step is idempotent: a second run plans zero edits. KNOWN-POSITIVE (chosen before the tree was read): a fixture CLAUDE.md naming `keel orient`, `keel add-task` and `keel report` in code spans and a contracts/attestation-policy.toml comment naming `keel guard attestation-authority` - the step plans one edit per file and the rewritten text names `keel show orient`, `keel record task`, `keel render report`, `keel gate guard attestation-authority`; the cli-reference guard over the rewritten fixture is green. KNOWN-NEGATIVE: the same fixture already at those spellings plans zero edits and is byte-identical after the step; a file the resync writes in the same plan is not touched by the step. Second positive: the downloaded-shape end-to-end - a 0.4.1 `keel init` tree with a Cargo workspace, migrated by this build, lands (no rollback) and its CLAUDE.md names `keel show orient`."; }
        // RAN: cargo test --release -p keel-guards --lib cli_reference_tests -> 4 passed (a_scaffolded_doc_is_respelled_to_what_the_binary_dispatches_and_the_current_spelling_is_left_alone: fixture CLAUDE.md respelled in 5 sites incl. fenced block + spans, second pass None, toml comment keel guard -> keel gate guard, current spellings None) cargo test --release -p keel-process --lib migrate::tests -> 13 passed (the_projects_own_living_docs_are_respelled_and_the_resyncs_files_are_not: KNOWN-POSITIVE one FileEdit each for CLAUDE.md + attestation-policy.toml, detail names file:line, edits == detail.len(); KNOWN-NEGATIVE shipped docs/guards.md holding keel orient not read; second run 0 edits; current spellings byte-identical) cargo test --release -p keel-guards --lib engine_written_tests -> 1 passed (respell of HEAD is outside the lock; respell + one line, a non-respell edit and the unchanged file are under it) cargo test --release -p keel-cli --test migration_respells_the_projects_own_docs -> 3 passed (a_tree_scaffolded_at_0_4_1_lands_and_its_own_docs_name_todays_verbs: keel init tree + 0.4.1 CLAUDE.md + Cargo workspace + 0.4.1 contract comments, migrate LANDS, CLAUDE.md names keel show orient / keel record task / keel render report / keel gate validate, gate guard cli-reference PASS on the migrated tree, committed second run says Nothing to do byte-identical; an_interrupted_run_restores_claude_md_with_the_rest; an_uncommitted_claude_md_is_refused_at_the_door) Real adopter: /c/kt/adopt050 (scaffolded by the released 0.4.1 keel-windows-x86_64.exe init, Cargo workspace) migrated by this build (4a0abc85+dirty): [verb-respell] attestation-policy.toml:6 keel guard -> keel gate guard, github-actors.toml:13 keel github-decider -> keel github decider, CLAUDE.md 14 edits; wrote 303 file(s); the project's own gate is GREEN under 0.5.0: RETAINED; CLAUDE.md:19 names keel show orient; keel gate guard cli-reference on the adopter -> PASS 429 scanned 0 violation(s) This tree: gate validate 863 clean; check-engine clean; gate guard cli-reference PASS 453 scanned (the today-it-is clause now names keel record task for add-task); process-change PASS (locked edits authorised by d0519 via sprint746 charter, d0523 co-committed marked); sync-claude --check matches
        part dcVerbFoldsTravelWithMigrateDoDR1 : TestResult { :>> id = "11aecf0a-9715-4097-954d-31eaa217a88f"; :>> outcome = VerdictKind::pass; :>> judgedAgainst = "4a0abc85"; :>> judgedAt = "2026-09-18"; :>> judgedBy = "claudeFable5"; }
        action dcARepeatedSingleFlagIsRefused;
        verification dcARepeatedSingleFlagIsRefusedDoD : Test { :>> id = "ecd71a2f-5e2b-4b47-b592-f3fa3798e3f3"; :>> method = VerificationMethod::test; :>> procedureText = "Resolves issue623. DONE MEANS: a single-valued flag given twice on any keel command (`--derived-from st167 --derived-from st168`, `--sha A --sha B`) is REFUSED at the parse with a message naming the flag and the comma form where one exists, never one value taken silently; the refusal lives in the one flag reader keel-cli/src/main.rs uses (req / the D0455 unknown-flag walk), so every command inherits it. KNOWN-POSITIVE (chosen before the tree was read): `keel record decision --from F --derived-from st167 --derived-from st168` exits 2 naming --derived-from and the comma form, and writes nothing. KNOWN-NEGATIVE: `--derived-from st167,st168` records both edges as today."; }
        action dcTouchedReceiptNamesItsWriter;
        verification dcTouchedReceiptNamesItsWriterDoD : Test { :>> id = "99681318-3322-4244-9241-ee68a018a39b"; :>> method = VerificationMethod::test; :>> procedureText = "Resolves issue660. FOUND 2026-09-19, sprint 751: the first live render of the verifier's receipt showed .keel/metrics/touched-receipt.toml holding the run keel land made AFTER the ladder (736 passed, its own touched set over the landed range) in place of the ladder's touched rung (963 passed, its verdict line still in verify-touched.out) - one receipt file, two writers (the verify ladder's touched rung and the post-commit keel land), and nothing in the file says which wrote it. The renderer now reports a touched receipt dated after the ladder as a discrepancy, which detects the overwrite and cannot prevent it. DONE MEANS: every writer of touched-receipt.toml stamps a `writer` field (`verify` or `land`) and its launch epoch, keel land writes its receipt to its own slot (land-receipt.toml) or leaves the ladder's file untouched when the ladder's head equals the one it lands, keel verify --wait and scripts/verify_receipt.py read the ladder's slot only, and D0474's skip reads whichever slot is green at the current content. Known-positive, chosen before the tree is read: a fixture pair of receipts in which land's carries the later at and the ladder's the touched rung's verdict renders the ladder's passed count and no rewritten-by-a-later-run discrepancy. Known-negative: a ladder slot with no writer field is a red in verify_receipt.py --probe naming the field."; }
        action dcCeremonyRequirementsDeriveFromTheVerificationNeed;
        verification dcCeremonyRequirementsDeriveFromTheVerificationNeedDoD : Test { :>> id = "401fd1f1-427c-4b78-bd25-803be6f9d433"; :>> method = VerificationMethod::inspect; :>> procedureText = "The D0425 ceremony line (D0425, D0438, D0473, D0476, D0492, D0500, D0501, D0502, D0516, D0533) is ten Decisions and eleven sprints of delivered engine behaviour with no SystemRequirement between them and the Need they now derive from (nVerificationByAuthorityAndMethod, grounded 2026-09-19): the verifier renders and never restates, the recorder writes only from the verifier's receipt and only through keel record, the ladder stops at the first red, the probe pair travels in a file the primary wrote, each subagent is measured from its own start. Each of those is a contract a stakeholder holds the engine to, and each can FAIL - so each is a requirement (D0088), not a Decision's consequence. PRECONDITION, read from keel show authority-queue, never assumed: the three EngineSelfAnalysisNeeds show no needAcceptance row - the human has accepted them through engineSelfAnalysisNeedsAccept (Business ordering rule: no SystemRequirement until the Need it serves is accepted). DONE MEANS: SystemRequirements in .tracking/requirements/engine-derived-requirements.sysml, one per contract, each with a shall statement that names a threshold something can fail, rationale naming the Decision that first stated it, kind, priority and verificationMethod; `satisfy nVerificationByAuthorityAndMethod by srX;` for each; #Verify edges from the existing DoD Tests of the delivering sprints where the Test already exercises the contract (copy-and-add, no result touched); keel show coverage and tier-satisfaction read back showing the Need satisfied by the new requirements and each requirement verified or reported unverified honestly. Known-positive, chosen before the tree is read: a fixture requirement with a satisfy edge to a Need and a #Verify edge from a passing Test reads as satisfied and verified in tier-satisfaction. Known-negative: the same requirement with no #Verify edge reads as unverified, never as verified."; }
        action dcEveryGuardHasAControlMapRow;
        verification dcEveryGuardHasAControlMapRowDoD : Test { :>> id = "e0864d9e-a558-44ce-9fa9-0b0cab8967c4"; :>> method = VerificationMethod::test; :>> procedureText = "RESOLVES issue662. FOUND 2026-09-20 (sprint 753 retro): guards.md's control-map-reconciled row says every enforced guard is a SystemSafetyConstraint bound to a hazard, but control_map_reconciled (members/keel-guards/src/enforcement.rs) reconciles control-events.toml against declared controls only; seventeen of 76 guards had no `guard: <name>` row in .tracking/architecture/control-map.sysml and the guard passed, and D0515 was written believing the sprint-closure row existed. DONE MEANS: through a CR (guard clause = enforcement surface), control-map-reconciled gains a clause holding every entry of GUARD_NAMES to a `guard: <name>` SystemSafetyConstraint in control-map.sysml with a dependency to a declared Hazard, naming each guard without one; the seventeen missing rows are authored first, each bound to the hazard its guard controls, so the ratchet starts at zero; the guards.md row says what the code does; the unit test carries the D0388 pair (a fixture whose GUARD_NAMES entry has no row is red naming the guard; the same fixture with the row bound is green). VERIFY: keel gate guard control-map-reconciled . green at the landing tree and the pair test passes."; }
        action dcDispatchOwedListResolvesInTheTree;
        verification dcDispatchOwedListResolvesInTheTreeDoD : Test { :>> id = "08ac66b4-12f4-4a82-9a32-c217c5e815a4"; :>> method = VerificationMethod::test; :>> procedureText = "RESOLVES issue663. FOUND 2026-09-20 (sprint 754 retro; sprints 741 and 753): the recorder dispatch's Records owed list is typed by the primary from the sprint file, and twice it named the DoD record by the Test's name (<action>DoD) where record result --task takes the action's name; the recorder's first attempt was refused by the write API, the retry landed, and at sprint 741 the retry was filed as REFUSED (issue602). Nothing checks that each --gate and --task the dispatch names resolves in the tree before the recorder is spawned. DONE MEANS: the delegated-ceremony skill gains a small check (references/check_owed.py, run by the primary before dispatch and named in the SKILL.md dispatch procedure) that takes the sprint file and the owed list - one --gate or --task key per line - and refuses a key that is not a declared verification (for --gate) or a declared action (for --task) anywhere under .tracking, naming the key and, when the key ends in DoD and the action of that name exists, saying so; the recorder brief's Records owed line is written from the check's output. Known-positive, chosen before the tree is read: a list naming --task dcTouchedSetDescendsTheWorkspaceDoD against the current tree is refused naming the key and the action dcTouchedSetDescendsTheWorkspace. Known-negative: sprint 754's eight keys (six gates, --task storyRecorderReportAccountsForEveryTreeWrite, --task dcRecorderReportAccountsForEveryTreeWrite) pass."; }
        action dcReceiptQuotesOnlyTheRunItDescribes;
        verification dcReceiptQuotesOnlyTheRunItDescribesDoD : Test { :>> id = "17f0a883-f403-49d4-bb6f-ebb9a095f855"; :>> method = VerificationMethod::test; :>> procedureText = "RESOLVES issue664. FOUND 2026-09-20, sprint 754: the verifier receipt rendered by scripts/verify_receipt.py (D0533) said test result line: keel suite --touched: pass - 925 passed in 776s while .keel/metrics/touched-receipt.toml for the same ladder said passed = 918, seconds = 726. verify_receipt.py:303 reads .keel/metrics/verify-touched.out - the file the test-verify skill's launch line redirects the ladder's stdout into - with no freshness check, and that file was dated 01:39, sprint 753's ladder, while verify-launch.epoch was 02:16: the verifier launched without the redirect and the renderer quoted the previous run's line as this run's. The recorder then copied the stale line into storyRecorderReportAccountsForEveryTreeWriteDoDR1's evidence. The LADDER and TOUCHED lines are epoch-checked (verify_receipt.py:292, :351) and were fresh; the two lines read from verify-touched.out (first red line, test result line) are not. DONE MEANS: verify_receipt.py reads verify-touched.out only when its mtime is at or after verify-launch.epoch; a stale or absent file renders first red line and test result line as STALE naming the file's date against the epoch, adds one DISCREPANCIES line, and exits 3, so the recorder's rule (2) records what the receipt shows; the touched summary is composed from touched-receipt.toml's own passed, failed and seconds fields beside the quoted line, so a fresh line and the receipt agree or the disagreement is visible; the renderer's self-test carries the pair. Known-positive, chosen before the tree is read: a metrics directory whose verify-touched.out is dated before verify-launch.epoch renders STALE on both lines and a DISCREPANCIES line and exits 3. Known-negative: the same directory with verify-touched.out dated after the epoch renders the line as today and exits 0."; }
        action dcLadderReceiptIsKeptPerLaunch;
        verification dcLadderReceiptIsKeptPerLaunchDoD : Test { :>> id = "4dcf98dd-856f-4852-a3d0-9488027776ee"; :>> method = VerificationMethod::test; :>> procedureText = "RESOLVES issue665. FOUND 2026-09-20, sprint 755: check_receipt.py's fixtures for the sprint 743 dispute (issue603) had to be reconstructed from the transcript's keel verify --wait table and the sprint's recorded counts, because .keel/metrics/verify-receipt.toml and touched-receipt.toml are each one file rewritten by every launch - the ladder that ended at=1789725917 was overwritten by the one at=1789728746 fifty minutes later, and keel land rewrote touched-receipt.toml again after the sprint 754 ladder. The touched LOG is already kept per launch (touched-<epoch>.log, named in the receipt's log field); the two receipts a later check reads are not. DONE MEANS: keel verify writes its ladder receipt to .keel/metrics/verify-<at>.toml beside the live verify-receipt.toml when the ladder ends, and keel suite --touched writes touched-<at>.toml beside the live touched-receipt.toml, both with the content of the live file at that moment; the live files and keel verify --wait are unchanged; the receipt renderer's LADDER and TOUCHED RECEIPT lines carry the per-launch file names so a dispute names the file that survives; .gitignore covers them as it covers the live files. Known-positive, chosen before the tree is read: a ladder that ended leaves verify-<at>.toml whose at, outcome and [[rung]] rows equal the live verify-receipt.toml's. Known-negative: a second launch after it leaves the first per-launch file byte-identical - its at unchanged - while the live file now carries the second at."; }
        action dcRendererHoldsItsAuxiliarySourcesToTheLadder;
        verification dcRendererHoldsItsAuxiliarySourcesToTheLadderDoD : Test { :>> id = "5d8c6632-62e6-4622-9d2e-2385cb93f52c"; :>> method = VerificationMethod::test; :>> procedureText = "Resolves issue666. scripts/verify_receipt.py reads the ladder's launch as at - seconds from verify-receipt.toml and holds its two auxiliary sources to it: a verify-touched.out whose mtime is before that launch is rendered STALE with no test result line quoted and a DISCREPANCIES line naming both times; a verify-launch.epoch later than the launch or more than the ladder's own duration before it is a DISCREPANCIES line rather than 'ok'; a test result line whose passed/failed differ from touched-receipt.toml's is a DISCREPANCIES line. check_receipt.py refuses a receipt whose test result line quotes passed/failed other than touched-receipt.toml's, or quotes one over a STALE stdout. Both scripts' --probe carry the sprint 755 receipt (positive: 917/1 quoted over passed=918 failed=0) and a fresh render (negative) as their D0388 pair; the test-verify table row for test result line names the discrepancy."; }
        action dcGuardTierHasOneHome;
        verification dcGuardTierHasOneHomeDoD : Test { :>> id = "1267a2a9-ce8e-4573-99c1-13055e5239e9"; :>> method = VerificationMethod::test; :>> procedureText = "Resolves issue668. A guard's tier - hard-blocking or warning-only - is stated in three homes held together by nothing: the section of .engine/docs/guards.md its row sits under, WARNING_ONLY_GUARDS in members/keel-serve/src/serve_verbs.rs (nine names, the list keel version subtracts from GUARD_NAMES to report the split), and the code (whether the guard's function ever pushes a violation). On 2026-09-20 the catalogue's Warning-only section held five rows absent from the list (decision-scaffolding, release-recorded, enrollment-binding, control-event-coverage, stpa-currency), so keel version counted them hard-blocking while the catalogue called them warning-only; four of the five build their GuardReport with violations: Vec::new() (enforcement.rs stpa_currency and control_event_coverage, release.rs release_recorded, identity.rs enrollment_binding) and one, decision-scaffolding, pushes violations (decisions.rs, D0303 option C) while its row calls it WARNING-tier. DONE MEANS: the tier has ONE home in code - each dispatch Arm in the FAMILY tables carries its tier - and both other homes are computed from or held to it: keel version's split is counted from the arms (WARNING_ONLY_GUARDS retired, the version_guard_split test rewritten over the arms), and a unit test holds every catalogue row's section equal to its arm's tier, so a row under the wrong heading is a red test naming the guard, the heading and the arm. A guard whose arm says warning-only and whose function pushes a violation is caught at the run: the runner downgrades nothing silently - it fails the guard run naming the guard, the arm and the violation, so the arm must be corrected or the tier promoted through a recorded review (D0180). Known-positive, chosen before the tree is read: a fixture catalogue with a hard-tier guard's row under Warning-only fails the test naming guard, heading and arm; a warning-only arm whose function returns a violation fails the run naming both. Known-negative: the catalogue and the arms as reconciled pass; keel version reports the same total as GUARD_NAMES.len(), with the hard and warning counts summing to it."; }
        action dcOwedRecordsAreComputedFromTheSprint;
        verification dcOwedRecordsAreComputedFromTheSprintDoD : Test { :>> id = "63df9ef1-dc63-4d9b-8fd3-26d1e1214181"; :>> method = VerificationMethod::test; :>> procedureText = "Resolves issue669. The records a sprint's recorder owes are computed from the sprint file, never typed by the primary: every Test the delivery file declares (the phase gates and the story DoD) and the DoD of each backlog task the story #Delivers, each owed exactly one TestResult at closeOut. On 2026-09-20 sprint 756's dispatch typed 7 and omitted the story DoD; check_report.py --owed 7 passed the seven that landed, and sprints 753-755 each carry the result 756 lacked until a second dispatch. DONE MEANS: a keel lens (keel show owed <sprint file>, or the sprint's row in an existing lens) lists the owed records as the record verbs that write them - record gate-result --file F --gate G, record result --file F --task T - with the count, reading the sprint file and the backlog; check_report.py gains --sprint FILE, under which it derives the owed count from that same set (the lens's JSON, or the same read) and refuses a report whose WROTE plus REFUSED lines number fewer, naming each owed Test no line accounts for - --owed N stays as the explicit override and a dispatch naming both with different counts is refused; the delegated-ceremony skill's recorder brief and the dispatch step quote the lens's output as the Records owed list and pass --sprint, so the primary types no list and no count. Known-positive, chosen before the tree is read: sprint 756's first recorder report (recorder-report-756.txt, seven WROTE lines) under --sprint sprint756_guardsCatalogueNamesTheFamily.sysml is refused naming storyGuardsCatalogueNamesTheFamilyDoD; a fixture sprint file with six gates, a story DoD and one delivered task lists eight owed. Known-negative: the same report plus the second recorder's WROTE line passes under --sprint; sprint 755's report passes under --sprint sprint755_verifierReceiptIsCheckedAgainstTheLadder.sysml. The check's --probe carries both."; }
    }
// =================================================================
    // NextWork — the post-bootstrap queue (2026-06-11 handoff). EngineBuild
    // (above) is COMPLETE 34/34; this is what comes next. Sources: the first
    // real dogfood (CLAUDE.md §4), deferred critique findings (M3/M6/U2/U5-U7,
    // UC3/UC9/UC10), parked pre-critique findings, and the runtime roadmap.
    // Resume: `python .engine/tools/query.py orient` surfaces the ready set.
    // =================================================================
    action def NextWork {
        // ---- TRACKING-MECHANISM FIXES (top priority, human direction 2026-08-13) ----
        // "if we're inaccurately identifying work, we need to be fixing our tracking
        // mechanisms so that these mistakes aren't missed." Each item below is a CONTROL for
        // a miss that actually happened in sprint 247 — vigilance already failed, so per D0047
        // each becomes an automated check rather than a reminder.
        // FIELD-REPORTED regression, top priority: D0133 blocked a downstream project entirely.
        action dcEngineMarkerBuiltins;
        verification dcEngineMarkerBuiltinsDoD : Test { :>> id = "0d770001-0814-5701-9b3e-000000270001"; :>> method = VerificationMethod::test; :>> procedureText = "Resolves issue089 (Critical, discoveredInField). D0133 shipped `marker-vocabulary` as a HARD guard in the BINARY whose passing condition was `metadata def` lines in the PROJECT's schema. include_dir! embeds .engine at BUILD time, so upgrading the binary never updates an existing project's on-disk .engine/schema/ — reproduced: pre-D0133 schema + v0.2.0 binary = 566 violations, exit 1, every commit blocked, including on the engine's own shipped files. Worse, the only remedy was editing FROZEN schema/core, so the guard forced downstream projects into a frozen-schema sign-off just to keep committing. FIX: (a) ENGINE_MARKERS builtin set in the binary — the engine's own algebra (#Verify, #DerivedFrom, #CharteredBy, #Resolves, #Measures, #Informs, #JustifiedBy, #Dispositions, #Covers, #DependsOn, #Supersede, #OrderingOnly, #ProspectiveChange, #SafetyChange, #Capability, #ProcessDefect, #View) is always valid with NO project declaration, because it is the engine's contract and the binary owns it; (b) project-declared markers scanned from ANY .engine or .tracking file, so a project declares its own vocabulary without touching frozen core; (c) guard stays HARD — with (a) and (b) the only remaining failures are genuine typos; (d) the violation message no longer directs people to edit frozen schema. VERIFY: the reproduced downstream state goes 566 -> 0; `#DerivdFrom` still hard-fails with exit 1 IN that state; this repo stays at 0; unit test asserts every engine marker resolves with an EMPTY project declaration set and that a misspelling does not; clippy + cargo test + keel validate + guard green. Ship as a patch release immediately — a downstream team is blocked."; }
        part dcEngineMarkerBuiltinsDoDR1 : TestResult { :>> id = "cb9d8483-fdd2-46e9-a346-b19754e74a60"; :>> outcome = VerdictKind::pass; :>> judgedAgainst = "c4464de"; :>> judgedAt = "2026-08-14"; :>> judgedBy = "claudeOpus5"; }
        action dcVerificationTrace;
        verification dcVerificationTraceDoD : Test { :>> id = "0d630001-0813-4301-9b3e-000000130001"; :>> method = VerificationMethod::test; :>> procedureText = "MISS IT CATCHES (sprint247, real): six SystemRequirements were IMPLEMENTED and CI-verified, yet tier-satisfaction correctly reported them UNVERIFIED because the passing DoD Tests #Verify-link the BACKLOG ACTION, not the requirement — so `work done` and `requirement verified` are disconnected, and the burndown was then mis-narrated to the human as if 34% meant functional verification. DO: a computed check (prefer a DECLARED rule per D0105/D0107) that flags a DONE work item whose charter/satisfy chain reaches a SystemRequirement carrying NO #Verify edge — i.e. work claims to deliver a requirement while no verification is linked to the requirement itself. Report the pair (done action -> untraced SR) so the fix is obvious. WARNING-level first (D0102 promote-once-low-noise), surfaced in orient's burndown; it is honest-state completeness, so it must NOT hard-block (D0098). ALSO: make `keel tier-satisfaction` state WHAT verified each SR (method mix), because in this repo the 24 'verified' SRs are verified overwhelmingly by method=critique, not by functional tests — a reader cannot currently tell. VERIFY: the six sprint247 SRs are flagged before their #Verify edges are authored and clean afterwards; a done action whose SR is critique-only is distinguishable from one verified by test; the check is non-blocking; clippy + cargo test + keel validate + guard green."; }
        part dcVerificationTraceDoDR1 : TestResult { :>> id = "275ef412-ffc8-4db9-9b6b-12029c8996dc"; :>> outcome = VerdictKind::pass; :>> judgedAgainst = "af2edd1"; :>> judgedAt = "2026-08-13"; :>> judgedBy = "claudeOpus5"; }
        action dcAttestationSubstance;
        verification dcAttestationSubstanceDoD : Test { :>> id = "0d630002-0813-4302-9b3e-000000130002"; :>> method = VerificationMethod::test; :>> procedureText = "MISS IT CATCHES (2026-08-13, real, found in the human's own record): d0129Accept was recorded with `procedureText = \"\"` — an EMPTY attestation — and passed EVERY guard, including acceptance-events and confirmation-authenticity. For method=confirmation the attestation text IS the evidence (D0016), so a contentless acceptance is an unsupported claim that looks complete. DO: extend the acceptance/confirmation checks so a method=confirmation Test carrying a passing TestResult must have a SUBSTANTIVE procedureText — non-empty and beyond a trivial token (a bare name, 'ok', 'approved') — mirroring the decision-rationale guard's substantive-field test (D0103). Forward-only: grandfather existing thin attestations to WARNING so historical records are not retro-failed (the issue068 lesson), hard-fail only NEW ones. VERIFY: an empty and a single-token procedureText both fail for a new acceptance; a substantive one passes; the existing corpus produces warnings, not violations; clippy + cargo test + keel validate + guard green."; }
        part dcAttestationSubstanceDoDR1 : TestResult { :>> id = "7cc82f28-6494-4fee-9456-7e0122a91867"; :>> outcome = VerdictKind::pass; :>> judgedAgainst = "336cec5"; :>> judgedAt = "2026-08-13"; :>> judgedBy = "claudeOpus5"; }
        action dcPriorityInversion;
        verification dcPriorityInversionDoD : Test { :>> id = "0d630003-0813-4303-9b3e-000000130003"; :>> method = VerificationMethod::test; :>> procedureText = "MISS IT CATCHES (sprint247, real): D0052 makes backlog DECLARATION ORDER the priority and requires the AI to auto-follow the ranked frontier. Sprint 247 appended 15 new actions at the file tail, so `keelArchViews` (issue069, Low) ranked #1 purely because an earlier session appended it to the end of the completed EngineBuild block, while `dcStaleKernelInstanceGate` (issue081, HIGH — an enforced commit gate being routinely bypassed) ranked 14th; the AI then narrated 'highest-leverage' items in PROSE instead of reordering the file. Both severity and order are recorded facts, so the inversion is COMPUTABLE. DO: a computed check flagging a ready item whose #Resolves-linked Issue is severity >= High while a lower-severity (or issue-free) ready item outranks it. WARNING-level + surfaced in orient (priority is judgment, so never a hard block) — it makes the inversion visible instead of trusting curation. VERIFY: the pre-reorder backlog state reproduces a flag for dcStaleKernelInstanceGate vs keelArchViews; the reordered state is clean; an issue-free ready item above a High one is flagged; clippy + cargo test + keel validate + guard green."; }
        part dcPriorityInversionDoDR1 : TestResult { :>> id = "4d42dcf1-624d-45a0-90f9-c8ff9581d82c"; :>> outcome = VerdictKind::pass; :>> judgedAgainst = "f1e4469"; :>> judgedAt = "2026-08-13"; :>> judgedBy = "claudeOpus5"; }
        action dcRetroToBacklog;
        verification dcRetroToBacklogDoD : Test { :>> id = "0d630004-0813-4304-9b3e-000000130004"; :>> method = VerificationMethod::test; :>> procedureText = "MISS IT CATCHES (sprint247, real): the retro gate named three AVOIDABLE-ISSUEs, but only two became tracked backlog items — the two shell-hygiene lessons went to CLAUDE.md prose plus AI memory, i.e. OUTSIDE the model, which is precisely the prose-shadow-truth D0018 forbids and leaves them unprioritized and unqueryable. The human's direction: 'the sprint retro should identify any potential recurring or serious issues and put it properly prioritized backlog items to resolve them.' DO: a computed check that a sprint retro gate whose procedureText names an avoidable issue (AVOIDABLE-ISSUE / LESSON markers) co-records a tracked Issue or backlog action in the same commit — the same git-diff-aware, heuristic, WARNING-first shape as the doc-sync guard (D0113), promotable once low-noise. ALSO update .engine/processes/agile-workflow.sysml's retro step + the sprint-retro skill so the obligation is DEFINED, not just checked (D0059: a check without a process is unowned). VERIFY: a retro naming an avoidable issue with no co-committed Issue/action warns; one with a co-committed tracked item is clean; the sprint247 retro reproduces a warning for its two prose-only lessons; clippy + cargo test + keel validate + guard green."; }
        part dcRetroToBacklogDoDR1 : TestResult { :>> id = "3b7b9485-2e43-4a3e-ae33-485d698bd4cf"; :>> outcome = VerdictKind::pass; :>> judgedAgainst = "ee2512d"; :>> judgedAt = "2026-08-13"; :>> judgedBy = "claudeOpus5"; }
        // ---- then, in priority order: the accepted D0129/D0128 programme ----
        action dcStaleKernelInstanceGate;
        verification dcStaleKernelInstanceGateDoD : Test { :>> id = "0d5e0010-0812-4e10-9b3e-00000000e010"; :>> method = VerificationMethod::test; :>> procedureText = "Resolves issue081. The pre-commit hook runs the KERNEL validator .engine/tools/validate/validate_instances.py, which validates each .engine instance file IN ISOLATION — so any cross-file reference fails to resolve. It therefore ALREADY FAILS 11 COMMITTED decision files (0114, 0116-0125) on `Couldn't resolve reference to Element 'dNNNN'` / 'nViewerX' / Type 'DerivedFrom', which means the only way those commits landed was SKIP_VALIDATE=1 — the gate is routinely bypassed, which is the exact dynamic issue076 warns about (a gate contributors learn to bypass is defeated everywhere at once). Meanwhile `keel check-engine` (D0112 phase 2, kernel-free) resolves references ACROSS files and passes clean, so the Rust path is both correct and stricter here. NOTE the kernel ALSO cannot resolve `DerivedFrom` — independent confirmation of issue077 (the marker is undeclared). DO: retire validate_instances.py from the blocking hook path in favour of `keel check-engine` (the D0112 phase-3 direction), or fix it to register all instance packages before validating (the same two-pass shape as issue079). Either way the gate must stop failing files that are correct. This changes what gates a commit, so it is a CHANGE (§3a) needing a Decision + acceptance. VERIFY: no committed .engine file fails the enforced instance gate; the gate needs no routine bypass; check-engine still catches a genuine unresolved reference (negative test); clippy + cargo test + keel validate + guard green."; }
        part dcStaleKernelInstanceGateDoDR1 : TestResult { :>> id = "fd99d88a-3dca-49cc-ae73-66bf9ae7cc5a"; :>> outcome = VerdictKind::pass; :>> judgedAgainst = "d6f9da5"; :>> judgedAt = "2026-08-13"; :>> judgedBy = "claudeOpus5"; }
        // The DELIVERED slice of in-loop governance (D0130). Declared separately because
        // keelInLoopGates ALSO requires measurement + Tier-1/Tier-2 hooks (D0128) which are NOT
        // done — marking that item complete would be the very mis-identification issue082 tracks.
        action dcResponseContractGate;
        verification dcResponseContractGateDoD : Test { :>> id = "0d650001-0813-4501-9b3e-000000150001"; :>> method = VerificationMethod::demo; :>> procedureText = "srDc response contract + Tier-3 in-loop gate (D0130). WHY: the response contract (parse-first routing, no prose state, no fabricated attestation) lived ONLY in CLAUDE.md — injected as ordinary user-turn context, the weakest layer that can hold a rule — with nothing checking it; sprint 247/248 recorded four bypasses of ALREADY-ACCEPTED decisions (issue082-085). DELIVERED: (a) `.claude/output-styles/keel.md` + `outputStyle: keel` — the contract now sits in the SYSTEM PROMPT, and is the CANONICAL home (CLAUDE.md references it, never restates it, so the two cannot drift into dual truth per D0105); (b) the `Stop` hook wired in `.claude/settings.json` running .engine/tools/stop_gate.py, which executes keel validate + guard at the TURN boundary and BLOCKS the turn while the model is dishonest, feeding violations back — harness-executed, so it ENFORCES rather than instructs; (c) two real defects fixed in the prototype while productionising it: it hardcoded a Windows-only `keel.exe` and so would have silently NO-OPPED on every other contributor's machine (the issue076 class inside the governance control itself), and it decoded subprocess output with the platform default so its feedback arrived as mojibake. VERIFIED by pipe-test: green tree -> exit 0, no output (stop allowed); injected parse error -> {\"decision\":\"block\"} with the violations in `reason`; stop_hook_active=true + still red -> allows the stop with a loud systemMessage (loop-safe, never traps the agent); missing binary -> visible systemMessage, never a silent no-op; encoding verified at byte level (em-dash U+2014 present, no U+FFFD, no cp1252 mojibake) rather than by reading the console. settings.json validated: JSON parses, outputStyle=keel, Stop command+timeout resolve, and the pre-existing 10 permission denies + 2 UserPromptSubmit hooks are PRESERVED. NOT DELIVERED (stays on keelInLoopGates): the D0128 measurement, Tier-2 PostToolUse per-edit gating, Tier-1 PreToolUse deny. NOT VERIFIABLE BY THE AI: that the Stop hook actually fires — the harness must reload settings (`/hooks` or restart), and a hook cannot be proven to fire within the turn that wires it."; }
        part dcResponseContractGateDoDR1 : TestResult { :>> id = "2a1ec890-7051-456b-a644-0c3fbae37797"; :>> outcome = VerdictKind::pass; :>> judgedAgainst = "7740eb0"; :>> judgedAt = "2026-08-13"; :>> judgedBy = "claudeOpus5"; }
        action dcDeclaredMarkers;
        verification dcDeclaredMarkersDoD : Test { :>> id = "0d5e0006-0812-4e06-9b3e-00000000e006"; :>> method = VerificationMethod::test; :>> procedureText = "srDcDeclaredMarkerVocabulary (D0129). Of the markers guards consume, ONLY #View is declared: #Capability (15 files), #DerivedFrom (22), #Covers (6), #Dispositions (10), #ProcessDefect (5) appear nowhere as `metadata def`, yet #DerivedFrom is load-bearing for the hard-blocking requirement-rootedness guard (guards.rs:386-398, view.rs:3085-3116). Markers are not type-checked, so a MISSPELLED marker validates clean and silently removes that item from the guard's view — a blind guard reports PASS, and the exposure scales with contributor count. DO: declare the missing markers in .engine/schema/core/relationships.sysml and make validation REJECT an undeclared/misspelled marker. NOTE schema/core is FROZEN: this needs explicit human sign-off before the schema edit. VERIFY: all guard-consumed markers are declared; a deliberately misspelled marker FAILS validation (today it passes); requirement-rootedness still sees every #Capability item it saw before (no regression in scanned counts); clippy + cargo test + validate + guard + check-engine green."; }
        part dcDeclaredMarkersDoDR1 : TestResult { :>> id = "44c4be6d-8cee-42c7-925e-1e77a62c99c0"; :>> outcome = VerdictKind::pass; :>> judgedAgainst = "56d7e21"; :>> judgedAt = "2026-08-13"; :>> judgedBy = "claudeOpus5"; }
        action keelInLoopGates;
        verification keelInLoopGatesDoD : Test { :>> id = "06cd07d2-bff7-4e41-9f61-4a3c342b8d1b"; :>> method = VerificationMethod::demo; :>> procedureText = "Productionise the in-loop governance gate (nAiGovernanceInLoop, D0128): promote the Stop-hook prototype (.engine/tools/stop_gate.py) into the shipped engine + project settings after measuring it; add Tier-2 (PostToolUse per-edit via a fast keel gate --changed) + Tier-1 (PreToolUse deny of clear prose-as-truth) as warranted; block clear violations, warn the rest (no thrash)."; }
        part keelInLoopGatesDoDR1 : TestResult { :>> id = "8fa0775e-ccae-4430-8cf6-5d5022821475"; :>> outcome = VerdictKind::pass; :>> judgedAgainst = "bb52d2a"; :>> judgedAt = "2026-08-14"; :>> judgedBy = "claudeOpus5"; }
        action dcRuleAbsenceNotViolation;
        verification dcRuleAbsenceNotViolationDoD : Test { :>> id = "0d7a0001-0814-5a01-9b3e-0000002a0001"; :>> method = VerificationMethod::test; :>> procedureText = "Resolves issue090 — the SECOND instance of D0136's class, found by deliberately hunting for more after issue089 rather than assuming it was isolated. Six HARD guards are rule-sourced (charter, issues, requirement-rootedness, decision-rationale, acceptance-events, confirmation-authenticity) and a MISSING rule made rule_violations return Err, which each guard reported as a VIOLATION. Reproduced on a fresh `keel init` project with `.engine/rules/` removed: SIX hard failures, exit 1, every commit blocked, with messages naming internal rule names (acceptanceEventRule, charterRule, ...) that mean nothing to a downstream project. Any project whose .engine/rules/ is absent, older, or authored fresh per D0093 would hit this. FIX: `view::rule_violations_opt` returns Ok(None) for an ABSENT rule; each guard maps that to a WARNING ('this control is NOT ADOPTED by this project') plus a pass — never silent, so deleting a rule to dodge a gate stays visible — while a MALFORMED rule still fails via Err. A project that never adopted a control has not violated it. VERIFY (all measured): fresh project minus .engine/rules -> 6 failures become ALL PASS exit 0 with 6 visible NOT-ADOPTED warnings; fresh project WITH rules still passes; this repo unaffected; NEGATIVE TEST — an injected untriaged Issue with issuesTriagedRule present still hard-fails with exit 1, so the protection is intact. clippy + cargo test + keel validate + guard green."; }
        part dcRuleAbsenceNotViolationDoDR1 : TestResult { :>> id = "30728921-a0c6-488f-9937-e333971af015"; :>> outcome = VerdictKind::pass; :>> judgedAgainst = "b98f526"; :>> judgedAt = "2026-08-14"; :>> judgedBy = "claudeOpus5"; }
        action dcVersionIdentification;
        verification dcVersionIdentificationDoD : Test { :>> id = "0d7e0001-0814-5e01-9b3e-0000002e0001"; :>> method = VerificationMethod::test; :>> procedureText = "Resolves issue091. Three versioned releases (v0.2.0/0.2.1/0.2.2) shipped with NO version identification in the artifact: `--version`, `-V` and `version` all printed usage. A guard's behaviour is a property of the BINARY, so 'which binary are you running' is the first diagnostic step for every blocked-downstream report (issue089, issue090) — and it was answerable by neither the reporter nor the maintainer, leaving a project still on the blocked version INDISTINGUISHABLE from one that had upgraded. DO: `keel version` (also --version / -V / --json) reporting the release version, the BUILD COMMIT baked by a new keel-cli/build.rs, and the guard inventory computed from GUARD_NAMES rather than restated. The commit is required because the version string alone cannot separate the published artifact from a stale local build claiming the same number; it degrades honestly (`unknown` off-git, `+dirty` from a modified tree) rather than guessing, and is checkable against the recorded Release facts in baselines.sysml. VERIFY (all measured at b006f10): all four invocation forms print version + commit + guard split, exit 0; `--json` emits the same as machine-readable; it answers from OUTSIDE a keel project (a caller establishing which binary they hold may be standing anywhere), so it resolves before any root resolution; `+dirty` correctly flagged a modified tree; a unit test asserts WARNING_ONLY_GUARDS is a strict subset of GUARD_NAMES, since a stray name would make the reported hard-blocking count overstate enforcement — the same defect class as the version gap itself, a number a reader trusts that nothing checks. clippy clean; 157 tests; validate + all 23 guards + check-engine green."; }
        part dcVersionIdentificationDoDR1 : TestResult { :>> id = "0d7e0002-0814-5e02-9b3e-0000002e0002"; :>> outcome = VerdictKind::pass; :>> judgedAgainst = "b006f10"; :>> judgedAt = "2026-08-14"; :>> judgedBy = "claudeOpus5"; }
        action dcHookConfigIntegrity;
        verification dcHookConfigIntegrityDoD : Test { :>> id = "0d800001-0814-6001-9b3e-000000300001"; :>> method = VerificationMethod::test; :>> procedureText = "Resolves issue093, reported by the human ('why are the stop hooks breaking?'). D0134 deleted .engine/tools/stop_gate.py when the in-loop gates moved into the binary, and .claude/settings.json got the replacement — but .claude/settings.local.json ALSO declared a Stop hook pointing at the deleted script, and Claude Code MERGES hooks across settings files, so both fired and the stale one failed on EVERY turn end for a full sitting. It survived because settings.local.json is GITIGNORED (.gitignore:70): invisible to git status, to every diff, and to the doc-sync grep, which sweeps the tracked surface. FIX: remove the stale hook, and add the `hook-config-integrity` guard checking that every hook `command` in .claude/settings*.json naming a repo-relative script actually exists. WARNING-level on purpose — the config is machine-local and partly gitignored, so CI cannot see it and one contributor's personal hook must never block another's commit; a warning still fires on every `keel guard`, including inside the Stop hook, making a sibling hook's breakage self-reporting. VERIFY (all measured): the real failure reproduced (`can't open file ... stop_gate.py`) before the fix; guard clean at 3 scanned after removal; NEGATIVE TEST — restoring the exact stale settings.local.json produces the warning naming the missing script, and removing it returns to clean; absolute paths and .exe references are deliberately not flagged (an unbuilt binary is a legitimate transient state the hook commands already probe for); a malformed settings JSON is reported, since every hook it declares is silently inert. `keel version` reports 24 guards (18 hard, 6 warning-only), computed from GUARD_NAMES. Doc-sync: guards.md catalogue + count, CLAUDE.md §5. clippy clean; 157 tests; validate + all 24 guards + check-engine green."; }
        part dcHookConfigIntegrityDoDR1 : TestResult { :>> id = "0d800002-0814-6002-9b3e-000000300002"; :>> outcome = VerdictKind::pass; :>> judgedAgainst = "97530bf"; :>> judgedAt = "2026-08-14"; :>> judgedBy = "claudeOpus5"; }
        action dcSupersededNotReady;
        verification dcSupersededNotReadyDoD : Test { :>> id = "0d80003f-0814-603f-9b3e-00000030003f"; :>> method = VerificationMethod::test; :>> procedureText = "Resolves issue100. `ready` was computed from successions and done-state only; `#Supersede` was consumed in view/guards/serve/write but referenced NOWHERE in orient.rs or indexer.rs, so a supersede edge had no effect on the frontier. Since the frontier is auto-followed (D0052), two items D0140 had just forbidden — whose execution would have silently deleted 493 edges — remained scheduled for the next session. FIX: `view::superseded_names` returns `#Supersede` edge targets; `ready` excludes them, conservative on error so a model-read failure cannot silently restore everything to ready. VERIFY (measured): ready 27 -> 25 with both superseded items gone; `outstanding` unchanged at 27, because a retired item is NOT done and reporting it as done would be a lie; a non-superseded ready item is unaffected; clippy clean; 161 tests; validate + all 25 guards + check-engine green."; }
        part dcSupersededNotReadyDoDR1 : TestResult { :>> id = "0d800040-0814-6040-9b3e-000000300040"; :>> outcome = VerdictKind::pass; :>> judgedAgainst = "e338eae"; :>> judgedAt = "2026-08-14"; :>> judgedBy = "claudeOpus5"; }
        // Human-raised 2026-08-14, mid-pass: "while building, we'll need a migration tool to get
        // projects leveraging keel up-to-date." Ranked with the conversion cohort, not after it — a
        // migration path retrofitted once ten conversions have landed cannot reconstruct what each one
        // changed, and every conversion in this pass widens the gap for downstream projects.
        action dcSchemaSweepResidue;
        verification dcSchemaSweepResidueDoD : Test { :>> id = "0d80014b-0814-614b-9b3e-00000030014b"; :>> method = VerificationMethod::inspect; :>> procedureText = "Resolves issue108. D0142's leanness sweep deleted `Risk`, `Mitigation` and `DesignElement` and left four pieces of residue behind: `.engine/schema/core/risk.sysml` is hollow (its header and doc string still describe the deleted types; its only content is `enum def RiskStatus`, which nothing references); `RiskLevel` in `element.sysml` is orphaned the same way, its only consumers having been `Risk`'s three level attributes; `architecture.sysml`'s header comment still lists `DesignElement`; and `sysmlv2-syntax-notes.md` still lists `EngineRisk` among the packages to import. DO: delete `risk.sysml` and `RiskLevel`, and correct both docs. VERIFY: no `EngineRisk`, `RiskStatus`, `RiskLevel` or `DesignElement` reference survives outside `.engine/decisions/` (where the historical record must stay intact); the dead-schema rule reports nothing new; validate + all guards + check-engine green; the kernel is run on the change, since the last two schema deletions in this pass each broke a reference the Rust validator accepted. NOTE: this is a `schema/core` change and therefore a CHANGE route needing its own Decision and sign-off, which is why it was NOT bundled into sprint 281. Deleting `risk.sysml` from the engine does not strand a downstream project: `keel migrate` never deletes a file it does not ship, so the project keeps its copy and the resync reports it as unrecognised."; }
        part dcSchemaSweepResidueDoDR1 : TestResult { :>> id = "0d80019b-0814-619b-9b3e-00000030019b"; :>> outcome = VerdictKind::pass; :>> judgedAgainst = "b745cc2"; :>> judgedAt = "2026-08-15"; :>> judgedBy = "claudeOpus5"; }
        action dcProjectMigrationTool;
        verification dcProjectMigrationToolDoD : Test { :>> id = "0d80003e-0814-603e-9b3e-00000030003e"; :>> method = VerificationMethod::demo; :>> procedureText = "A downstream project's `.engine/` is a COPY taken at `keel init` time, so it diverges from the binary the moment the engine changes — and this pass changes the schema repeatedly. That divergence has already blocked two projects entirely (issue089: 566 violations, every commit blocked; issue090: six hard guards failing), and both were fixed by making the BINARY tolerant, which works for a vocabulary set and does not work for a schema conversion: no amount of binary tolerance retypes a project's `part def Process` into an `action def`. DO: `keel migrate [--dry-run]` — a versioned, ordered set of migration steps, each idempotent, that brings a project's on-disk `.engine/` and `.tracking/` from any prior vintage to the current one. NON-NEGOTIABLES, from D0067 and from what the field reports already cost: a DRY RUN that reconciles control totals per step and refuses on any mismatch; idempotent steps, so a re-run is a no-op rather than a double-application; NEVER fabricate history — a migration rewrites authored facts only where the transform is mechanical and total, and reports anything it cannot transform rather than guessing; it must REFUSE on a dirty tree, since a half-migrated working copy mixed with uncommitted human edits is unrecoverable; and it must state the vintage it detected and the steps it will run BEFORE running them. Each conversion sprint in this pass CONTRIBUTES its migration step as part of its own DoD — the step is written by whoever makes the change, when they still know what it changed, not reconstructed later. VERIFY: a project pinned at the pre-pass engine vintage migrates to current and then passes its OWN full gate (validate + all guards + check-engine) — the only test that matters, since that is the state a downstream user is in; a second run changes nothing; a dry run on that project reports every step and reconciles totals; a project already current is a no-op reporting so; a dirty tree is REFUSED with the reason; a project that authored its own `.engine` content fresh per D0093 is migrated without clobbering that content; the vintage is DETECTED rather than asked for. Also verify the failure path honestly: a step that cannot transform an item reports the item and exits non-zero rather than leaving a partial migration silently."; }
        part dcProjectMigrationToolDoDR1 : TestResult { :>> id = "0d80014a-0814-614a-9b3e-00000030014a"; :>> outcome = VerdictKind::pass; :>> judgedAgainst = "8b785ff"; :>> judgedAt = "2026-08-14"; :>> judgedBy = "claudeOpus5"; }
        // PANEL OUTCOME (2026-08-14): the three critics reached unanimity that D0139(E) must not be
        // executed, by three independent routes. These four items carry that outcome. dcVerificationLink
        // ranks first because an accepted Decision currently instructs a migration that would silently
        // destroy the verification spine.
        action dcVerificationLinkDecision;
        verification dcVerificationLinkDecisionDoD : Test { :>> id = "0d80003a-0814-603a-9b3e-00000030003a"; :>> method = VerificationMethod::inspect; :>> procedureText = "Resolves issue098. `objective r;` DECLARES a nested member and carries NO edge — kernel-verified with a deliberately undeclared name, against controls that correctly fail. So the shape recorded since June as 'the only valid verification shape' is not a relationship, and D0139(E) instructs a migration onto it that would leave every verification link silently non-existent while both toolchains report clean. DO: author the superseding Decision (D0140, PROPOSED — supersedes D0139 clauses E and G only, leaving the base-first rule intact) recording that #Verify and #DerivedFrom are RETAINED with kernel-verified justification: for #Verify, 309 of 456 edges target `part Decision`, which cannot be a requirement objective, and the only reference-bearing forms (`objective :>> r` / `:> r`) require a requirement-typed target; for #DerivedFrom, all 37 edges are cross-metaclass and D0055 already records that cross-metaclass `:>` is impossible. This is the base-first rule WORKING, not failing — D0139(B) demands a recorded justification that no base construct suffices, and these two now have one. VERIFY: D0140 supersedes only E and G, with the #ProspectiveChange marker and the D0070 keystone co-commit; relationships.sysml:7-12 is corrected so it no longer presents the objective shape as an edge; sysmlv2-syntax-notes.md gains the declares-vs-references distinction with the discriminator method; the two migration backlog items are superseded rather than left instructing a harmful change; validate + guard + check-engine green."; }
        part dcVerificationLinkDecisionDoDR1 : TestResult { :>> id = "0d800041-0814-6041-9b3e-000000300041"; :>> outcome = VerdictKind::pass; :>> judgedAgainst = "e338eae"; :>> judgedAt = "2026-08-14"; :>> judgedBy = "claudeOpus5"; }
        action dcMarkerCensusView;
        verification dcMarkerCensusViewDoD : Test { :>> id = "0d80003b-0814-603b-9b3e-00000030003b"; :>> method = VerificationMethod::test; :>> procedureText = "Resolves issue099. I recorded #Verify at 613, #DerivedFrom at 91 and #DependsOn at 91 in an accepted Decision; the real EDGE counts are 456, 37 and 42. The inflation came from grepping the marker name, which also matches the 129 prose mentions inside `description`/`procedureText` strings — a corpus that contains prose about itself inflates its own census, and it grows as more is written about the migration. guards.rs:936 and relationships.sysml:66 already carried the correct 456. DO: compute the census instead of grepping it — a marker-census view or `keel` subcommand counting EDGE STATEMENTS per marker (and reporting prose mentions separately, since the gap between the two is the tell), so every future migration quotes one place. Correct the recorded totals in D0139/issue095 via the superseding Decision rather than editing an accepted record. VERIFY: the census reports 456/37/42 for the three markers and agrees with guards.rs; prose mentions are reported separately and are non-zero; a marker with zero edges is reported as zero rather than omitted (#SafetyChange is exactly this case); the figure is reachable from a declared view; clippy + cargo test + validate + guard green."; }
        part dcMarkerCensusViewDoDR1 : TestResult { :>> id = "0d8000b8-0814-60b8-9b3e-0000003000b8"; :>> outcome = VerdictKind::pass; :>> judgedAgainst = "62d0c3e"; :>> judgedAt = "2026-08-14"; :>> judgedBy = "claudeOpus5"; }
        action dcPanelCritiqueRecords;
        verification dcPanelCritiqueRecordsDoD : Test { :>> id = "0d80003c-0814-603c-9b3e-00000030003c"; :>> method = VerificationMethod::demo; :>> procedureText = "The human commissioned a three-critic panel (antagonist / protagonist / dispassionate technical-correctness) and asked for iterative deliberation to unanimity. The panel RAN and reached unanimity on the central question, but its findings currently exist only in conversation history — which D0018 forbids as a home for anything a successor needs. DO: author the panel's findings as engine-native critique facts (method=critique, `#Verify`-linked to the critiqued element, with `lens` and `severity`), each attributed to a registered critic actor. NOTE THE INTEGRITY CONSTRAINT and resolve it explicitly rather than by convenience: `critic-independence` requires judgedBy != the element's author, and these critics were separate agent CONTEXTS but the same model as the author. Registering them as actors is honest only if the actor record states exactly that — a distinct critique context, not a distinct model — so a later reader cannot mistake them for independent reviewers. Decide and record whether that satisfies critic-independence or merely passes it; if it merely passes it, say so in the record. VERIFY: every finding the panel carried into a tracked item has a critique record citing its evidence; the critic actors' records state what they actually were; critic-independence passes for a stated reason rather than by accident; no finding is recorded as unanimous that was not; validate + guard green."; }
        part dcPanelCritiqueRecordsDoDR1 : TestResult { :>> id = "0d80015b-0814-615b-9b3e-00000030015b"; :>> outcome = VerdictKind::pass; :>> judgedAgainst = "55f181e"; :>> judgedAt = "2026-08-14"; :>> judgedBy = "claudeOpus5"; }
        action dcSchemaLeannessSweep;
        verification dcSchemaLeannessSweepDoD : Test { :>> id = "0d80003d-0814-603d-9b3e-00000030003d"; :>> method = VerificationMethod::demo; :>> procedureText = "The panel's non-marker findings, which all three critics considered more consequential than the marker count and which the human's phase-1 ask (lean, fact-laden items) targets directly. Each needs its own measurement before action; this item is the CHARTER for that sweep, not a licence to change schema. (a) TWO live `Release` types — `part def` (work.sysml:63, 0 instances, carries a dead `membershipRule`) and `occurrence def` (baseline.sysml:18, 11 instances) — and deploy.sysml:6 imports the 0-instance one, threading it through four action signatures. (b) ~15 never-instantiated types persist in frozen schema/core while rules.sysml:63-66 records the OPPOSITE policy for `OrderingRule` ('removed as dead schema … re-add it THEN, with an instance'). (c) `Process`/`ProcessStep` are `part def` with behaviour in strings and sequence in an Integer, and process.sysml:5-6 records that the fields were renamed BECAUSE `action` and `output` are reserved — the model reached for `action def` and was deflected by a name clash; `.engine/workflows/business.sysml:9-21` already uses the base form correctly, so the repo holds two mechanisms for an ordered procedure. (d) `port def InterfacePort` sits in schema/core while ACCEPTED D0100 states 'No ports/interfaces enter schema/core', and `#View item def ICD` advertises a computation over data that has never existed. (e) provenance (`createdBy`/`owner`/`judgedBy`) is String while `part def Actor` exists and single-valued `ref` is portable in BOTH toolchains — ~3000 attestation records a viewer cannot navigate. (f) stale claims inside frozen schema: `query.py` cited 8 times though retired at D0074, rules.sysml:5 says 14 guards against the real 25, rules.sysml:22 classes `verifyEdge` as a native typed edge when it is a marker. (g) the 17th marker `metadata def View` lives in workflows/_meta.sysml:15, not relationships.sysml, so any audit from the declared home undercounts. VERIFY: each lettered finding is independently re-measured before any change; every schema/core edit carries the §2.5 sign-off; deletions leave no tombstones; each is a separate sprint with its own gate rather than one sweeping commit."; }
        part dcSchemaLeannessSweepDoDR1 : TestResult { :>> id = "0d8000d8-0814-60d8-9b3e-0000003000d8"; :>> outcome = VerdictKind::pass; :>> judgedAgainst = "5f149bd"; :>> judgedAt = "2026-08-14"; :>> judgedBy = "claudeOpus5"; }
        // The single highest-leverage base-first fix: this parser gap is WHY markers looked unavoidable.
        action dcParserSequenceSupport;
        verification dcParserSequenceSupportDoD : Test { :>> id = "0d800039-0814-6039-9b3e-000000300039"; :>> method = VerificationMethod::test; :>> procedureText = "keel-parser REJECTS `:>> feature = (a, b, c)` — multi-valued feature assignment — with 'unexpected character (`('`)', while the KERNEL ACCEPTS it (`_spike_base_algebra.py` case ref_multi_sequence, 2026-08-14). So this is OUR defect, not a SysML v2 limitation, and it is the reason a multi-valued `ref` feature was never a candidate: sysmlv2-syntax-notes.md recorded the form as kernel-confirmed without noting the rust rejection, so `ref` features looked unusable for anything with more than one target and metadata markers on dependencies looked like the only way to express a one-to-many edge. WHY THIS RANKS HIGH: `ref` features are BASE SysML v2 structure and need no marker at all, so fixing the parser converts a whole class of custom edges into base constructs — it unblocks dcProcessAssertsConstraints and reduces what the two migrations have to invent. DO: support the sequence form in keel-parser (lexer + feature-value parse), preserve the values as an ordered list, and make `keel check`/`validate` accept what the kernel accepts here. VERIFY: the exact case the kernel accepts now passes `keel check`; a single value still works unchanged; an empty sequence `()` and a trailing comma are handled deliberately (accept or reject, but decided and tested, not incidental); the indexer resolves EVERY element of a multi-valued ref, proven by a reference that would be reported unresolved if any element were dropped; no existing file changes meaning; clippy + cargo test + validate + guard + check-engine green."; }
        part dcParserSequenceSupportDoDR1 : TestResult { :>> id = "0d800051-0814-6051-9b3e-000000300051"; :>> outcome = VerdictKind::pass; :>> judgedAgainst = "e733115"; :>> judgedAt = "2026-08-14"; :>> judgedBy = "claudeOpus5"; }
        // The safety property that lifting the `(` restriction incidentally removed (issue101).
        action dcSequenceMultiplicityGuard;
        verification dcSequenceMultiplicityGuardDoD : Test { :>> id = "0d800052-0814-6052-9b3e-000000300052"; :>> method = VerificationMethod::test; :>> procedureText = "Resolves issue101. Enabling the sequence form removed a property the old lex error had provided accidentally: a sequence could not be written into a SINGLE-valued attribute either. Measured on a fresh keel init project — `createdBy = (\"you\", \"ghostActorNotRegistered\")` on a `String[0..1]` attribute passes validate AND passes `guard actors`, so an unregistered actor enters silently, defeating the control that makes provenance non-forgeable (D0037/D0129). The PRECISE rule needs multiplicity metadata that neither the AST nor the registry carries, and there is no attribute-declaration validation at all — a larger gap that must close before `ref` features can carry edges. INTERIM: warning-level `sequence-multiplicity` guard reporting EVERY sequence, which is useful rather than a placeholder because the model has ZERO today, so any hit is new. AST-based, not a text scan — grepping `= (` matched 4 hits that were ALL prose discussing the form (issue099 in miniature). Warning-level because it cannot be exact and a hard guard firing on a legitimate multi-valued ref would train its author to disable it (issue081). VERIFY (measured): real model reports 0 scanned / 0 warnings; the hazard project reports the createdBy sequence with file:line; `keel version` reports 26 guards (19 hard, 7 warning-only) computed from GUARD_NAMES; clippy clean; 161 tests; validate + all 26 guards + check-engine green."; }
        part dcSequenceMultiplicityGuardDoDR1 : TestResult { :>> id = "0d800053-0814-6053-9b3e-000000300053"; :>> outcome = VerdictKind::pass; :>> judgedAgainst = "e733115"; :>> judgedAt = "2026-08-14"; :>> judgedBy = "claudeOpus5"; }
        // Makes skipping VISIBLE. The reader itself (capturing these constructs) is dcParserReadBase.
        action dcParserSkipVisibility;
        verification dcParserSkipVisibilityDoD : Test { :>> id = "0d800063-0814-6063-9b3e-000000300063"; :>> method = VerificationMethod::test; :>> procedureText = "Resolves issue102. keel-parser skips what it cannot read, silently. MEASURED with the undeclared-name discriminator against validate: control `part x : NoSuchTypeAnywhere` yields 1 semantic diagnostic, while `ref e : NoSuchTypeAnywhere`, `port p : NoSuchPortDef`, `assert constraint c : NoSuchConstraint` and `connect ghostA.p to ghostB.p` ALL validate clean — invisible, not merely unresolved. Every construct D0139 converts toward is in that set. DELIVERED: `Package.skipped` (line + lead token) recorded inside `skip_item`, the single choke point all skips pass through; warning-level `parser-coverage` guard reporting counts grouped by lead token, head-ranked with the tail collapsed. VERIFY (measured): reports 165 skipped statements across 473 files, of which 52 are `:>` specialization clauses (so the type hierarchy is unread — and `:>` is D0140's derivation form), 57 are `use case` usages, 18 are `flow`; the report stays legible (the first version printed 57 singleton element names and buried the findings); warning-level, since 165 is the honest current state and hard-failing would block every commit (issue081); 27 guards (19 hard, 8 warning-only); clippy clean; 161 tests; validate + guard + check-engine green."; }
        part dcParserSkipVisibilityDoDR1 : TestResult { :>> id = "0d800064-0814-6064-9b3e-000000300064"; :>> outcome = VerdictKind::pass; :>> judgedAgainst = "4e9fd63"; :>> judgedAt = "2026-08-14"; :>> judgedBy = "claudeOpus5"; }
        // Construct 1 of 6 for dcParserReadBase, delivered. The umbrella item stays outstanding until
        // the remaining five land — partial progress is tracked by sub-items, never by prose.
        action dcParserReadSpecialize;
        verification dcParserReadSpecializeDoD : Test { :>> id = "0d800075-0814-6075-9b3e-000000300075"; :>> method = VerificationMethod::test; :>> procedureText = "Reads the `:>` SPECIALIZATION clause — construct 1 of dcParserReadBase, ranked first because `:>` is the derivation form D0140 names as the only valid replacement for #DerivedFrom, and 52 clauses were unread so the type hierarchy was invisible. DELIVERED: `TypeDef.specializes`, a `parse_specializes` helper called at all six def sites via an extracted `type_def_tail` (the extraction removes duplication this change itself introduced), and registry resolution of the target through the existing `check_type_ref`. ALSO FIXED, exposed by the positive control (issue103): the package's own declarations were absent from the validation scope, so a same-package supertype reported unresolved. VERIFY, both polarities measured: undeclared supertype FAILS with a semantic diagnostic; declared same-package supertype PASSES; no clause PASSES; real repo + .engine stay clean; `parser-coverage` no longer reports ColonGt. ALSO corrected the metric itself — capturing `:>` moved 52 records from ColonGt to LBrace WITHOUT changing the total, revealing that it counted skip_item INVOCATIONS rather than unread statements; `{` and `;` leads are no longer recorded, so the figure fell 165 -> 74 and now means what its name says. clippy clean; 161 tests; validate + all 27 guards + check-engine green."; }
        part dcParserReadSpecializeDoDR1 : TestResult { :>> id = "0d800076-0814-6076-9b3e-000000300076"; :>> outcome = VerdictKind::pass; :>> judgedAgainst = "662a94b"; :>> judgedAt = "2026-08-14"; :>> judgedBy = "claudeOpus5"; }
        action dcParserReadUseCaseAndFlow;
        verification dcParserReadUseCaseAndFlowDoD : Test { :>> id = "0d800086-0814-6086-9b3e-000000300086"; :>> method = VerificationMethod::test; :>> procedureText = "Constructs 2 and 6 of dcParserReadBase, taken together because both are statements PRESENT and unread in the model today (the remaining three — ref, assert/require constraint, ports/connect — have zero instances and are about future capability, not current blindness). USE CASE USAGES: `use case name : Type { ... }` was skipped entirely, only `use case def` handled, so all 56 carried unchecked type references and unchecked enum literals and were absent from every view. Added `Item::UseCase(UseCaseUsage)` as its own variant rather than reusing Part — a use case is not a structural part, following the precedent Verification already sets — with registry type + attribute checking and Model ingestion. FLOW: all 18 `flow from A.x to B.y` sit inside `action def` workflow bodies; added `FlowEdge`, `ActionDef.flows`, a `parse_flow` matched on the IDENTIFIER `flow` (promoting it to a keyword would change the word's behaviour everywhere for one construct's benefit), and dotted-path capture keeping the full endpoint text. VERIFY (measured): use case usage with an UNDECLARED type FAILS, with a declared type PASSES, with attributes PASSES; `attribute def` still parses (a regression check — an earlier patch of mine landed in the attribute arm by mistake and was reverted); `parser-coverage` falls 74 -> 18 -> 0, dropping by exactly 56 then exactly 18, so every statement in the model is now read; real repo + .engine clean; clippy clean; 161 tests; all 27 guards green."; }
        part dcParserReadUseCaseAndFlowDoDR1 : TestResult { :>> id = "0d800087-0814-6087-9b3e-000000300087"; :>> outcome = VerdictKind::pass; :>> judgedAgainst = "dedc999"; :>> judgedAt = "2026-08-14"; :>> judgedBy = "claudeOpus5"; }
        action dcModelIngestWorkflows;
        verification dcModelIngestWorkflowsDoD : Test { :>> id = "0d800088-0814-6088-9b3e-000000300088"; :>> method = VerificationMethod::demo; :>> procedureText = "Resolves issue104. `Model::build` ingests `.tracking` + `.engine/{decisions,processes,views,skills,rules}` and NOT `.engine/workflows`, so the six workflow definitions — the one place this repo models behaviour in base SysML v2 rather than in strings — contribute nothing to any view, trace, diagram or guard, and the newly-parsed flow edges have nowhere to land. DO: add the directory, then reconcile the blast radius, which is the actual work: workflow actions become items subject to charter, requirement-rootedness and critique-coverage, so guard output must be compared item by item BEFORE and AFTER and every new violation individually judged as either a real gap to fix or a scope error to exclude. Do NOT resolve it by grandfathering wholesale — that would hide precisely the traceability gaps the ingestion exists to reveal. VERIFY: flow edges appear in `keel diagram` and in a declared view; workflow actions are reachable by `keel trace`; the before/after guard diff is enumerated and each delta has a recorded verdict; no guard newly fails without that verdict; clippy + cargo test + validate + guard + check-engine green."; }
        part dcModelIngestWorkflowsDoDR1 : TestResult { :>> id = "0d80012b-0814-612b-9b3e-00000030012b"; :>> outcome = VerdictKind::pass; :>> judgedAgainst = "f7f7296"; :>> judgedAt = "2026-08-14"; :>> judgedBy = "claudeOpus5"; }
        action dcParserReadBase;
        verification dcParserReadBaseDoD : Test { :>> id = "0d800065-0814-6065-9b3e-000000300065"; :>> method = VerificationMethod::demo; :>> procedureText = "The reader itself, and the true gate on every conversion in the base-first pass. issue102 made skipping VISIBLE; this makes the constructs READABLE. Visibility means a conversion fails loudly instead of silently; it does not mean the conversion is possible. DO: capture, with type/target resolution so an undeclared target FAILS, in priority order by what the pass needs — (1) `:>` specialization clauses on type definitions, 52 present and unread today, which is D0140's derivation form and therefore needed before any #DerivedFrom work; (2) `ref` members with their type, the base construct that replaces markers for one-to-many edges and the reason dcParserSequenceSupport was built; (3) `assert constraint` / `require constraint`, needed by D0139(D) for process-to-controls; (4) `port` members, `interface def` and `connect`, the up/downstream surface the human asked for in phase 1; (5) `use case` USAGES, 57 skipped entirely today; (6) `flow`, 18 present. VERIFY, per construct and not in aggregate: the undeclared-name discriminator FAILS for each newly-read construct, matching the `part x : NoSuchType` control — that is the only proof the content is actually captured rather than merely tolerated; `parser-coverage` drops by exactly the number of statements each step claims to have absorbed, reconciled per step; every existing view, guard and orient output is UNCHANGED for constructs already read, proven by capturing output before and after; the kernel still accepts every file (the rust parser must not diverge from conformance in the permissive direction again — issue097); clippy + cargo test + validate + all guards + check-engine green at every step."; }
        part dcParserReadBaseDoDR1 : TestResult { :>> id = "0d800098-0814-6098-9b3e-000000300098"; :>> outcome = VerdictKind::pass; :>> judgedAgainst = "3df2ef0"; :>> judgedAt = "2026-08-14"; :>> judgedBy = "claudeOpus5"; }
        action dcAssumptionsView;
        verification dcAssumptionsViewDoD : Test { :>> id = "0d8000ea-0814-60ea-9b3e-0000003000ea"; :>> method = VerificationMethod::test; :>> procedureText = "Resolves issue105. I recorded the deleted `Assumption` type as 'the one genuine loss' of D0142's sweep; the human corrected it — an accepted unverified requirement with downstream non-verification dependencies IS an assumption, so the class is COMPUTABLE and §1.1 makes it a view rather than an authored type. The behaviour the type was justified by (downstream suspicion) already exists per relationships.sysml:29-31 and has worked the whole time the type sat unused. DELIVERED: `keel assumptions` — unverified AND depended-upon, scoped to Need/SystemRequirement/SubsystemRequirement/Decision, with verification edges excluded from the dependency test since a Test DISCHARGES an assumption rather than resting on it. VERIFIED both directions: reports 73; a verified Need (n01AtomicItems) is correctly absent; every listed item has >=1 dependent; the three types represented are Decision, Need and SystemRequirement. clippy + cargo test + validate + all 28 guards + check-engine green."; }
        part dcAssumptionsViewDoDR1 : TestResult { :>> id = "0d8000eb-0814-60eb-9b3e-0000003000eb"; :>> outcome = VerdictKind::pass; :>> judgedAgainst = "79e7b06"; :>> judgedAt = "2026-08-14"; :>> judgedBy = "claudeOpus5"; }
        // EXCLUDED from D0142's sweep on purpose: both are migrations over INSTANCE data needing
        // D0067's gated expand/migrate/contract, and bundling either into a dead-code deletion would
        // make the deletion unreviewable and the migration unverifiable.
        action dcProcessAsBehaviour;
        verification dcProcessAsBehaviourDoD : Test { :>> id = "0d8000d9-0814-60d9-9b3e-0000003000d9"; :>> method = VerificationMethod::demo; :>> procedureText = "Panel finding (c), all three critics agreeing and the correctness adjudicator rating it High confidence. `Process` and `ProcessStep` are `part def` with behaviour in strings and sequence in an Integer: `actionText`, `producedArtifact`, `triggerCondition`, `order : Integer`. process.sysml:5-6 records WHY — `action` and `output` are RESERVED WORDS, so the author renamed the fields instead of reaching for the constructs those words belong to. The repo already models behaviour correctly elsewhere: .engine/workflows/business.sysml:9-21 is a clean `action def` with typed in/out parameters, `first..then` successions and `flow`. So there are TWO mechanisms for an ordered procedure and 93 ProcessStep instances use the weaker one. DO: retype to `action def` with `first..then` for order and typed `out` parameters plus `flow` for producedArtifact; `owner` stays an attribute. This is what makes a process connectable upstream/downstream by typed item flow rather than by prose — the phase-1 ask. VERIFY: `perform action` and `first..then` are kernel-confirmed valid; every existing process step survives with its order preserved, reconciled by control total; `keel activation` still reads the same 6 units and 14 asserts (D0141 attached asserts to these very parts, so the retype must preserve them); parser-coverage stays 0; a fresh keel init project passes its own gate; D0067 gated phases, green at each."; }
        part dcProcessAsBehaviourDoDR1 : TestResult { :>> id = "0d80010a-0814-610a-9b3e-00000030010a"; :>> outcome = VerdictKind::pass; :>> judgedAgainst = "06e9154"; :>> judgedAt = "2026-08-14"; :>> judgedBy = "claudeOpus5"; }
        action dcActorTraceView;
        verification dcActorTraceViewDoD : Test { :>> id = "0d80010b-0814-610b-9b3e-00000030010b"; :>> method = VerificationMethod::test; :>> procedureText = "Resolves issue106, and SUPERSEDES the shape of dcProvenanceAsRefs. The panel's complaint — provenance strings are unnavigable — is correct, but `ref createdBy : Actor` is unavailable: `.engine` carries 137 provenance values and would have to import `ProjectActors`, a per-project INSTANCE package, inverting the D0093 engine/instance boundary. `.engine` ships downstream via `keel init`, where this project's actors do not exist. DELIVERED INSTEAD: `keel actor-trace <actor>` computing authored / judged / owned from the strings — the same derive-do-not-author move the human reasoned to for Assumption. VERIFIED: wweatherholtz 643/233/0; claudeSonnet46 9/91/13. RESIDUAL, recorded not glossed: a raw viewer still sees strings, so navigability lives in keel rather than SysON; that is the price of not inverting the boundary."; }
        part dcActorTraceViewDoDR1 : TestResult { :>> id = "0d80010c-0814-610c-9b3e-00000030010c"; :>> outcome = VerdictKind::pass; :>> judgedAgainst = "a14d564"; :>> judgedAt = "2026-08-14"; :>> judgedBy = "claudeOpus5"; }
        // FRONTIER TOP: every base-first choice downstream depends on knowing which oracle answered.
        // Without this, the whole D0139 programme can be measured against the wrong tool — as it already
        // was once (issue097).
        action dcKernelConformanceGate;
        verification dcKernelConformanceGateDoD : Test { :>> id = "0d800038-0814-6038-9b3e-000000300038"; :>> method = VerificationMethod::demo; :>> procedureText = "Resolves issue097. `keel validate`/`check` are the ENGINE's semantic authority (D0048) — reference resolution, identity, provenance — and are NOT a SysML v2 conformance check, but nothing says so, so 'validate is green' reads as 'this is valid SysML v2'. It is not: the kernel rejects `verify X by Y` at package level while the rust parser accepts it, which is how a wrong migration target reached an accepted Decision (D0139 clause E). The human's goal is a model usable in a standard viewer (SysON), so conformance is the property that actually matters and it is currently unmeasured. DO: (a) a CONFORMANCE LANE running the kernel over the model and reporting non-conformance, as an INDICATOR or warning-level control — NOT hard-blocking, because D0132 demoted the per-file instance validator for failing correct files and forcing an all-or-nothing bypass (issue081), and repeating that would disable every other layer again; (b) a standing rule that any NEW base construct is kernel-validated before adoption, never on the rust parser alone; (c) state the oracle boundary plainly wherever `validate` is documented as the authority, so the next author cannot make my mistake. VERIFY: the lane runs kernel-side and reports a count plus the specific non-conforming constructs; a deliberately non-conformant construct that the rust parser accepts IS reported; the lane never blocks a commit; `keel validate` docs and CLAUDE.md §5 state what the rust authority does and does not check; the D0139 construct table is re-measured kernel-side and corrected; clippy + cargo test + validate + guard green."; }
        part dcKernelConformanceGateDoDR1 : TestResult { :>> id = "0d80015c-0814-615c-9b3e-00000030015c"; :>> outcome = VerdictKind::pass; :>> judgedAgainst = "0bd61be"; :>> judgedAt = "2026-08-14"; :>> judgedBy = "claudeOpus5"; }
        // Ranked ABOVE the remaining D0139 items because those are BLOCKED on an acceptance the human
        // could not see — fixing the surface unblocks the queue behind it.
        action dcPendingAcceptanceSurface;
        verification dcPendingAcceptanceSurfaceDoD : Test { :>> id = "0d800037-0814-6037-9b3e-000000300037"; :>> method = VerificationMethod::demo; :>> procedureText = "Resolves issue096. The console's Decisions surface is wired to the `keel decisions` governance scorecard, which filters to accepted (132 rows) and omits the 2 `proposed` decisions; the declared view `keel view decisions` shows all 139. Acceptance is the single human gate in an otherwise autonomous loop, so an oversight surface that renders everything EXCEPT what needs action inverts its purpose — and it fails silently, since nothing states that decisions are waiting. DO: surface PENDING ACCEPTANCES as a first-class computed count plus names in BOTH `keel orient` and the console, sourced from the declared view rather than the scorecard; leave the scorecard's accepted-only scope alone, since scoring citations and critique coverage is meaningful only for a committed decision. VERIFY: with 2 proposed decisions present, orient reports exactly those 2 by name and the console shows them; with none, both report zero rather than omitting the field (absence must be stated, not implied — the D0138 lesson); the scorecard's 132-row output is unchanged; a decision moving proposed -> accepted leaves the pending list without any other edit; clippy + cargo test + validate + guard green."; }
        part dcPendingAcceptanceSurfaceDoDR1 : TestResult { :>> id = "0d80017b-0814-617b-9b3e-00000030017b"; :>> outcome = VerdictKind::pass; :>> judgedAgainst = "4ba45c8"; :>> judgedAt = "2026-08-15"; :>> judgedBy = "claudeOpus5"; }
        // Human-raised direction, 2026-08-14: "minimum custom connections, maximum using real
        // relationships defined in base sysmlv2. anytime we use something custom, it should be strongly
        // critiqued." Ranked top — it governs how everything else is authored. All four AWAIT
        // acceptance of D0139 (frozen edge algebra + a 613-use migration).
        action dcBaseFirstVocabulary;
        verification dcBaseFirstVocabularyDoD : Test { :>> id = "0d800033-0814-6033-9b3e-000000300033"; :>> method = VerificationMethod::demo; :>> procedureText = "Resolves issue095 — the RULE and its control, not the migrations. Base SysML v2 relationships that parse clean in the rust authority are going unused while custom markers cover the same ground: `verify` 0 uses vs #Verify 613, `refine` 0 vs #DerivedFrom 91, plus `assert constraint`/`require constraint`/`perform action`/`include use case` all unused. The recorded justification for markers covered only genuinely NEW edge kinds (no `dependency def`) and was never re-tested. DO: (a) state the BASE-FIRST rule — a custom `metadata def` is a last resort, permitted only with a recorded justification naming the base constructs considered and why each fails; (b) an automated control (not a reminder, D0047) requiring every PROJECT-declared marker to carry that justification as a `doc` clause, warning-level for the engine's own 17 grandfathered markers (forward-only, issue068) and applying to anything new; (c) correct sysmlv2-syntax-notes.md to list the verified base relationships FIRST so the next author reaches for them before inventing an edge. VERIFY: a new undocumented `metadata def` is flagged; one carrying a justification passes; the engine's existing markers are grandfathered to warnings and the list cannot be extended; the notes name every base construct actually verified against `keel check`; clippy + cargo test + validate + guard green."; }
        part dcBaseFirstVocabularyDoDR1 : TestResult { :>> id = "0d8000c8-0814-60c8-9b3e-0000003000c8"; :>> outcome = VerdictKind::pass; :>> judgedAgainst = "bf8e1b0"; :>> judgedAt = "2026-08-14"; :>> judgedBy = "claudeOpus5"; }
        action dcProcessAssertsConstraints;
        verification dcProcessAssertsConstraintsDoD : Test { :>> id = "0d800034-0814-6034-9b3e-000000300034"; :>> method = VerificationMethod::demo; :>> procedureText = "The first application of dcBaseFirstVocabulary, and a correction of my own sprint-265 choice. Process-to-controls went into `.engine/contracts/process-units.toml` when `assert constraint` was available and is semantically exact: CLAUDE.md §1.7 already holds that the guards ARE the constraint layer, so a Process asserting the constraints it enforces is base SysML v2 stating precisely what is meant, and it makes the mapping TRACEABLE — a TOML table cannot be reached by `keel trace`, `view`, or any declared viewpoint. DO: model each guard as a `constraint` in the engine schema and each Process as asserting the ones it brings; read the activation unit mapping from the MODEL rather than from process-units.toml; retire that file with no tombstone. NOTE THE PARSER CONSTRAINT: the multi-valued `:>> x = (a, b, c)` form is rejected by the rust authority (issue095), so either several single-valued asserts are used or keel-parser gains sequence support first — decide with measurement, not preference. VERIFY: the unit mapping is computed from the model and `keel activation` output is unchanged; the mapping is reachable by a declared view; process-units.toml is gone; a fresh `keel init` project still passes with and without a manifest; the D0138 core-vs-process-bound split is preserved exactly, including the adversarial `active = []` case still hard-failing on a duplicate id; clippy + cargo test + validate + guard green."; }
        part dcProcessAssertsConstraintsDoDR1 : TestResult { :>> id = "0d8000a8-0814-60a8-9b3e-0000003000a8"; :>> outcome = VerdictKind::pass; :>> judgedAgainst = "5b1aea4"; :>> judgedAt = "2026-08-14"; :>> judgedBy = "claudeOpus5"; }
        action dcMigrateVerifyToBase;
        verification dcMigrateVerifyToBaseDoD : Test { :>> id = "0d800035-0814-6035-9b3e-000000300035"; :>> method = VerificationMethod::demo; :>> procedureText = "Migrate `#Verify dependency from T to R` to the base relationship `verify R by T` — 613 occurrences, so this follows the D0067 migration process strictly: gated expand/migrate/contract, a COMMITTED transform, a dry run reconciling control totals, green at every step, and never fabricated history. TARGET CORRECTED 2026-08-14 (issue097): `verify X by Y` is NOT a valid target — the KERNEL rejects it and every other standalone verify form, its own message being 'A requirement verification must be in the objective of a verification case'. My earlier claim that it parsed clean measured the PERMISSIVE rust parser, not conformance. The ONLY kernel-valid verification shape is structural: `verification def V { subject s : P; objective r; }`. That makes this a REMODELLING, not a relationship swap — every Test becomes a verification case with a subject and an objective — so re-estimate before starting and treat the old estimate as void. WHY IT MATTERS BEYOND tidiness: `#Verify` is load-bearing for the hard `requirement-rootedness` and warning-level `verification-trace` guards, and a MISSPELLED marker validates clean while silently removing an item from a guard's view (the D0133 argument). A base relationship is parsed as a relationship, so the misspelling class disappears rather than being guarded against. VERIFY: control totals reconcile exactly — the count of #Verify edges before equals the count of `verify` relationships after, per file; every guard consuming verification sees the same element set before and after, proven by capturing guard output on both sides; `keel coverage`/`tier-satisfaction`/`assured` are unchanged; the expand phase leaves both forms readable so no commit is ever red; clippy + cargo test + validate + guard green at every phase."; }
        action dcMigrateDerivedFromToBase;
        verification dcMigrateDerivedFromToBaseDoD : Test { :>> id = "0d800036-0814-6036-9b3e-000000300036"; :>> method = VerificationMethod::demo; :>> procedureText = "Migrate `#DerivedFrom` (91 occurrences) to base derivation. TARGET RESOLVED 2026-08-14 by kernel measurement (issue097), so the 'decide first' step is DONE: `refine X by Y`, `trace X to Y` and `derive X from Y` are ALL REJECTED by the kernel — they are v1 keywords absent from the v2 pilot grammar — while `requirement b :> a` (specialization) is accepted. The target is therefore `:>`, exactly as sysmlv2-syntax-notes.md:16 recorded all along. My earlier report that `refine` parsed clean measured the PERMISSIVE rust parser and was wrong. #DerivedFrom is consumed by the HARD requirement-rootedness guard, so the same misspelling-blindness argument as dcMigrateVerifyToBase applies. D0067 migration process, control totals reconciled. VERIFY: the chosen target is justified in a recorded Decision against the alternative; requirement-rootedness sees the identical #Capability element set before and after; rootedness and tier-satisfaction outputs unchanged; green at every phase."; }
        // BLOCKED ON A CONTENT GATE, not on effort: editing a process definition is a CHANGE (§3a) and
        // cannot be self-accepted. Ranked above dcActivationManifest because it resolves a High-severity
        // process defect (issue092) and is a one-step edit once accepted.
        action dcReleaseAssetVerification;
        verification dcReleaseAssetVerificationDoD : Test { :>> id = "0d7f0011-0814-5f11-9b3e-0000002f0011"; :>> method = VerificationMethod::inspect; :>> procedureText = "Resolves issue092. `relTagPublish` (.engine/processes/deploy.sysml, D0135) requires verifying that release assets are ATTACHED, which is satisfied by a green workflow plus a non-empty asset list — so v0.2.0, v0.2.1 and v0.2.2 were each verified by confirming files existed at a URL, and no published asset was ever downloaded or executed. Claims about those releases' behaviour were measured on a LOCAL build and attributed to the published one. DO: extend `relTagPublish` to require obtaining a published asset and confirming it self-identifies as the tagged version and commit (`keel version`, available as of v0.2.3) before a release counts as published. AWAITS HUMAN ACCEPTANCE: this edits a process definition, which is a CHANGE (§3a) and cannot be self-accepted — the item is blocked on that gate, not on effort. VERIFY once accepted: the step names the check and the artifact it produces; the release skill deploying the process performs it; a deliberately mismatched asset (a tag whose published binary reports a different version or commit) is REJECTED rather than recorded as published; the v0.2.3 evidence (asset reports 0.2.3 / b006f10, matching the tag) is what the step would have required; doc-sync across the release surface; validate + guard + check-engine green."; }
        part dcReleaseAssetVerificationDoDR1 : TestResult { :>> id = "0d800012-0814-6012-9b3e-000000300012"; :>> outcome = VerdictKind::pass; :>> judgedAgainst = "95ec70e"; :>> judgedAt = "2026-08-14"; :>> judgedBy = "claudeOpus5"; }
        // The PRINCIPLED answer to what a downstream project adopts (human, 2026-08-14: "the answer
        // should be through defining portable processes, no?"). Supersedes presence-inference.
        action dcActivationManifest;
        verification dcActivationManifestDoD : Test { :>> id = "0d7c0001-0814-5c01-9b3e-0000002c0001"; :>> method = VerificationMethod::demo; :>> procedureText = "Delivers srPortActivationManifest (nProcessPortability, D0128). WHY NOW: issues 089 and 090 were both the same question wearing different clothes — WHAT HAS THIS PROJECT ADOPTED? Both fixes answer it by INFERENCE from file presence (a marker declared somewhere; a rule file existing), which is implicit and accidental: a project cannot state what it adopted, cannot see what it has not, cannot adopt a control while temporarily disabling it, and cannot take a process as a UNIT — and enforcement changes silently when a file moves. DO: a per-project ACTIVATION MANIFEST declaring which processes are active (follow the D0097 `.engine/contracts/critique-policy.toml` precedent — a declared, downstream-overridable policy file, so the pattern already exists); `keel guard` and `orient` enforce and report exactly the active set; a process activates as a UNIT (definition + deploying skill + its declared rules/guards), so activating it turns on its enforcement rather than merely adding a skill (D0059). Absent manifest => everything present is active, so no existing project changes behaviour. This SUBSUMES both patches: 'rule absent -> not adopted' becomes 'that process is not in your active set', which is a DECLARED fact rather than an inference. VERIFY: a fresh `keel init` project passes with and without a manifest; a project that activates a subset has ONLY those controls enforced and the inactive ones REPORTED (never silently dropped); activating a process turns its rules on in one step; deactivating is visible in `keel guard` output; the guard set reported by orient matches the manifest; clippy + cargo test + keel validate + guard green."; }
        part dcActivationManifestDoDR1 : TestResult { :>> id = "0d800023-0814-6023-9b3e-000000300023"; :>> outcome = VerdictKind::pass; :>> judgedAgainst = "da8b8de"; :>> judgedAt = "2026-08-14"; :>> judgedBy = "claudeOpus5"; }
        // Ranked BELOW dcActivationManifest: Medium severity against a p0 direction item, and the
        // friction it removes is mine, not a downstream project's.
        action dcShellAdaptationGate;
        verification dcShellAdaptationGateDoD : Test { :>> id = "0d800022-0814-6022-9b3e-000000300022"; :>> method = VerificationMethod::demo; :>> procedureText = "Resolves issue094. Host/shell adaptation errors recurred THREE times in one sitting (two MSYS paths handed to Windows Python — one of which I briefly reported to the human as a product defect before checking my own path form — and one PowerShell `&` call operator inside a bash command), the class of the closed issue065 and named in CLAUDE.md §6 as the #1 avoidable-friction class. Sprint 263's retro wrongly concluded the class was not automatable because it 'lives in throwaway shell commands, not committed artifacts'; that assumed a control must inspect ARTIFACTS, while D0134's in-loop gates inspect TOOL CALLS, and a shell command is a tool call. DO: a PreToolUse check on Bash commands (`keel hook pre-bash`) detecting (a) an MSYS-style `/c/...`, `/tmp/...` or `/mnt/...` path passed as an argument to a Windows executable, and (b) PowerShell-only syntax inside a bash command — a leading `&` call operator, `$env:`, backtick line continuation — emitting an ADVISORY message naming the concrete fix (`cygpath -w`, or switch to the PowerShell tool). ADVISORY not blocking, deliberately: this check cannot be exact, and a heuristic that blocks every shell command is the issue076/issue081 dynamic where an over-strict gate trains its actor to disable it. VERIFY: each of the three real commands from this sitting is detected and names the right remedy; a correct bash command with a genuine POSIX path is NOT flagged; a Windows path passed to a Windows program is not flagged; the hook is silent on the common case so it costs nothing; absent binary degrades to no-op without erroring (the issue093 lesson); clippy + cargo test + validate + guard green."; }
        part dcShellAdaptationGateDoDR1 : TestResult { :>> id = "0d80018b-0814-618b-9b3e-00000030018b"; :>> outcome = VerdictKind::pass; :>> judgedAgainst = "9e14881"; :>> judgedAt = "2026-08-15"; :>> judgedBy = "claudeOpus5"; }
        action dcEnrollment;
        verification dcEnrollmentDoD : Test { :>> id = "0d5e0009-0812-4e09-9b3e-00000000e009"; :>> method = VerificationMethod::demo; :>> procedureText = "srDcEnrollment (D0129) — deploys .engine/processes/actor-enrollment.sysml. Every remote contributor starts unenrolled, and enrollment is the gate through which attribution, acceptance authority and gate uniformity are all established. Distinct from the existing `introduction` process, which onboards a fresh PROJECT (zero to first value) and never establishes WHO is acting. DO: one sanctioned command that determines the acting identity, obtains kind (human/AI) and role EXPLICITLY, registers the actor if absent without duplicating an entry, writes the machine-local identity binding, verifies the local gate actually executes, and reports readiness or the specific remedy — requiring no other contributor present, and REFUSING rather than enrolling into indeterminate identity or a non-running gate. Supersedes capture_user.py's git-identity-only, Person-only capture. VERIFY: a fresh clone with no engine identity reaches ready in one command; an AI enrolls as kind=ai (never Person); re-enrolling an existing actor re-binds without duplicating; a machine with a broken gate is reported NOT ready with the remedy; indeterminate identity is refused, never defaulted; clippy + cargo test + validate + guard green."; }
        part dcEnrollmentDoDR1 : TestResult { :>> id = "0d8001ab-0814-61ab-9b3e-0000003001ab"; :>> outcome = VerdictKind::pass; :>> judgedAgainst = "1b69544"; :>> judgedAt = "2026-08-15"; :>> judgedBy = "claudeOpus5"; }
        action dcBlockedFrontier;
        verification dcBlockedFrontierDoD : Test { :>> id = "0d8001ac-0814-61ac-9b3e-0000003001ac"; :>> method = VerificationMethod::test; :>> procedureText = "Resolves issue112. The ready frontier ranked `dcWorkClaim` first while it was blocked on a proposed frozen-core Decision (D0147), so the auto-followed frontier pointed the next contributor at work that provably could not be done — a COMPUTED view asserting something untrue, which is the one failure this engine's premise cannot survive. DO: exclude from `ready` any task carrying a `#DependsOn` edge to a Decision whose status is `proposed`, as a predicate DISTINCT from supersession (retired vs waiting), and author the edge for dcWorkClaim. VERIFY: ready drops the blocked item; `outstanding` does NOT drop, because blocked work is not done; the item returns to the frontier with no further edit when the Decision is accepted OR rejected; an accepted Decision blocks nothing; conservative on a model-read error, so a failure cannot silently make everything ready again; clippy + cargo test + validate + guard green."; }
        part dcBlockedFrontierDoDR1 : TestResult { :>> id = "0d8001ad-0814-61ad-9b3e-0000003001ad"; :>> outcome = VerdictKind::pass; :>> judgedAgainst = "21122a8"; :>> judgedAt = "2026-08-15"; :>> judgedBy = "claudeOpus5"; }
        action dcWorkClaim;
        verification dcWorkClaimDoD : Test { :>> id = "0d5e0007-0812-4e07-9b3e-00000000e007"; :>> method = VerificationMethod::demo; :>> procedureText = "srDcWorkClaim + srDcStaleClaimExpiry (D0129). The ready frontier is one global list with no owner or claim (orient.rs:33-45), so several contributors rationally select the same top item and duplication surfaces only at integration. DO: a claim is an AUTHORED fact (claiming actor, item, time, commit-claimed-against) whose liveness is COMPUTED — mutual exclusion comes from the remote accepting exactly one of two concurrent claims (git ref update is a compare-and-swap), not from a lock server; add a claim write path, actor-filtered `whats-next`, and computed stale-claim expiry from git-derived time (D0013) that releases the CLAIM but never the recorded facts. VERIFY: two clones claim the same item concurrently and exactly one wins, the loser re-syncs and selects different work with no human involved; a claim held past expiry is reported stale and its item returns to the frontier; facts recorded under an expired claim remain; orient shows who holds what; clippy + cargo test + validate + guard green."; }
        part dcWorkClaimDoDR1 : TestResult { :>> id = "2073d6ec-e457-491f-9f54-d9bd23a48d12"; :>> outcome = VerdictKind::pass; :>> judgedAgainst = "0c9836f"; :>> judgedAt = "2026-08-15"; :>> judgedBy = "claudeOpus5"; }
        action dcLandLoop;
        verification dcLandLoopDoD : Test { :>> id = "0d5e0008-0812-4e08-9b3e-00000000e008"; :>> method = VerificationMethod::demo; :>> procedureText = "srDcGateOnMergedTree + srDcSyncAwareOrient (D0129). Two contributions that each pass the gate alone can fail together, which is why the gate must run on the tree that will LAND (the not-rocket-science rule, executed client-side — no server needed). Today nothing fetches: post-commit is fire-and-forget (.githooks/post-commit:8-9). DO: `keel sync` (fetch, report divergence, ancestry-preserving integrate, gate-parity check, then orient) and `keel land` (loop: fetch, merge trunk, run the FULL enforced gate on the merged tree, push; retry on rejection with bounded back-off); make orientation report its own divergence from the remote so every computed answer carries the sync state it was computed against. VERIFY: a green-alone/red-together pair is caught BEFORE push; a push race resolves by retry without human action; retries exhaust into an honest failure rather than a force-push; orient reports behind/ahead/diverged counts; clippy + cargo test + validate + guard green."; }
        part dcLandLoopDoDR1 : TestResult { :>> id = "0d8001cc-0814-61cc-9b3e-0000003001cc"; :>> outcome = VerdictKind::pass; :>> judgedAgainst = "fe7f8ea"; :>> judgedAt = "2026-08-15"; :>> judgedBy = "claudeOpus5"; }
        action dcUnresolvedEvidence;
        verification dcUnresolvedEvidenceDoD : Test { :>> id = "0d5e000a-0812-4e0a-9b3e-00000000e00a"; :>> method = VerificationMethod::test; :>> procedureText = "srDcUnresolvedEvidenceClass (D0129). Under partial synchronization — the normal state of a distributed team — a contributor cannot see anchors for evidence another has recorded but not pushed, or pushed but not yet fetched here. Today both collapse into `invalidEvidence`, which orient treats as not-done (orient.rs:38, 494-531), so finished work re-enters the ready frontier and is redone. DO: distinguish 'anchor absent from THIS clone' (unsynchronized) from 'anchor genuinely unresolvable' (invalid), never count the former as work-not-done, surface the distinction in orient, and name what to fetch to resolve it. Honest-state discipline (D0098): unverifiable-from-here is a different fact from unverified. VERIFY: an anchor present remotely but unfetched reports unsynchronized (not invalid) and is NOT counted as outstanding; a genuinely dangling anchor still reports invalid; after fetching, the unsynchronized set empties with no other change; clippy + cargo test + validate + guard green."; }
        part dcUnresolvedEvidenceDoDR1 : TestResult { :>> id = "0d8001dc-0814-61dc-9b3e-0000003001dc"; :>> outcome = VerdictKind::pass; :>> judgedAgainst = "33aa053"; :>> judgedAt = "2026-08-15"; :>> judgedBy = "claudeOpus5"; }
        action dcContentionAdjudication;
        verification dcContentionAdjudicationDoD : Test { :>> id = "0d5e000b-0812-4e0b-9b3e-00000000e00b"; :>> method = VerificationMethod::demo; :>> procedureText = "srDcContentionAdjudication (D0129). D0108 clause 5 already MANDATES that conflicting conclusions across threads be recorded as an Issue for HUMAN adjudication with neither thread silently winning — and there is no command that records an Issue at all (`record decision` exists, `record issue` does not), so the sanctioned path has no implementation, which is the friction that guarantees non-compliance (D0054). DO: add `keel record issue` (parity with `record decision`: auto number + UUID + provenance, scaffolding the #Resolves triage the issues guard requires), plus a computed contention view (two live claims on one item; two open Decisions governing one subject; contradictory recorded judgments) feeding the human-authority queue. VERIFY: `keel record issue` produces a green-validating, guard-passing triaged Issue in one call; a synthesized contradiction appears in the contention view and in what awaits human authority; adjudication is recorded as a Decision and closes it; no contributor can resolve a contention in favour of its own conclusion; clippy + cargo test + validate + guard green."; }
        part dcContentionAdjudicationDoDR1 : TestResult { :>> id = "0d8001ec-0814-61ec-9b3e-0000003001ec"; :>> outcome = VerdictKind::pass; :>> judgedAgainst = "c400309"; :>> judgedAt = "2026-08-15"; :>> judgedBy = "claudeOpus5"; }
        action dcAuthorityQueue;
        verification dcAuthorityQueueDoD : Test { :>> id = "0d5e000c-0812-4e0c-9b3e-00000000e00c"; :>> method = VerificationMethod::demo; :>> procedureText = "srDcHumanAuthorityQueue (D0129). Human judgment is the only resource in a mostly-AI team that cannot be scaled by adding contributors, so it must never sit on the critical path of each unit of work; and asking for judgment an automated check could make degrades review into rubber-stamping, which launders unreviewed work as reviewed (D0051: confirm only what tests cannot). Builds on the D0121 review queue + D0049 batched per-sitting review, adding the distributed dimensions. DO: a computed view of everything genuinely awaiting human authority — Decisions to accept, findings at/above the disposition threshold, contentions to adjudicate, per-sitting reviews — each with WAITING AGE and ORIGINATING CONTRIBUTOR, with visible escalation past a threshold; contributors must not block while items wait. VERIFY: the queue lists exactly the items requiring human authority across several contributors, with age + origin; an item past threshold is visibly escalated; a self-evidencing test result never appears; the queue respects governing-version so historical gates are not resurrected (issue068's lesson); clippy + cargo test + validate + guard green."; }
        part dcAuthorityQueueDoDR1 : TestResult { :>> id = "0d8001fc-0814-61fc-9b3e-0000003001fc"; :>> outcome = VerdictKind::pass; :>> judgedAgainst = "07f000f"; :>> judgedAt = "2026-08-15"; :>> judgedBy = "claudeOpus5"; }
        action dcMechanizeOwnership;
        verification dcMechanizeOwnershipDoD : Test { :>> id = "0d5e000d-0812-4e0d-9b3e-00000000e00d"; :>> method = VerificationMethod::test; :>> procedureText = "srDcAuthorityFromRegistry + mechanize D0108 (D0129). D0108's coordination contract (owner-of-record edits fields; non-owners only ADD items/edges or SUPERSEDE; shared regions are append-or-rebase; conflicts go to the human) is CONVENTION-ONLY: absent from the seventeen guards (guards.rs:885-886) and the eight declared rules (rules.sysml:14-132), enforced by CLAUDE.md prose plus a reminder hook — and D0047 says manual vigilance is not a control. In-place writes exist that can clobber another actor's item (write.rs:551-583 set_attr; write.rs:1029 accept_decision replacen on the first proposed status), defended only by a doc comment. DO: a git-diff-aware ownership guard (cf. the doc-sync guard's diff machinery, guards.rs:785+) failing a commit that edits fields of an item whose createdBy is another actor, additive edges and supersedes excepted; and check attestation authority against the registry (kind/role) for acceptance, disposition and adjudication, refusing rather than warning. VERIFY: a non-owner field edit fails the guard while an added edge and a supersede pass; an AI actor attempting a human-only attestation is refused; per-actor landing files reduce shared-anchor conflicts (srDcPerActorWriteTargets); clippy + cargo test + validate + guard green."; }
        part dcMechanizeOwnershipDoDR1 : TestResult { :>> id = "0d80020c-0814-620c-9b3e-00000030020c"; :>> outcome = VerdictKind::pass; :>> judgedAgainst = "1b2fd4f"; :>> judgedAt = "2026-08-15"; :>> judgedBy = "claudeOpus5"; }
        action dcSupersededNeedGaps;
        verification dcSupersededNeedGapsDoD : Test { :>> id = "0d6f0001-0813-4f01-9b3e-0000001f0001"; :>> method = VerificationMethod::test; :>> procedureText = "Resolves issue088. `tier-satisfaction` counts a SUPERSEDED Need as an undecomposed gap. Found 2026-08-13: after decomposing the three D0128 Needs, 5 of the 6 remaining Need gaps (nViewerAuditProvenance, nViewerCoverageGap, nViewerMultiStakeholder, nViewerNotifications, nViewerTemporalState) carry a #Supersede edge from d0115/d0116 — they were DELIBERATELY DESCOPED, and §2.4 makes a superseding Decision the engine's own mechanism for scope. Demanding decomposition of descoped work understates completeness (real decomposition is 47/48 = 98%, reported as 47/53 = 88%) and, worse, invites a future contributor to 'fix' the gap by authoring SystemRequirements for work that was explicitly cut — the metric actively pointing at wrong work. DO: exclude Needs carrying an incoming #Supersede edge from the Need tier's denominator and gap set in compute_tier_satisfaction, and report the superseded count separately so the descoping stays VISIBLE rather than silently vanishing (an excluded item must not become an invisible one). Check whether the same blind spot affects rootedness/coverage/assured, which may share the assumption. VERIFY: the 5 superseded Needs leave the gap set; nViewerPersistedViewpoints (genuinely undecomposed, no supersede edge) REMAINS a gap; the superseded count is reported; a unit test covers superseded-excluded and unsuperseded-retained; clippy + cargo test + keel validate + guard green."; }
        part dcSupersededNeedGapsDoDR1 : TestResult { :>> id = "0d80021c-0814-621c-9b3e-00000030021c"; :>> outcome = VerdictKind::pass; :>> judgedAgainst = "cc9acb3"; :>> judgedAt = "2026-08-15"; :>> judgedBy = "claudeOpus5"; }
        action dcBackfillVerifyEdges;
        verification dcBackfillVerifyEdgesDoD : Test { :>> id = "0d670001-0813-4701-9b3e-000000170001"; :>> method = VerificationMethod::inspect; :>> procedureText = "Resolves issue087. The new verification-trace guard (dcVerificationTrace, D0130/issue082) found 60 PRE-EXISTING pairs after excluding phase-gate noise and after this thread closed its own six: a delivered DoD names a SystemRequirement in its procedure while no #Verify edge reaches that requirement, so `tier-satisfaction` reports the requirement unverified even though its work is done and passing. Almost all are the keel-viewer programme (srViewer*, d0114-d0127 era). NOT fixed by the thread that built the guard, deliberately: authoring `#Verify dependency from <viewerXDoD> to <srViewerX>` asserts that that DoD's evidence actually discharges that requirement, which is a judgment only the delivering thread has the evidence to make (D0108 — add, never speak for another thread's work). DO: walk the 60 pairs; for each, either author the #Verify edge (evidence genuinely discharges the requirement) or record why it does not (the DoD delivered only part of it -> the requirement stays honestly unverified, and the prose mention should be narrowed so it stops reading as a claim). Work in reviewable batches, not one sweep. VERIFY: `keel guard verification-trace` reports 0 warnings; every #Verify edge added is defensible from its DoD's recorded evidence; sr_verified_pct rises with the METHOD MIX shown (keel tier-satisfaction verifiedByMethod) so the rise is not mistaken for functional-test coverage; keel validate + guard green."; }
        part dcBackfillVerifyEdgesDoDR1 : TestResult { :>> id = "0d80023e-0814-623e-9b3e-00000030023e"; :>> outcome = VerdictKind::pass; :>> judgedAgainst = "6b4515d"; :>> judgedAt = "2026-08-15"; :>> judgedBy = "claudeOpus5"; }
        action dcRepairDuplicateIds;
        verification dcRepairDuplicateIdsDoD : Test { :>> id = "0d5e000f-0812-4e0f-9b3e-00000000e00f"; :>> method = VerificationMethod::test; :>> procedureText = "Resolves issue080. The duplicate-identity guard (dcDuplicateIdentityGuard) found 18 distinct element ids reused across 26 locations in .tracking — bootstrap ids copy-pasted between files; `a1b2c3d4-e5f6-4a7b-8c9d-0e1f2a3b4c5d` appears FOUR times. Immutable id is the invariant that lets items share a title without colliding (§2.3), so a duplicated id makes those records not distinctly addressable and any id-keyed view or edge may resolve to the wrong element. Currently GRANDFATHERED to warning (forward-only, per the issue068 lesson) via GRANDFATHERED_DUPLICATE_IDS in keel-cli/src/guards.rs. This is a MIGRATION (D0067 — run the migration skill), NOT a guard change: mint fresh UUIDs for the later occurrences, repoint every reference, reconcile control totals (count of records before == after; no record loses provenance), keep green at each step, and never fabricate historical data. VERIFY: the grandfather list is EMPTY and removed; `keel guard duplicate-identity` passes with 0 warnings and 0 violations; record counts reconcile exactly; every re-identified record retains its original createdAt/createdBy/judgedAt provenance; clippy + cargo test + keel validate + guard green."; }
        part dcRepairDuplicateIdsDoDR1 : TestResult { :>> id = "0d80022c-0814-622c-9b3e-00000030022c"; :>> outcome = VerdictKind::pass; :>> judgedAgainst = "33090db"; :>> judgedAt = "2026-08-15"; :>> judgedBy = "claudeOpus5"; }
        // ---- the headline: first real dogfood (in order) ----
        action dogfoodBusiness;     // move cursor to BusinessWorkflow::Business/brief; author a REAL Brief->Personas->Needs->UseCases in .tracking (use the template idioms) + the phase-gate verification instances (critique S6)
        action dogfoodArchitecture; // derive SystemRequirements with native satisfy from the Needs; native allocate to Components
        action dogfoodDelivery;     // run one Story/task through DoR -> implement -> appended TestResults -> DoD

        // ---- query/tooling gaps from the use-case walkthroughs ----
        action traceNeeds;          // UC3: satisfy-edge text reader + `trace-need <name>` subcommand in query.py
        action issueLoop;           // UC10: .tracking/issues.sysml convention + `query.py issues` listing
        action baselineView;        // UC9: Release = commit SHA + explicit member refs; baseline view computed from it

        // ---- deferred native-leverage (spiked or design-ready) ----
        action trackedMetadataReplan; // D0053: scope the @Tracked migration / decide do-vs-drop. RESOLVED by D0060/D0061 — do the attribution-events migration (see attrModel* below); the old `trackedMetadata` collapse is SUPERSEDED and removed.
        action stateDefSpike;       // M3: spike native state def/transition; if green replace WorkflowDefinition.transitions strings
        action occurrenceRetype;    // M6: spike occurrence def :> Element; retype TestResult (+Decision?) if green
        action authoredByRefs;      // M4 remainder: authoredBy/judgedBy as typed refs to ProjectActors parts (deferred at CR-5)

        // ---- parked design questions (pre-critique + critique) ----
        action safetyCaseViews;     // parked: curated-view + frozen Baseline/Signoff design for the safety case
        action needLayer;           // parked: does Need require a layer discriminator? decide + record
        action crVersioning;        // parked: CR self-modification versioning (meta-process unfreeze design)
        action skillsRefresh;       // rename agile-refinement->backlog-refinement; build test-design/test-result/traceability-audit skills; register

        // ---- the deliverable runtime (after dogfood proves the model) ----
        action runtimeParser;       // text parser/indexer (Rust candidate) replacing kernel+regex readers; opens SysON interop
        action writeApi;            // the write API: enforces writePolicy, ids, append-only results (D0003 becomes real)
        action toolchainWatch;      // adopt expose/render, verify-by, derive/refine/trace when a newer SysML v2 toolchain supports them

        action foldWhatsNext;       // UC6 leftover: merge whats_next.py's workflow-DAG resolution into query.py (a `workflows` subcommand); retire whats_next.py — one tool, one answer
        action contractAlign;       // computed-state contract vs query.py: implement coverageState/satisfaction over verify edges or amend the contract; remove its stale currentState reference
        action specRefresh;         // rewrite/retire the historical design spec so no doc contradicts decisions (was RESUME 'known debt' prose)
        action modelOnlyState;      // D0018: RESUME.md deleted; orient computed; CLAUDE.md bans prose state docs

        // ---- Rust parser CLI sprint backlog (2026-06-12): rustS0..rustS7 feed runtimeParser ----
        action rustS0Workspace;   // Sprint 0: Cargo workspace + quality gates + BDD harness
        action rustS1Lexer;       // Sprint 1: tokenizer for engine dialect; proptest-covered
        action rustS2Parser;      // Sprint 2: recursive descent parser; full thiserror; no .unwrap()
        action rustS3Semantic;    // Sprint 3: package registry + cross-package resolution + type checking
        action rustS4SpecCompat;  // Sprint 4: build.rs spec pin + compile-time grammar hash assertion
        action rustS5CLI;         // Sprint 5: sysmlv2 binary — check + validate subcommands; CI exit codes
        action rustS6Orient;      // Sprint 6: sysmlv2 orient subcommand — pure-Rust pipeline view
        action rustS7QueryAlign;  // Sprint 7: fix done detection (DoDR + R naming); sysmlv2 whats-next; query.py regex align
        action rustS8runtimeParser; // Sprint 8: AST-driven indexer replacing text-scan; Succession.is_ordering_only; parity
        action rustS9writeApi;    // Sprint 9: write.rs — append-result + add-task enforcing UUID/append-only

        verification rustS0WorkspaceDoR : Test { :>> id = "c6788072-6045-438f-a95b-879ce9147ebd"; :>> method = VerificationMethod::inspect; :>> procedureText = "Cargo workspace layout agreed (sysmlv2-parser lib + sysmlv2-cli bin); deny attributes decided; BDD framework (cucumber-rs) selected; CI script drafted; no blocking dependencies"; }
        part rustS0WorkspaceDoRR1 : TestResult { :>> id = "d7891183-7156-4f9c-a0a6-980dc058b4e5"; :>> outcome = VerdictKind::pass; :>> judgedAgainst = "53cd43a"; :>> judgedAt = "2026-06-12"; :>> judgedBy = "claudeOpus"; }
        verification rustS0WorkspaceDoD : Test { :>> id = "4092ffcd-70a7-4fc5-98f6-aebacb68ecff"; :>> method = VerificationMethod::test; :>> procedureText = "Cargo.toml workspace at repo root; sysmlv2-parser and sysmlv2-cli crates exist; both compile with #![deny(warnings, clippy::all, clippy::pedantic, clippy::nursery)]; cargo test passes with zero warnings; pre-commit hook runs cargo clippy -D warnings; validate_all.py still green"; }
        part rustS0WorkspaceDoDR1 : TestResult { :>> id = "e8902294-8267-4a0d-b1b7-091ed169f5e6"; :>> outcome = VerdictKind::pass; :>> judgedAgainst = "fdffd53"; :>> judgedAt = "2026-06-15"; :>> judgedBy = "claudeOpus"; }
        verification rustS0RetroGate : Test { :>> id = "baecae84-8740-494d-b091-982bffed0b14"; :>> method = VerificationMethod::confirmation; :>> procedureText = "Sprint 0 retro held; process improvement items reviewed; any accepted changes recorded as Decisions with CR: commits; team lead confirms retro complete"; }
        verification rustS1LexerDoR : Test { :>> id = "554ef94a-5eba-4e38-8d39-6a503c20960b"; :>> method = VerificationMethod::inspect; :>> procedureText = "Token type list complete; at least three failing proptest strategies written (identifier, string_lit, enum_literal); lexer API type signature agreed; DoD accepted"; }
        part rustS1LexerDoRR1 : TestResult { :>> id = "e8013405-9378-4c2f-d3d9-213ef38a06f7"; :>> outcome = VerdictKind::pass; :>> judgedAgainst = "fc2e44e"; :>> judgedAt = "2026-06-15"; :>> judgedBy = "claudeOpus"; }
        verification rustS1LexerDoD : Test { :>> id = "113eaa88-c18b-4ed3-8cf8-11eeb4e94cee"; :>> method = VerificationMethod::test; :>> procedureText = "Lexer tokenizes all token types in the engine dialect (package, import, action/part/verification/requirement/use-case/attribute/enum def, :>>, ::, first/then, string, UUID, enum literal); proptest: minimum 50 cases/strategy; zero panics; no .unwrap() in src/; cargo test + cargo clippy -D warnings green"; }
        part rustS1LexerDoDR1 : TestResult { :>> id = "f9124516-a489-4d3a-e4ea-324bf49b17b8"; :>> outcome = VerdictKind::pass; :>> judgedAgainst = "fc2e44e"; :>> judgedAt = "2026-06-15"; :>> judgedBy = "claudeOpus"; }
        part rustS1LexerDoDR2 : TestResult { :>> id = "bf9971e7-aef1-42ff-bfd2-d420982d6df9"; :>> outcome = VerdictKind::pass; :>> judgedAgainst = "724b19e"; :>> judgedAt = "2026-06-16"; :>> judgedBy = "claudeOpus"; }
        part rustS1LexerDoDR3 : TestResult { :>> id = "6b0a7f41-866d-4574-8016-7589d484840c"; :>> outcome = VerdictKind::pass; :>> judgedAgainst = "ce746fb"; :>> judgedAt = "2026-06-16"; :>> judgedBy = "claudeOpus"; }
        part rustS1LexerDoDR4 : TestResult { :>> id = "e8cef932-f3c1-4201-a3d0-e51cfddbca0f"; :>> outcome = VerdictKind::pass; :>> judgedAgainst = "168c590"; :>> judgedAt = "2026-06-16"; :>> judgedBy = "claudeOpus"; }
        part rustS1LexerDoDR5 : TestResult { :>> id = "61ace018-f0ec-4f68-86cb-eb08967d74e8"; :>> outcome = VerdictKind::pass; :>> judgedAgainst = "2c12483"; :>> judgedAt = "2026-06-17"; :>> judgedBy = "claudeOpus"; }
        part rustS1LexerDoDR6 : TestResult { :>> id = "93ab3cf9-06d2-46b5-8a07-cb16b892c15e"; :>> outcome = VerdictKind::pass; :>> judgedAgainst = "edd7b75"; :>> judgedAt = "2026-06-25"; :>> judgedBy = "claudeOpus"; }
        part rustS1LexerDoDR7 : TestResult { :>> id = "e5ab381e-57b4-4ad3-87f1-a87f2a405556"; :>> outcome = VerdictKind::pass; :>> judgedAgainst = "d2e6874"; :>> judgedAt = "2026-08-14"; :>> judgedBy = "claudeOpus5"; }
        verification rustS1RetroGate : Test { :>> id = "4b5a378d-60f6-495c-96c1-964f99aaa6f5"; :>> method = VerificationMethod::confirmation; :>> procedureText = "Sprint 1 retro held; process improvement items reviewed; any accepted changes recorded as Decisions with CR: commits; team lead confirms retro complete"; }
        verification rustS2ParserDoR : Test { :>> id = "13b90e4a-4c91-4368-9383-cecb5834efe4"; :>> method = VerificationMethod::inspect; :>> procedureText = "BDD feature file has passing scenario skeletons for package, part def, action def, succession, satisfy, allocate; AST node types sketched; error recovery strategy (synchronize-on-semicolon) accepted; DoD accepted"; }
        part rustS2ParserDoRR1 : TestResult { :>> id = "a3b4c5d6-1111-4e7f-b8c9-d0e1f2a3b4c5"; :>> outcome = VerdictKind::pass; :>> judgedAgainst = "513580f"; :>> judgedAt = "2026-06-15"; :>> judgedBy = "claudeOpus"; }
        verification rustS2ParserDoD : Test { :>> id = "5b62f1fd-2b49-44ac-87a3-e122a4c012c3"; :>> method = VerificationMethod::test; :>> procedureText = "Recursive-descent parser produces typed AST for full engine dialect (package, import, part/action/verification/requirement/use-case def, attribute, enum, block, :>> assignments, first/then, satisfy, allocate, #DependsOn); all existing .tracking/ and .engine/ files parse without error; BDD scenarios green; no .unwrap() in src/; cargo test + cargo clippy -D warnings green"; }
        part rustS2ParserDoDR1 : TestResult { :>> id = "b4c5d6e7-2222-4f8a-c9d0-e1f2a3b4c5d6"; :>> outcome = VerdictKind::pass; :>> judgedAgainst = "513580f"; :>> judgedAt = "2026-06-15"; :>> judgedBy = "claudeOpus"; }
        part rustS2ParserDoDR2 : TestResult { :>> id = "b2b9958e-7731-481f-b6b3-615d5e9ba415"; :>> outcome = VerdictKind::pass; :>> judgedAgainst = "724b19e"; :>> judgedAt = "2026-06-16"; :>> judgedBy = "claudeOpus"; }
        part rustS2ParserDoDR3 : TestResult { :>> id = "c1913b0b-8713-49cc-8016-7589d693a494"; :>> outcome = VerdictKind::pass; :>> judgedAgainst = "ce746fb"; :>> judgedAt = "2026-06-16"; :>> judgedBy = "claudeOpus"; }
        part rustS2ParserDoDR4 : TestResult { :>> id = "dd0a09f8-3b4c-4f7d-a3d0-e51d007878df"; :>> outcome = VerdictKind::pass; :>> judgedAgainst = "168c590"; :>> judgedAt = "2026-06-16"; :>> judgedBy = "claudeOpus"; }
        part rustS2ParserDoDR5 : TestResult { :>> id = "ba802566-407f-4ca0-86cb-eb089cd44c2c"; :>> outcome = VerdictKind::pass; :>> judgedAgainst = "2c12483"; :>> judgedAt = "2026-06-17"; :>> judgedBy = "claudeOpus"; }
        part rustS2ParserDoDR6 : TestResult { :>> id = "4d5bd617-d3a3-4507-9f44-b296351ecf91"; :>> outcome = VerdictKind::pass; :>> judgedAgainst = "447effd"; :>> judgedAt = "2026-06-20"; :>> judgedBy = "claudeOpus"; }
        part rustS2ParserDoDR7 : TestResult { :>> id = "bced7232-2e08-41ad-90a2-87857e21c397"; :>> outcome = VerdictKind::pass; :>> judgedAgainst = "0b11080"; :>> judgedAt = "2026-06-21"; :>> judgedBy = "claudeOpus"; }
        part rustS2ParserDoDR8 : TestResult { :>> id = "000d6427-0e8d-47f7-9b84-8ccde7589dcb"; :>> outcome = VerdictKind::pass; :>> judgedAgainst = "edd7b75"; :>> judgedAt = "2026-06-25"; :>> judgedBy = "claudeOpus"; }
        part rustS2ParserDoDR9 : TestResult { :>> id = "b950b275-0c77-4023-b5f6-99bbdfa7741b"; :>> outcome = VerdictKind::pass; :>> judgedAgainst = "d2e6874"; :>> judgedAt = "2026-08-14"; :>> judgedBy = "claudeOpus5"; }
        part rustS2ParserDoDR10 : TestResult { :>> id = "3678b92e-f374-4c6b-aae0-60ff81b50500"; :>> outcome = VerdictKind::pass; :>> judgedAgainst = "a7b39f8"; :>> judgedAt = "2026-08-14"; :>> judgedBy = "claudeOpus5"; }
        part rustS2ParserDoDR11 : TestResult { :>> id = "fcb1f920-043f-4a77-9e0c-174786c29551"; :>> outcome = VerdictKind::pass; :>> judgedAgainst = "cfdca16"; :>> judgedAt = "2026-08-15"; :>> judgedBy = "claudeOpus5"; }
        part rustS2ParserDoDR12 : TestResult { :>> id = "1cf64b61-097a-4d92-96ac-163e5c2aac5f"; :>> outcome = VerdictKind::pass; :>> judgedAgainst = "3c9645e"; :>> judgedAt = "2026-08-22"; :>> judgedBy = "claudeFable5"; }
        verification rustS2RetroGate : Test { :>> id = "b746580e-0978-468e-b101-f88aa41f5a12"; :>> method = VerificationMethod::confirmation; :>> procedureText = "Sprint 2 retro held; process improvement items reviewed; any accepted changes recorded as Decisions with CR: commits; team lead confirms retro complete"; }
        verification rustS3SemanticDoR : Test { :>> id = "80047e3a-6b18-4d89-84ad-7be64038b968"; :>> method = VerificationMethod::inspect; :>> procedureText = "Package registry API agreed; cross-package import resolution algorithm sketched (topological load order); at least two failing BDD scenarios for unresolved-reference errors; DoD accepted"; }
        part rustS3SemanticDoRR1 : TestResult { :>> id = "e7f8a9b0-1234-4e5f-a6b7-c8d9e0f1a2b3"; :>> outcome = VerdictKind::pass; :>> judgedAgainst = "d32fda4"; :>> judgedAt = "2026-06-15"; :>> judgedBy = "claudeSonnet46"; }
        verification rustS3SemanticDoD : Test { :>> id = "ca479d99-727d-4367-837d-50bcde3781da"; :>> method = VerificationMethod::test; :>> procedureText = "PackageRegistry resolves `private import X::*` across all preloaded schema + tracking files; typed references (`: Story`, `: TestResult`) validated against registry; enum literals (e.g. `WorkKind::code`) validated; diagnostic messages include file + line + suggested fix; all .tracking/ files validate green; proptest covers registry merge; cargo test + cargo clippy -D warnings green"; }
        part rustS3SemanticDoDR1 : TestResult { :>> id = "f8a9b0c1-5678-4f6a-b7c8-d9e0f1a2b3c4"; :>> outcome = VerdictKind::pass; :>> judgedAgainst = "d32fda4"; :>> judgedAt = "2026-06-15"; :>> judgedBy = "claudeSonnet46"; }
        part rustS3SemanticDoDR2 : TestResult { :>> id = "5d47ca29-2b45-43fb-b6b3-615d639ecacd"; :>> outcome = VerdictKind::pass; :>> judgedAgainst = "724b19e"; :>> judgedAt = "2026-06-16"; :>> judgedBy = "claudeOpus"; }
        part rustS3SemanticDoDR3 : TestResult { :>> id = "ee219db4-9804-4bf4-8016-7589d888a6c8"; :>> outcome = VerdictKind::pass; :>> judgedAgainst = "ce746fb"; :>> judgedAt = "2026-06-16"; :>> judgedBy = "claudeOpus"; }
        part rustS3SemanticDoDR4 : TestResult { :>> id = "4b0fee64-f1a7-4135-a3d0-e51d05a7d58f"; :>> outcome = VerdictKind::pass; :>> judgedAgainst = "168c590"; :>> judgedAt = "2026-06-16"; :>> judgedBy = "claudeOpus"; }
        part rustS3SemanticDoDR5 : TestResult { :>> id = "077be37b-0af4-4a58-86cb-eb08a224e574"; :>> outcome = VerdictKind::pass; :>> judgedAgainst = "2c12483"; :>> judgedAt = "2026-06-17"; :>> judgedBy = "claudeOpus"; }
        part rustS3SemanticDoDR6 : TestResult { :>> id = "6c6f8b55-1648-4939-ad01-4e851679e364"; :>> outcome = VerdictKind::pass; :>> judgedAgainst = "edd7b75"; :>> judgedAt = "2026-06-25"; :>> judgedBy = "claudeOpus"; }
        part rustS3SemanticDoDR7 : TestResult { :>> id = "2cea8289-8a9e-4fa1-bbb0-e04328e09565"; :>> outcome = VerdictKind::pass; :>> judgedAgainst = "d2e6874"; :>> judgedAt = "2026-08-14"; :>> judgedBy = "claudeOpus5"; }
        part rustS3SemanticDoDR8 : TestResult { :>> id = "9fa7443b-7aa3-483a-8312-4f69069646a5"; :>> outcome = VerdictKind::pass; :>> judgedAgainst = "a7b39f8"; :>> judgedAt = "2026-08-14"; :>> judgedBy = "claudeOpus5"; }
        verification rustS3RetroGate : Test { :>> id = "51cbca04-1509-46ce-8fab-0cabb90ac7f5"; :>> method = VerificationMethod::confirmation; :>> procedureText = "Sprint 3 retro held; process improvement items reviewed; any accepted changes recorded as Decisions with CR: commits; team lead confirms retro complete"; }
        verification rustS4SpecCompatDoR : Test { :>> id = "171b72f1-f5b5-4fc1-bc12-701bed84c53c"; :>> method = VerificationMethod::inspect; :>> procedureText = "Canonical SysML v2 spec URL confirmed (https://github.com/Systems-Modeling/SysML-v2-Release); grammar manifest format understood; SYSML_V2_GRAMMAR_SHA constant to pin agreed; offline-mode env var name agreed; DoD accepted"; }
        part rustS4SpecCompatDoRR1 : TestResult { :>> id = "cdef0123-abcd-4e5f-a6b7-c8d9e0f1a2b4"; :>> outcome = VerdictKind::pass; :>> judgedAgainst = "6bbf241"; :>> judgedAt = "2026-06-15"; :>> judgedBy = "claudeSonnet46"; }
        verification rustS4SpecCompatDoD : Test { :>> id = "7ce88f0c-6f1d-40bb-a3c8-8c045daba7af"; :>> method = VerificationMethod::test; :>> procedureText = "build.rs defines SYSML_V2_SPEC_URL and SYSML_V2_GRAMMAR_SHA constants; fetches grammar manifest on build and verifies SHA256; build fails with actionable message if hash mismatch; SYSML_V2_SPEC_OFFLINE=1 skips remote check; version string emitted as cargo:rustc-env=SYSML_V2_GRAMMAR_VERSION; BDD scenario covers offline and mismatch cases; cargo test + cargo clippy -D warnings green"; }
        part rustS4SpecCompatDoDR1 : TestResult { :>> id = "def01234-bcde-4f6a-b7c8-d9e0f1a2b3c5"; :>> outcome = VerdictKind::pass; :>> judgedAgainst = "6bbf241"; :>> judgedAt = "2026-06-15"; :>> judgedBy = "claudeSonnet46"; }
        part rustS4SpecCompatDoDR2 : TestResult { :>> id = "421905c9-32a3-420f-b6b3-615d67ed5211"; :>> outcome = VerdictKind::pass; :>> judgedAgainst = "724b19e"; :>> judgedAt = "2026-06-16"; :>> judgedBy = "claudeOpus"; }
        part rustS4SpecCompatDoDR3 : TestResult { :>> id = "65411376-f2dc-4bfc-8016-7589dcb7bba8"; :>> outcome = VerdictKind::pass; :>> judgedAgainst = "ce746fb"; :>> judgedAt = "2026-06-16"; :>> judgedBy = "claudeOpus"; }
        part rustS4SpecCompatDoDR4 : TestResult { :>> id = "78391f40-6a69-439a-9863-9b8c8d72706e"; :>> outcome = VerdictKind::pass; :>> judgedAgainst = "168c590"; :>> judgedAt = "2026-06-16"; :>> judgedBy = "claudeOpus"; }
        part rustS4SpecCompatDoDR5 : TestResult { :>> id = "dd6f7ce4-37df-4479-bb5e-a1782a01bc4b"; :>> outcome = VerdictKind::pass; :>> judgedAgainst = "2c12483"; :>> judgedAt = "2026-06-17"; :>> judgedBy = "claudeOpus"; }
        part rustS4SpecCompatDoDR6 : TestResult { :>> id = "d8d1b283-1e03-4a7b-be7e-103c4556996d"; :>> outcome = VerdictKind::pass; :>> judgedAgainst = "edd7b75"; :>> judgedAt = "2026-06-25"; :>> judgedBy = "claudeOpus"; }
        verification rustS4RetroGate : Test { :>> id = "0e7c8f1c-6aeb-49e4-af15-50a937a8f68a"; :>> method = VerificationMethod::confirmation; :>> procedureText = "Sprint 4 retro held; process improvement items reviewed; any accepted changes recorded as Decisions with CR: commits; team lead confirms retro complete"; }
        verification rustS5CLIDoR : Test { :>> id = "f01234ab-5678-4cde-9012-3456789abc10"; :>> method = VerificationMethod::inspect; :>> procedureText = "sysmlv2-cli binary approach agreed: lib.rs (check_files/validate_root/collect_sysml) + main.rs dispatching check/validate/ls; BDD tests via cucumber-rs test lib functions directly; 3 scenarios outlined; no clap dep; DoD accepted"; }
        part rustS5CLIDoRR1 : TestResult { :>> id = "a1b2c3d4-e5f6-4a7b-8c9d-0e1f2a3b4c5d"; :>> outcome = VerdictKind::pass; :>> judgedAgainst = "0d379c3"; :>> judgedAt = "2026-06-15"; :>> judgedBy = "claudeSonnet46"; }
        verification rustS5CLIDoD : Test { :>> id = "01234abc-5678-4bcd-ef01-23456789abcd"; :>> method = VerificationMethod::test; :>> procedureText = "sysmlv2 binary: check FILE... exits 0/1/2; validate [ROOT] registers schema + validates .tracking/ exits 0/1/2; ls [ROOT] lists .sysml files; lib.rs exports check_files/validate_root/collect_sysml; 3 BDD scenarios green; 71 total tests pass; clippy -D warnings clean"; }
        part rustS5CLIDoDR1 : TestResult { :>> id = "b2c3d4e5-f6a7-4b8c-9d0e-1f2a3b4c5d6e"; :>> outcome = VerdictKind::pass; :>> judgedAgainst = "18e5a51"; :>> judgedAt = "2026-06-15"; :>> judgedBy = "claudeSonnet46"; }
        part rustS5CLIDoDR2 : TestResult { :>> id = "fb297db1-12d8-4d3f-b6b3-615d6cbbe569"; :>> outcome = VerdictKind::pass; :>> judgedAgainst = "724b19e"; :>> judgedAt = "2026-06-16"; :>> judgedBy = "claudeOpus"; }
        part rustS5CLIDoDR3 : TestResult { :>> id = "dd9cdb70-d88c-4424-8016-7589e16b626c"; :>> outcome = VerdictKind::pass; :>> judgedAgainst = "ce746fb"; :>> judgedAt = "2026-06-16"; :>> judgedBy = "claudeOpus"; }
        part rustS5CLIDoDR4 : TestResult { :>> id = "8a062d2f-49db-43f2-9863-9b8c91e6292e"; :>> outcome = VerdictKind::pass; :>> judgedAgainst = "168c590"; :>> judgedAt = "2026-06-16"; :>> judgedBy = "claudeOpus"; }
        part rustS5CLIDoDR5 : TestResult { :>> id = "4c0e2f83-560b-466d-bb5e-a1782e928b23"; :>> outcome = VerdictKind::pass; :>> judgedAgainst = "2c12483"; :>> judgedAt = "2026-06-17"; :>> judgedBy = "claudeOpus"; }
        part rustS5CLIDoDR6 : TestResult { :>> id = "bda8474e-0e5b-476b-9f44-b2963c4bf4f1"; :>> outcome = VerdictKind::pass; :>> judgedAgainst = "447effd"; :>> judgedAt = "2026-06-20"; :>> judgedBy = "claudeOpus"; }
        part rustS5CLIDoDR7 : TestResult { :>> id = "406aa561-a926-45b4-b607-09bad0de55f0"; :>> outcome = VerdictKind::pass; :>> judgedAgainst = "464d71b"; :>> judgedAt = "2026-06-20"; :>> judgedBy = "claudeOpus"; }
        part rustS5CLIDoDR8 : TestResult { :>> id = "8af916aa-8618-4df5-90a2-878585d3a4a7"; :>> outcome = VerdictKind::pass; :>> judgedAgainst = "0b11080"; :>> judgedAt = "2026-06-21"; :>> judgedBy = "claudeOpus"; }
        part rustS5CLIDoDR9 : TestResult { :>> id = "4533d9b1-25be-4bbe-848d-8862f72d567d"; :>> outcome = VerdictKind::pass; :>> judgedAgainst = "edd7b75"; :>> judgedAt = "2026-06-25"; :>> judgedBy = "claudeOpus"; }
        part rustS5CLIDoDR10 : TestResult { :>> id = "18e83796-de8a-435b-94b2-1a7735d5a671"; :>> outcome = VerdictKind::pass; :>> judgedAgainst = "9391588"; :>> judgedAt = "2026-06-30"; :>> judgedBy = "claudeOpus"; }
        part rustS5CLIDoDR11 : TestResult { :>> id = "140c5a5e-29a8-4693-97d5-2c8af9d50d55"; :>> outcome = VerdictKind::pass; :>> judgedAgainst = "cb5720e"; :>> judgedAt = "2026-07-14"; :>> judgedBy = "claudeOpus"; }
        part rustS5CLIDoDR12 : TestResult { :>> id = "de6c223d-9c5e-4a52-bcce-4c8919c828cc"; :>> outcome = VerdictKind::pass; :>> judgedAgainst = "1f1cd66"; :>> judgedAt = "2026-08-14"; :>> judgedBy = "claudeOpus5"; }
        part rustS5CLIDoDR13 : TestResult { :>> id = "264e4489-b32b-4d8d-8826-9cd6141d335c"; :>> outcome = VerdictKind::pass; :>> judgedAgainst = "98b78ba"; :>> judgedAt = "2026-08-14"; :>> judgedBy = "claudeOpus5"; }
        part rustS5CLIDoDR14 : TestResult { :>> id = "da261574-c963-4889-9ebf-94f36eafd887"; :>> outcome = VerdictKind::pass; :>> judgedAgainst = "d2e6874"; :>> judgedAt = "2026-08-14"; :>> judgedBy = "claudeOpus5"; }
        part rustS5CLIDoDR15 : TestResult { :>> id = "d63e97b9-c41e-4db5-9806-2f42f1da6b9f"; :>> outcome = VerdictKind::pass; :>> judgedAgainst = "a7b39f8"; :>> judgedAt = "2026-08-14"; :>> judgedBy = "claudeOpus5"; }
        part rustS5CLIDoDR16 : TestResult { :>> id = "c528c201-7657-4a6f-b285-5e27044f2593"; :>> outcome = VerdictKind::pass; :>> judgedAgainst = "cfdca16"; :>> judgedAt = "2026-08-15"; :>> judgedBy = "claudeOpus5"; }
        part rustS5CLIDoDR17 : TestResult { :>> id = "0b335752-43c8-4559-9f65-c2cf42d24bd0"; :>> outcome = VerdictKind::pass; :>> judgedAgainst = "3f3340f"; :>> judgedAt = "2026-08-17"; :>> judgedBy = "claudeOpus5"; }
        part rustS5CLIDoDR18 : TestResult { :>> id = "fc3bc03c-f2df-4206-95c6-3701a6420da6"; :>> outcome = VerdictKind::pass; :>> judgedAgainst = "c9999aa"; :>> judgedAt = "2026-08-21"; :>> judgedBy = "claudeOpus5"; }
        part rustS5CLIDoDR19 : TestResult { :>> id = "cc696dd0-f5fb-47f0-b3de-02e44b57fbb3"; :>> outcome = VerdictKind::pass; :>> judgedAgainst = "0433ca6"; :>> judgedAt = "2026-08-21"; :>> judgedBy = "claudeFable5"; }
        part rustS5CLIDoDR20 : TestResult { :>> id = "1b913d24-1f63-49ce-9b2b-9c7d2cc66e2d"; :>> outcome = VerdictKind::pass; :>> judgedAgainst = "2af2ac9"; :>> judgedAt = "2026-08-21"; :>> judgedBy = "claudeFable5"; }
        part rustS5CLIDoDR21 : TestResult { :>> id = "50f6acd6-7341-4150-89b7-951757f88b4b"; :>> outcome = VerdictKind::pass; :>> judgedAgainst = "58f54f0"; :>> judgedAt = "2026-08-21"; :>> judgedBy = "claudeFable5"; }
        part rustS5CLIDoDR22 : TestResult { :>> id = "d9a2b449-8a09-4b40-8a4b-8ac9a8b2c1f0"; :>> outcome = VerdictKind::pass; :>> judgedAgainst = "3c9645e"; :>> judgedAt = "2026-08-22"; :>> judgedBy = "claudeFable5"; }
        verification rustS5CLIRetroGate : Test { :>> id = "12345bcd-6789-4dea-f012-3456789abcde"; :>> method = VerificationMethod::confirmation; :>> procedureText = "Sprint 5 retro held; process improvement items reviewed; any accepted changes recorded as Decisions with CR: commits; team lead confirms retro complete"; }
        verification rustS6OrientDoR : Test { :>> id = "23456cde-789a-4efb-0123-456789abcdef"; :>> method = VerificationMethod::inspect; :>> procedureText = "orient subcommand approach agreed: reads .tracking/state.sysml cursor + backlog.sysml outstanding/ready; outputs current phase, ready items, suspect items; exit 0; DoD accepted"; }
        part rustS6OrientDoRR1 : TestResult { :>> id = "f0e1d2c3-b4a5-4f6e-7d8c-9b0a1f2e3d4c"; :>> outcome = VerdictKind::pass; :>> judgedAgainst = "38609e7"; :>> judgedAt = "2026-06-15"; :>> judgedBy = "claudeSonnet46"; }
        verification rustS6OrientDoD : Test { :>> id = "3456def0-89ab-4f0c-1234-56789abcdef0"; :>> method = VerificationMethod::test; :>> procedureText = "sysmlv2 orient [ROOT]: reads state cursor from .tracking/state.sysml; resolves ready/outstanding from backlog action defs + TestResult outcomes; outputs orientation view matching query.py orient; all tests pass; clippy -D warnings clean"; }
        part rustS6OrientDoDR1 : TestResult { :>> id = "e1d2c3b4-a5f6-4e7d-8c9b-0a1f2e3d4c5b"; :>> outcome = VerdictKind::pass; :>> judgedAgainst = "6f45a85"; :>> judgedAt = "2026-06-15"; :>> judgedBy = "claudeSonnet46"; }
        part rustS6OrientDoDR2 : TestResult { :>> id = "0de37861-63f1-417f-b6b3-615d7115b621"; :>> outcome = VerdictKind::pass; :>> judgedAgainst = "724b19e"; :>> judgedAt = "2026-06-16"; :>> judgedBy = "claudeOpus"; }
        part rustS6OrientDoDR3 : TestResult { :>> id = "cdd24c78-8c72-4c48-8016-7589e5ef0b40"; :>> outcome = VerdictKind::pass; :>> judgedAgainst = "ce746fb"; :>> judgedAt = "2026-06-16"; :>> judgedBy = "claudeOpus"; }
        part rustS6OrientDoDR4 : TestResult { :>> id = "b7736bdd-b3a2-4e86-9863-9b8c965b2752"; :>> outcome = VerdictKind::pass; :>> judgedAgainst = "168c590"; :>> judgedAt = "2026-06-16"; :>> judgedBy = "claudeOpus"; }
        part rustS6OrientDoDR5 : TestResult { :>> id = "4f0eef98-4dc6-470d-bb5e-a1783403edc7"; :>> outcome = VerdictKind::pass; :>> judgedAgainst = "2c12483"; :>> judgedAt = "2026-06-17"; :>> judgedBy = "claudeOpus"; }
        part rustS6OrientDoDR6 : TestResult { :>> id = "eee7ca73-a088-4f03-9f44-b29644d6aafd"; :>> outcome = VerdictKind::pass; :>> judgedAgainst = "447effd"; :>> judgedAt = "2026-06-20"; :>> judgedBy = "claudeOpus"; }
        part rustS6OrientDoDR7 : TestResult { :>> id = "b19600df-2d79-4d00-960a-4a1a260920fa"; :>> outcome = VerdictKind::pass; :>> judgedAgainst = "edd7b75"; :>> judgedAt = "2026-06-25"; :>> judgedBy = "claudeOpus"; }
        part rustS6OrientDoDR8 : TestResult { :>> id = "806e818c-3163-47d5-a951-ee4223553b66"; :>> outcome = VerdictKind::pass; :>> judgedAgainst = "cb5720e"; :>> judgedAt = "2026-07-14"; :>> judgedBy = "claudeOpus"; }
        part rustS6OrientDoDR9 : TestResult { :>> id = "948cf0cf-45b1-40df-8fe7-34c9ccfe1957"; :>> outcome = VerdictKind::pass; :>> judgedAgainst = "98b78ba"; :>> judgedAt = "2026-08-14"; :>> judgedBy = "claudeOpus5"; }
        part rustS6OrientDoDR10 : TestResult { :>> id = "828049f5-a917-41cf-89eb-b32823b5cdd5"; :>> outcome = VerdictKind::pass; :>> judgedAgainst = "e338eae"; :>> judgedAt = "2026-08-14"; :>> judgedBy = "claudeOpus5"; }
        part rustS6OrientDoDR11 : TestResult { :>> id = "1950fd5e-cac4-468d-86a3-fa93819b7b0d"; :>> outcome = VerdictKind::pass; :>> judgedAgainst = "cfdca16"; :>> judgedAt = "2026-08-15"; :>> judgedBy = "claudeOpus5"; }
        part rustS6OrientDoDR12 : TestResult { :>> id = "63e0f0b5-1a95-4808-bf11-58c0bce5d383"; :>> outcome = VerdictKind::pass; :>> judgedAgainst = "c9999aa"; :>> judgedAt = "2026-08-21"; :>> judgedBy = "claudeOpus5"; }
        verification rustS6OrientRetroGate : Test { :>> id = "456ef012-9abc-4a1d-2345-6789abcdef01"; :>> method = VerificationMethod::confirmation; :>> procedureText = "Sprint 6 retro held; process improvement items reviewed; any accepted changes recorded as Decisions with CR: commits; team lead confirms retro complete"; }
        verification rustS7QueryAlignDoR : Test { :>> id = "a5b6c7d8-e9f0-4a1b-9c2d-3e4f5a6b7c8d"; :>> method = VerificationMethod::inspect; :>> procedureText = "done detection updated to handle both {task}DoDR{n} and {task}R{n} naming in dod_result_is_pass (lib.rs) and parse_result_header (orient.rs); query.py _RESULT_LINE regex aligned (non-greedy + optional DoD infix); sysmlv2 whats-next subcommand approach agreed (outputs orient.ready as plain lines); CHANGE accepted (D0023); DoD accepted"; }
        verification rustS7QueryAlignDoD : Test { :>> id = "b6c7d8e9-f0a1-4b2c-8d3e-4f5a6b7c8d9e"; :>> method = VerificationMethod::test; :>> procedureText = "dod_result_is_pass handles both {task}DoDR{n} (new) and {task}R{n} (legacy) naming; parse_result_header handles both; query.py regex updated to key results under task name; sysmlv2 orient shows all S0-S6 sprints done; sysmlv2 whats-next [ROOT] outputs ready list (one per line); 6 orient BDD scenarios + 6 cli BDD scenarios green; clippy -D warnings clean"; }
        part rustS7QueryAlignDoDR1 : TestResult { :>> id = "5ef6a7b8-c9d0-4e1f-8f30-4a5b6c7d8e9f"; :>> outcome = VerdictKind::pass; :>> judgedAgainst = "2811f5c"; :>> judgedAt = "2026-06-15"; :>> judgedBy = "claudeSonnet46"; }
        part rustS7QueryAlignDoDR2 : TestResult { :>> id = "bad443f5-4a54-49eb-b6b3-615d75898e85"; :>> outcome = VerdictKind::pass; :>> judgedAgainst = "724b19e"; :>> judgedAt = "2026-06-16"; :>> judgedBy = "claudeOpus"; }
        part rustS7QueryAlignDoDR3 : TestResult { :>> id = "85c87912-5a52-4370-8016-7589ea400258"; :>> outcome = VerdictKind::pass; :>> judgedAgainst = "ce746fb"; :>> judgedAt = "2026-06-16"; :>> judgedBy = "claudeOpus"; }
        part rustS7QueryAlignDoDR4 : TestResult { :>> id = "23a42fe0-7754-47e2-9863-9b8c9ad30cd2"; :>> outcome = VerdictKind::pass; :>> judgedAgainst = "168c590"; :>> judgedAt = "2026-06-16"; :>> judgedBy = "claudeOpus"; }
        part rustS7QueryAlignDoDR5 : TestResult { :>> id = "576850e8-b454-4d35-bb5e-a17839bababb"; :>> outcome = VerdictKind::pass; :>> judgedAgainst = "2c12483"; :>> judgedAt = "2026-06-17"; :>> judgedBy = "claudeOpus"; }
        part rustS7QueryAlignDoDR6 : TestResult { :>> id = "aa117098-646c-4abf-9f44-b2964a9d06c1"; :>> outcome = VerdictKind::pass; :>> judgedAgainst = "447effd"; :>> judgedAt = "2026-06-20"; :>> judgedBy = "claudeOpus"; }
        part rustS7QueryAlignDoDR7 : TestResult { :>> id = "a8365374-a732-4a04-b607-09badabb3fac"; :>> outcome = VerdictKind::pass; :>> judgedAgainst = "464d71b"; :>> judgedAt = "2026-06-20"; :>> judgedBy = "claudeOpus"; }
        part rustS7QueryAlignDoDR8 : TestResult { :>> id = "1df8280d-3534-4e42-a787-0bd154b3309b"; :>> outcome = VerdictKind::pass; :>> judgedAgainst = "edd7b75"; :>> judgedAt = "2026-06-25"; :>> judgedBy = "claudeOpus"; }
        part rustS7QueryAlignDoDR9 : TestResult { :>> id = "ecd0a8ba-391e-4918-af61-6668d652c72a"; :>> outcome = VerdictKind::pass; :>> judgedAgainst = "cb5720e"; :>> judgedAt = "2026-07-14"; :>> judgedBy = "claudeOpus"; }
        part rustS7QueryAlignDoDR10 : TestResult { :>> id = "fc19f92a-d42e-4237-bec9-84b61b6aaf20"; :>> outcome = VerdictKind::pass; :>> judgedAgainst = "1f1cd66"; :>> judgedAt = "2026-08-14"; :>> judgedBy = "claudeOpus5"; }
        part rustS7QueryAlignDoDR11 : TestResult { :>> id = "e09f9be4-6beb-445c-9849-865ebac00a9e"; :>> outcome = VerdictKind::pass; :>> judgedAgainst = "98b78ba"; :>> judgedAt = "2026-08-14"; :>> judgedBy = "claudeOpus5"; }
        part rustS7QueryAlignDoDR12 : TestResult { :>> id = "026a2d7a-7a24-421a-8b73-cf8af1673510"; :>> outcome = VerdictKind::pass; :>> judgedAgainst = "e338eae"; :>> judgedAt = "2026-08-14"; :>> judgedBy = "claudeOpus5"; }
        part rustS7QueryAlignDoDR13 : TestResult { :>> id = "adf637c6-d6bf-4e11-ae85-c82c3e3b371e"; :>> outcome = VerdictKind::pass; :>> judgedAgainst = "d2e6874"; :>> judgedAt = "2026-08-14"; :>> judgedBy = "claudeOpus5"; }
        part rustS7QueryAlignDoDR14 : TestResult { :>> id = "43797833-e19f-4310-bfa0-c699a5d00217"; :>> outcome = VerdictKind::pass; :>> judgedAgainst = "cfdca16"; :>> judgedAt = "2026-08-15"; :>> judgedBy = "claudeOpus5"; }
        part rustS7QueryAlignDoDR15 : TestResult { :>> id = "9c649ce2-b190-43e9-8ad8-c20d7c3e7213"; :>> outcome = VerdictKind::pass; :>> judgedAgainst = "c9999aa"; :>> judgedAt = "2026-08-21"; :>> judgedBy = "claudeOpus5"; }
        part rustS7QueryAlignDoDR16 : TestResult { :>> id = "2fc28c62-2869-4033-a7af-d761af4db526"; :>> outcome = VerdictKind::pass; :>> judgedAgainst = "0433ca6"; :>> judgedAt = "2026-08-21"; :>> judgedBy = "claudeFable5"; }
        verification rustS7QueryAlignRetroGate : Test { :>> id = "c7d8e9f0-a1b2-4c3d-be4f-5a6b7c8d9e0f"; :>> method = VerificationMethod::confirmation; :>> procedureText = "Sprint 7 retro held; process improvement items reviewed; any accepted changes recorded as Decisions with CR: commits; team lead confirms retro complete"; }
        verification rustS8runtimeParserDoR : Test { :>> id = "a7b8c9d0-e1f2-4a3b-9c4d-5e6f7a8b9c0d"; :>> method = VerificationMethod::inspect; :>> procedureText = "approach agreed: Succession.is_ordering_only field added (D0025); indexer.rs AST-based extractor replaces orient.rs text-scan; orient::compute wired to indexer; 8 orient BDD scenarios green; parity verified (60 done, same ready list); DoD accepted"; }
        part rustS8runtimeParserDoRR1 : TestResult { :>> id = "b8c9d0e1-f2a3-4b4c-8d5e-6f7a8b9c0d1e"; :>> outcome = VerdictKind::pass; :>> judgedAgainst = "276c833"; :>> judgedAt = "2026-06-15"; :>> judgedBy = "claudeSonnet46"; }
        verification rustS8runtimeParserDoD : Test { :>> id = "f0a1b2c3-d4e5-4f6a-bc7d-8e9f0a1b2c3d"; :>> method = VerificationMethod::test; :>> procedureText = "Succession.is_ordering_only added to AST (D0025); indexer.rs extracts tasks/succs/DoDs/results; orient::compute uses indexer; ordering-only edges handled; package-level items indexed; 8 orient BDD scenarios green; parity with query.py orient (same done/ready counts); clippy clean"; }
        part rustS8runtimeParserDoDR1 : TestResult { :>> id = "ad3e4f5a-b6c7-4d8e-a19c-3b4c5d6e7f8a"; :>> outcome = VerdictKind::pass; :>> judgedAgainst = "5ec2c08"; :>> judgedAt = "2026-06-15"; :>> judgedBy = "claudeSonnet46"; }
        part rustS8runtimeParserDoDR2 : TestResult { :>> id = "c26d7540-72f3-47eb-b6b3-615d79cecc71"; :>> outcome = VerdictKind::pass; :>> judgedAgainst = "724b19e"; :>> judgedAt = "2026-06-16"; :>> judgedBy = "claudeOpus"; }
        part rustS8runtimeParserDoDR3 : TestResult { :>> id = "5f99ae95-d7ce-469c-8016-7589eeae1ba4"; :>> outcome = VerdictKind::pass; :>> judgedAgainst = "ce746fb"; :>> judgedAt = "2026-06-16"; :>> judgedBy = "claudeOpus"; }
        part rustS8runtimeParserDoDR4 : TestResult { :>> id = "1c0048c2-937f-423a-9863-9b8c9f9c77da"; :>> outcome = VerdictKind::pass; :>> judgedAgainst = "168c590"; :>> judgedAt = "2026-06-16"; :>> judgedBy = "claudeOpus"; }
        part rustS8runtimeParserDoDR5 : TestResult { :>> id = "d637056c-1b2c-4eed-bb5e-a17840af9bcf"; :>> outcome = VerdictKind::pass; :>> judgedAgainst = "2c12483"; :>> judgedAt = "2026-06-17"; :>> judgedBy = "claudeOpus"; }
        part rustS8runtimeParserDoDR6 : TestResult { :>> id = "36978290-fe41-4bfb-9f44-b29651173d7d"; :>> outcome = VerdictKind::pass; :>> judgedAgainst = "447effd"; :>> judgedAt = "2026-06-20"; :>> judgedBy = "claudeOpus"; }
        part rustS8runtimeParserDoDR7 : TestResult { :>> id = "b303a01b-32cc-4fb9-90a2-87858d392b3b"; :>> outcome = VerdictKind::pass; :>> judgedAgainst = "0b11080"; :>> judgedAt = "2026-06-21"; :>> judgedBy = "claudeOpus"; }
        part rustS8runtimeParserDoDR8 : TestResult { :>> id = "8a5a4f3b-3cef-4f84-b903-cd8884076800"; :>> outcome = VerdictKind::pass; :>> judgedAgainst = "edd7b75"; :>> judgedAt = "2026-06-25"; :>> judgedBy = "claudeOpus"; }
        part rustS8runtimeParserDoDR9 : TestResult { :>> id = "50c8a27c-d2d0-499d-b949-9270dc99288f"; :>> outcome = VerdictKind::pass; :>> judgedAgainst = "d2e6874"; :>> judgedAt = "2026-08-14"; :>> judgedBy = "claudeOpus5"; }
        part rustS8runtimeParserDoDR10 : TestResult { :>> id = "a7b8c264-dee2-4e1f-bc41-1822174cdf6f"; :>> outcome = VerdictKind::pass; :>> judgedAgainst = "a7b39f8"; :>> judgedAt = "2026-08-14"; :>> judgedBy = "claudeOpus5"; }
        part rustS8runtimeParserDoDR11 : TestResult { :>> id = "a9d45483-3b2f-4ed2-9955-1ea962c6bb2f"; :>> outcome = VerdictKind::pass; :>> judgedAgainst = "cfdca16"; :>> judgedAt = "2026-08-15"; :>> judgedBy = "claudeOpus5"; }
        part rustS8runtimeParserDoDR12 : TestResult { :>> id = "04d5848f-3242-4267-ba6a-29307f83ac14"; :>> outcome = VerdictKind::pass; :>> judgedAgainst = "3c9645e"; :>> judgedAt = "2026-08-22"; :>> judgedBy = "claudeFable5"; }
        verification rustS9writeApiDoR : Test { :>> id = "df6b7c8d-e9f0-4a1b-cd2e-3f4a5b6c7d8e"; :>> method = VerificationMethod::inspect; :>> procedureText = "approach agreed: write.rs uses parser for validation + text insertion; append_result: parse→find N→gen UUID→text insert; add_task: find action def→check dup→gen UUID→insert; subcommands parse --file/--task/--sha/--def/--dod/--method flags; 7 BDD scenarios agreed; CLAUDE.md §4 updates scoped; DoD accepted"; }
        part rustS9writeApiDoRR1 : TestResult { :>> id = "ef7c8d9e-f0a1-4b2c-de3f-4a5b6c7d8e9f"; :>> outcome = VerdictKind::pass; :>> judgedAgainst = "6d9fdb5"; :>> judgedAt = "2026-06-15"; :>> judgedBy = "claudeSonnet46"; }
        verification rustS9writeApiDoD : Test { :>> id = "fa8d9e0f-a1b2-4c3d-ef4a-5b6c7d8e9f0a"; :>> method = VerificationMethod::test; :>> procedureText = "write.rs: append_result enforces append-only + auto-UUID; add_task enforces no-dup + auto-UUID; sysmlv2 append-result + add-task subcommands; 7 write BDD scenarios green; all existing tests green; CLAUDE.md §4 updated to retire direct editing as primary path; clippy clean"; }
        part rustS9writeApiDoDR1 : TestResult { :>> id = "de8f9a0b-c1d2-4e3f-b24a-5c6d7e8f9a0b"; :>> outcome = VerdictKind::pass; :>> judgedAgainst = "58ba2c3"; :>> judgedAt = "2026-06-15"; :>> judgedBy = "claudeSonnet46"; }
        part rustS9writeApiDoDR2 : TestResult { :>> id = "6aedd341-6b85-4f43-b6b3-615d7e61c595"; :>> outcome = VerdictKind::pass; :>> judgedAgainst = "724b19e"; :>> judgedAt = "2026-06-16"; :>> judgedBy = "claudeOpus"; }
        part rustS9writeApiDoDR3 : TestResult { :>> id = "2360c3dd-f345-40b0-8016-7589f339e040"; :>> outcome = VerdictKind::pass; :>> judgedAgainst = "ce746fb"; :>> judgedAt = "2026-06-16"; :>> judgedBy = "claudeOpus"; }
        part rustS9writeApiDoDR4 : TestResult { :>> id = "9a6ee543-5b61-4fde-9863-9b8ca450ba7a"; :>> outcome = VerdictKind::pass; :>> judgedAgainst = "168c590"; :>> judgedAt = "2026-06-16"; :>> judgedBy = "claudeOpus"; }
        part rustS9writeApiDoDR5 : TestResult { :>> id = "a0c525cc-c1a2-463d-bb5e-a17848cf7983"; :>> outcome = VerdictKind::pass; :>> judgedAgainst = "2c12483"; :>> judgedAt = "2026-06-17"; :>> judgedBy = "claudeOpus"; }
        part rustS9writeApiDoDR6 : TestResult { :>> id = "35ed6001-a3b4-4783-9f44-b29656b84759"; :>> outcome = VerdictKind::pass; :>> judgedAgainst = "447effd"; :>> judgedAt = "2026-06-20"; :>> judgedBy = "claudeOpus"; }
        part rustS9writeApiDoDR7 : TestResult { :>> id = "f6bc7669-44aa-40c6-8a80-8f3fb3cacfd9"; :>> outcome = VerdictKind::pass; :>> judgedAgainst = "edd7b75"; :>> judgedAt = "2026-06-25"; :>> judgedBy = "claudeOpus"; }
        part rustS9writeApiDoDR8 : TestResult { :>> id = "5932cfe8-40d9-4a5a-80de-282002870f5b"; :>> outcome = VerdictKind::pass; :>> judgedAgainst = "cb5720e"; :>> judgedAt = "2026-07-14"; :>> judgedBy = "claudeOpus"; }
        part rustS9writeApiDoDR9 : TestResult { :>> id = "258923cb-b830-4e24-8f04-49d906453589"; :>> outcome = VerdictKind::pass; :>> judgedAgainst = "1f1cd66"; :>> judgedAt = "2026-08-14"; :>> judgedBy = "claudeOpus5"; }
        part rustS9writeApiDoDR10 : TestResult { :>> id = "a409a9ec-4f70-4487-9bf8-ada07a925e6a"; :>> outcome = VerdictKind::pass; :>> judgedAgainst = "cfdca16"; :>> judgedAt = "2026-08-15"; :>> judgedBy = "claudeOpus5"; }
        part rustS9writeApiDoDR11 : TestResult { :>> id = "dce09e2a-7f40-4203-852f-414c7095f9e6"; :>> outcome = VerdictKind::pass; :>> judgedAgainst = "c9999aa"; :>> judgedAt = "2026-08-21"; :>> judgedBy = "claudeOpus5"; }
        part rustS9writeApiDoDR12 : TestResult { :>> id = "13114117-52e0-4b2e-a822-621ebc6ba210"; :>> outcome = VerdictKind::pass; :>> judgedAgainst = "0433ca6"; :>> judgedAt = "2026-08-21"; :>> judgedBy = "claudeFable5"; }
        part rustS9writeApiDoDR13 : TestResult { :>> id = "fc5bdb53-1652-4bc4-8f46-0dd94f8d79b9"; :>> outcome = VerdictKind::pass; :>> judgedAgainst = "58f54f0"; :>> judgedAt = "2026-08-21"; :>> judgedBy = "claudeFable5"; }
        part rustS9writeApiDoDR14 : TestResult { :>> id = "adc18ea5-6dc0-4980-a1da-c63fb2544f38"; :>> outcome = VerdictKind::pass; :>> judgedAgainst = "3c9645e"; :>> judgedAt = "2026-08-22"; :>> judgedBy = "claudeFable5"; }

        first dogfoodBusiness then dogfoodArchitecture;
        first dogfoodArchitecture then dogfoodDelivery;
        first traceNeeds then baselineView;
        first dogfoodDelivery then runtimeParser;
        first runtimeParser then writeApi;
        first dogfoodDelivery then rustS0Workspace;
        first rustS0Workspace then rustS1Lexer;
        first rustS1Lexer then rustS2Parser;
        first rustS2Parser then rustS3Semantic;
        first rustS3Semantic then rustS4SpecCompat;
        first rustS4SpecCompat then rustS5CLI;
        first rustS5CLI then rustS6Orient;
        first rustS6Orient then rustS7QueryAlign;
        first rustS7QueryAlign then rustS8runtimeParser;
        first rustS8runtimeParser then rustS9writeApi;
        first rustS9writeApi then writeApi;

        verification foldWhatsNextDoD : Test { :>> id = "4338695c-eb93-4d73-b904-c9c4c1469840"; :>> method = VerificationMethod::test; :>> procedureText = "query.py workflows subcommand resolves the six workflow DAGs (parity with whats_next.py); whats_next.py retired; single query tool"; }
        part foldWhatsNextR1 : TestResult { :>> id = "6d7e8f9a-0b1c-4d2e-3f4a-5b6c7d8e9f0a"; :>> outcome = VerdictKind::pass; :>> judgedAgainst = "5282ad3"; :>> judgedAt = "2026-06-11"; :>> judgedBy = "claudeOpus"; }
        verification contractAlignDoD : Test { :>> id = "cda3ab15-159b-4e2d-850c-405237a85dc9"; :>> method = VerificationMethod::inspect; :>> procedureText = "computed-state contract and query.py agree clause-by-clause: each view implemented, amended, or explicitly queued; no stale references"; }
        part contractAlignR1 : TestResult { :>> id = "d5e6f7a8-b9c0-4d1e-2f3a-4b5c6d7e8f9a"; :>> outcome = VerdictKind::pass; :>> judgedAgainst = "cc332a5"; :>> judgedAt = "2026-06-15"; :>> judgedBy = "claudeSonnet46"; }
        verification specRefreshDoD : Test { :>> id = "3d2823ec-9cd9-4449-bc35-3db8a5f9773d"; :>> method = VerificationMethod::inspect; :>> procedureText = "the 2026-06-04 spec is rewritten to match decisions 0001-0018 or formally retired to design-history; no doc contradicts the model"; }
        part specRefreshR1 : TestResult { :>> id = "e6f7a8b9-c0d1-4e2f-3a4b-5c6d7e8f9a0b"; :>> outcome = VerdictKind::pass; :>> judgedAgainst = "cc332a5"; :>> judgedAt = "2026-06-15"; :>> judgedBy = "claudeSonnet46"; }
        verification modelOnlyStateDoD : Test { :>> id = "2dc52776-7c18-425f-9413-57ac62aabeec"; :>> method = VerificationMethod::inspect; :>> procedureText = "RESUME.md deleted; CLAUDE.md sec4 bans prose state docs + sec1 routes orientation to query.py orient; no file shadow-tracks the backlog"; }
        part modelOnlyStateR1 : TestResult { :>> id = "2c4dfc07-6c91-4bba-869f-829578959ad6"; :>> outcome = VerdictKind::pass; :>> judgedAgainst = "f1f65d9"; :>> judgedAt = "2026-06-11"; :>> judgedBy = "inspect"; }
        verification dogfoodBusinessDoD : Test { :>> id = "dec73f98-f883-4f0c-b50a-ff8dd24e0e27"; :>> method = VerificationMethod::confirmation; :>> procedureText = "a real Brief/Personas/Needs/UseCases authored in .tracking, phase gates as verification instances, cursor moved, all green; user accepts the Business run"; }
        part dogfoodBusinessR1 : TestResult { :>> id = "a0b1c2d3-e4f5-4a6b-7c8d-9e0f1a2b3c4d"; :>> outcome = VerdictKind::pass; :>> judgedAgainst = "2f70f0e"; :>> judgedAt = "2026-06-11"; :>> judgedBy = "wweatherholtz"; }
        verification dogfoodArchitectureDoD : Test { :>> id = "1ddedbcd-ced1-4537-ace3-ae82759ee1bf"; :>> method = VerificationMethod::confirmation; :>> procedureText = "SystemRequirements satisfy-linked to Needs, allocated to Components; trace queryable; user accepts"; }
        part dogfoodArchitectureR1 : TestResult { :>> id = "f5a6b7c8-d9e0-4f1a-2b3c-4d5e6f7a8b9c"; :>> outcome = VerdictKind::pass; :>> judgedAgainst = "abb033a"; :>> judgedAt = "2026-06-11"; :>> judgedBy = "wweatherholtz"; }
        verification dogfoodDeliveryDoD : Test { :>> id = "50c631b3-5396-4f3c-84f0-054da815afd3"; :>> method = VerificationMethod::confirmation; :>> procedureText = "one item through DoR->implement->appended results->DoD with gates computed; user accepts"; }
        part dogfoodDeliveryR1 : TestResult { :>> id = "8f9a0b1c-2d3e-4f4a-5b6c-7d8e9f0a1b2c"; :>> outcome = VerdictKind::pass; :>> judgedAgainst = "5282ad3"; :>> judgedAt = "2026-06-11"; :>> judgedBy = "wweatherholtz"; }
        verification traceNeedsDoD : Test { :>> id = "9465131e-1510-4d5d-9827-72f311601e0c"; :>> method = VerificationMethod::test; :>> procedureText = "query.py trace-need answers upstream/downstream over satisfy edges read from text; demonstrated on dogfood data"; }
        part traceNeedsR1 : TestResult { :>> id = "9a0b1c2d-3e4f-4a5b-6c7d-8e9f0a1b2c3d"; :>> outcome = VerdictKind::pass; :>> judgedAgainst = "fcef256"; :>> judgedAt = "2026-06-11"; :>> judgedBy = "claudeOpus"; }
        verification issueLoopDoD : Test { :>> id = "1456d1db-63be-4cad-9c0b-4bc8ea2dee97"; :>> method = VerificationMethod::demo; :>> procedureText = "an Issue authored per convention surfaces in `query.py issues` and routes to a backlog task"; }
        part issueLoopDoDR1 : TestResult { :>> id = "e48f0a1b-c2d3-4e4f-a5b6-c7d8e9f0a1b2"; :>> outcome = VerdictKind::pass; :>> judgedAgainst = "5ed8c55"; :>> judgedAt = "2026-06-15"; :>> judgedBy = "claudeSonnet46"; }
        verification baselineViewDoD : Test { :>> id = "25e39c3c-632e-4d51-af2e-1b1604539dbb"; :>> method = VerificationMethod::demo; :>> procedureText = "a Release (commit + member refs) renders a computed baseline view"; }
        part baselineViewDoDR1 : TestResult { :>> id = "4e6b10fe-8963-46d5-8d40-1665cc7f4026"; :>> outcome = VerdictKind::pass; :>> judgedAgainst = "62cd0b6"; :>> judgedAt = "2026-06-16"; :>> judgedBy = "claudeSonnet46"; }
        verification trackedMetadataReplanDoD : Test { :>> id = "293a4b5c-6d7e-4f81-0619-405162738401"; :>> method = VerificationMethod::confirmation; :>> procedureText = "migration scoped + do-vs-drop decided + recorded; fresh sign-off to touch schema obtained. RESOLVED: D0060/D0061 decide the attribution-events migration (attrModel*); schema sign-off given ('proceed and unfreeze' / 'fine with breaking changes')."; }
        part trackedMetadataReplanDoDR1 : TestResult { :>> id = "293a4b5c-6d7e-4f81-1719-405162738402"; :>> outcome = VerdictKind::pass; :>> judgedAgainst = "06ea622"; :>> judgedAt = "2026-06-17"; :>> judgedBy = "wweatherholtz"; }
        verification stateDefSpikeDoD : Test { :>> id = "37c1b11f-e0f4-4955-bdd1-b1e15651aad5"; :>> method = VerificationMethod::test; :>> procedureText = "state def/transition spike verdict recorded; transitions strings replaced if green"; }
        part stateDefSpikeDoDR1 : TestResult { :>> id = "fb279cad-1e2f-4a3b-bcd4-5e6f7a8b9c0e"; :>> outcome = VerdictKind::pass; :>> judgedAgainst = "146bc25"; :>> judgedAt = "2026-06-15"; :>> judgedBy = "claudeSonnet46"; }
        verification occurrenceRetypeDoD : Test { :>> id = "4ef8cff4-11db-4a48-9e20-58447aafe676"; :>> method = VerificationMethod::test; :>> procedureText = "occurrence def spike verdict recorded; TestResult retyped if green; validate_all green"; }
        part occurrenceRetypeDoDR1 : TestResult { :>> id = "0c38adbe-2f3a-4b4c-cde5-6f7a8b9c0d1f"; :>> outcome = VerdictKind::pass; :>> judgedAgainst = "146bc25"; :>> judgedAt = "2026-06-15"; :>> judgedBy = "claudeSonnet46"; }
        verification authoredByRefsDoD : Test { :>> id = "40a97fd6-50bb-4831-b505-60da3050ab97"; :>> method = VerificationMethod::test; :>> procedureText = "authoredBy/judgedBy reference ProjectActors parts (typed or validated-name); tooling reads them"; }
        part authoredByRefsDoDR1 : TestResult { :>> id = "ec7c3fe2-0b1c-4d2e-efa4-5d6e7f8a9b0c"; :>> outcome = VerdictKind::pass; :>> judgedAgainst = "35bf281"; :>> judgedAt = "2026-06-16"; :>> judgedBy = "claudeSonnet46"; }
        verification safetyCaseViewsDoD : Test { :>> id = "a316b216-d051-4f5f-acec-11f7ec092981"; :>> method = VerificationMethod::confirmation; :>> procedureText = "curated-view + frozen Baseline/Signoff design decided + recorded as a Decision"; }
        part safetyCaseViewsDoDR1 : TestResult { :>> id = "eb6b2cb0-7d8e-4f9a-bcd1-2e3f4a5b6c7d"; :>> outcome = VerdictKind::pass; :>> judgedAgainst = "30a9476"; :>> judgedAt = "2026-06-16"; :>> judgedBy = "wweatherholtz"; }
        verification needLayerDoD : Test { :>> id = "c2c81ff3-059e-4831-a609-602d7312809e"; :>> method = VerificationMethod::confirmation; :>> procedureText = "Need layer-discriminator question decided + recorded as a Decision"; }
        part needLayerDoDR1 : TestResult { :>> id = "fc7c3dc1-8e9f-4a0b-cde2-3f4a5b6c7d8e"; :>> outcome = VerdictKind::pass; :>> judgedAgainst = "30a9476"; :>> judgedAt = "2026-06-16"; :>> judgedBy = "wweatherholtz"; }
        verification crVersioningDoD : Test { :>> id = "a0db11b0-fd52-4166-9436-db03ad1d9e42"; :>> method = VerificationMethod::confirmation; :>> procedureText = "CR self-modification versioning decided + recorded as a Decision"; }
        part crVersioningDoDR1 : TestResult { :>> id = "ad8d4ed2-9f0a-4b1c-def3-4a5b6c7d8e9f"; :>> outcome = VerdictKind::pass; :>> judgedAgainst = "30a9476"; :>> judgedAt = "2026-06-16"; :>> judgedBy = "wweatherholtz"; }
        verification skillsRefreshDoD : Test { :>> id = "e5a7417c-bf60-46e0-895f-38aee849b01b"; :>> method = VerificationMethod::inspect; :>> procedureText = "agile-refinement renamed backlog-refinement; test-design/test-result/traceability-audit built + registered"; }
        part skillsRefreshR1 : TestResult { :>> id = "f7a8b9c0-d1e2-4f3a-4b5c-6d7e8f9a0b1c"; :>> outcome = VerdictKind::pass; :>> judgedAgainst = "cc332a5"; :>> judgedAt = "2026-06-15"; :>> judgedBy = "claudeSonnet46"; }
        verification runtimeParserDoR : Test { :>> id = "84374358-4357-4913-a69d-386dd7826104"; :>> method = VerificationMethod::inspect; :>> procedureText = "approach agreed: Succession.is_ordering_only field added (D0025); indexer.rs AST-based extractor replaces orient.rs text-scan; orient::compute wired to indexer; 8 orient BDD scenarios green; parity verified (60 done, same ready list); DoD accepted"; }
        part runtimeParserDoRR1 : TestResult { :>> id = "6574369c-2e60-45bc-a85e-560bc5b55586"; :>> outcome = VerdictKind::pass; :>> judgedAgainst = "276c833"; :>> judgedAt = "2026-06-15"; :>> judgedBy = "claudeSonnet46"; }
        verification runtimeParserDoD : Test { :>> id = "7c78b3cd-b51e-4a26-9b84-bd5e7040b605"; :>> method = VerificationMethod::test; :>> procedureText = "standalone parser/indexer reads schema+instances without the pilot kernel; query layer runs on it; parity with current outputs"; }
        part runtimeParserDoDR1 : TestResult { :>> id = "c7cebdcc-1313-475b-8a9e-eccadbf8d698"; :>> outcome = VerdictKind::pass; :>> judgedAgainst = "5ec2c08"; :>> judgedAt = "2026-06-15"; :>> judgedBy = "claudeSonnet46"; }
        part runtimeParserDoDR2 : TestResult { :>> id = "226d3892-4a17-4a47-b6b3-615d82f832b5"; :>> outcome = VerdictKind::pass; :>> judgedAgainst = "724b19e"; :>> judgedAt = "2026-06-16"; :>> judgedBy = "claudeOpus"; }
        part runtimeParserDoDR3 : TestResult { :>> id = "60873d27-b66a-4ee4-8016-7589f7d6cd0c"; :>> outcome = VerdictKind::pass; :>> judgedAgainst = "ce746fb"; :>> judgedAt = "2026-06-16"; :>> judgedBy = "claudeOpus"; }
        part runtimeParserDoDR4 : TestResult { :>> id = "d5e2450c-a460-49ce-9863-9b8ca8a6896a"; :>> outcome = VerdictKind::pass; :>> judgedAgainst = "168c590"; :>> judgedAt = "2026-06-16"; :>> judgedBy = "claudeOpus"; }
        part runtimeParserDoDR5 : TestResult { :>> id = "fd4806d7-5422-4800-86cb-eb08913b363c"; :>> outcome = VerdictKind::pass; :>> judgedAgainst = "2c12483"; :>> judgedAt = "2026-06-17"; :>> judgedBy = "claudeOpus"; }
        part runtimeParserDoDR6 : TestResult { :>> id = "3751b5dc-719f-4bee-aab1-fc26aa218c22"; :>> outcome = VerdictKind::pass; :>> judgedAgainst = "447effd"; :>> judgedAt = "2026-06-20"; :>> judgedBy = "claudeOpus"; }
        part runtimeParserDoDR7 : TestResult { :>> id = "4e4367ef-e7b0-43b1-90a2-8785732c529f"; :>> outcome = VerdictKind::pass; :>> judgedAgainst = "0b11080"; :>> judgedAt = "2026-06-21"; :>> judgedBy = "claudeOpus"; }
        part runtimeParserDoDR8 : TestResult { :>> id = "274915ca-ff17-4573-b88b-095f8f2bf941"; :>> outcome = VerdictKind::pass; :>> judgedAgainst = "edd7b75"; :>> judgedAt = "2026-06-25"; :>> judgedBy = "claudeOpus"; }
        part runtimeParserDoDR9 : TestResult { :>> id = "56cf2663-d328-444e-996c-c292c73dc6cd"; :>> outcome = VerdictKind::pass; :>> judgedAgainst = "d2e6874"; :>> judgedAt = "2026-08-14"; :>> judgedBy = "claudeOpus5"; }
        part runtimeParserDoDR10 : TestResult { :>> id = "a5d42320-075f-4303-b333-98550ccd4623"; :>> outcome = VerdictKind::pass; :>> judgedAgainst = "a7b39f8"; :>> judgedAt = "2026-08-14"; :>> judgedBy = "claudeOpus5"; }
        part runtimeParserDoDR11 : TestResult { :>> id = "6707c044-d13d-4a9b-8589-53740b8831fc"; :>> outcome = VerdictKind::pass; :>> judgedAgainst = "cfdca16"; :>> judgedAt = "2026-08-15"; :>> judgedBy = "claudeOpus5"; }
        part runtimeParserDoDR12 : TestResult { :>> id = "1a66de2c-2fa2-484e-9415-743240dac09d"; :>> outcome = VerdictKind::pass; :>> judgedAgainst = "3c9645e"; :>> judgedAt = "2026-08-22"; :>> judgedBy = "claudeFable5"; }
        verification runtimeParserRetroGate : Test { :>> id = "c9d0e1f2-a3b4-4c5d-9e6f-7a8b9c0d1e2f"; :>> method = VerificationMethod::confirmation; :>> procedureText = "Sprint 8 retro held; process improvement items reviewed; any accepted changes recorded as Decisions with CR: commits; team lead confirms retro complete"; }
        verification writeApiDoR : Test { :>> id = "881f7dd3-5a0c-437e-8cbf-22083354506b"; :>> method = VerificationMethod::inspect; :>> procedureText = "approach agreed: write.rs uses parser for validation + text insertion; append_result: parse→find N→gen UUID→text insert; add_task: find action def→check dup→gen UUID→insert; subcommands parse --file/--task/--sha/--def/--dod/--method flags; 7 BDD scenarios agreed; CLAUDE.md §4 updates scoped; DoD accepted"; }
        part writeApiDoRR1 : TestResult { :>> id = "b9ecc698-751d-4af4-98d7-c6f17b4449a9"; :>> outcome = VerdictKind::pass; :>> judgedAgainst = "6d9fdb5"; :>> judgedAt = "2026-06-15"; :>> judgedBy = "claudeSonnet46"; }
        verification writeApiDoD : Test { :>> id = "864722ea-23bb-469b-9813-a8840d0d526d"; :>> method = VerificationMethod::test; :>> procedureText = "write API enforces writePolicy/ids/append-only; direct text editing retired as the write path"; }
        part writeApiDoDR1 : TestResult { :>> id = "ef0a1b2c-d3e4-4f5a-c06b-7d8e9f0a1b2c"; :>> outcome = VerdictKind::pass; :>> judgedAgainst = "58ba2c3"; :>> judgedAt = "2026-06-15"; :>> judgedBy = "claudeSonnet46"; }
        part writeApiDoDR2 : TestResult { :>> id = "c989e288-e1b4-4193-b6b3-615d877336a5"; :>> outcome = VerdictKind::pass; :>> judgedAgainst = "724b19e"; :>> judgedAt = "2026-06-16"; :>> judgedBy = "claudeOpus"; }
        part writeApiDoDR3 : TestResult { :>> id = "c1f0b13d-b914-4980-8016-7589fb908c6c"; :>> outcome = VerdictKind::pass; :>> judgedAgainst = "ce746fb"; :>> judgedAt = "2026-06-16"; :>> judgedBy = "claudeOpus"; }
        part writeApiDoDR4 : TestResult { :>> id = "7f82eb15-79d8-4d62-9863-9b8cad2691ba"; :>> outcome = VerdictKind::pass; :>> judgedAgainst = "168c590"; :>> judgedAt = "2026-06-16"; :>> judgedBy = "claudeOpus"; }
        part writeApiDoDR5 : TestResult { :>> id = "fc331672-9f68-47cd-bb5e-a178604dd807"; :>> outcome = VerdictKind::pass; :>> judgedAgainst = "2c12483"; :>> judgedAt = "2026-06-17"; :>> judgedBy = "claudeOpus"; }
        part writeApiDoDR6 : TestResult { :>> id = "be5d1fb0-241e-438b-9f44-b296663cd465"; :>> outcome = VerdictKind::pass; :>> judgedAgainst = "447effd"; :>> judgedAt = "2026-06-20"; :>> judgedBy = "claudeOpus"; }
        part writeApiDoDR7 : TestResult { :>> id = "a8451321-6396-45cf-8506-4c8bf240f8c0"; :>> outcome = VerdictKind::pass; :>> judgedAgainst = "edd7b75"; :>> judgedAt = "2026-06-25"; :>> judgedBy = "claudeOpus"; }
        part writeApiDoDR8 : TestResult { :>> id = "9e594572-580a-4e20-b554-6d4593f8d8da"; :>> outcome = VerdictKind::pass; :>> judgedAgainst = "cb5720e"; :>> judgedAt = "2026-07-14"; :>> judgedBy = "claudeOpus"; }
        part writeApiDoDR9 : TestResult { :>> id = "7b163038-bd59-4529-b864-de6d2fa24bf0"; :>> outcome = VerdictKind::pass; :>> judgedAgainst = "1f1cd66"; :>> judgedAt = "2026-08-14"; :>> judgedBy = "claudeOpus5"; }
        part writeApiDoDR10 : TestResult { :>> id = "eec81edd-2065-4960-bbe8-46ca14f213e9"; :>> outcome = VerdictKind::pass; :>> judgedAgainst = "cfdca16"; :>> judgedAt = "2026-08-15"; :>> judgedBy = "claudeOpus5"; }
        part writeApiDoDR11 : TestResult { :>> id = "34e863ee-0062-432e-8cc8-a663d7f26d8a"; :>> outcome = VerdictKind::pass; :>> judgedAgainst = "c9999aa"; :>> judgedAt = "2026-08-21"; :>> judgedBy = "claudeOpus5"; }
        part writeApiDoDR12 : TestResult { :>> id = "9fe5d36d-d1cf-4035-9811-3e891a30bfa8"; :>> outcome = VerdictKind::pass; :>> judgedAgainst = "0433ca6"; :>> judgedAt = "2026-08-21"; :>> judgedBy = "claudeFable5"; }
        part writeApiDoDR13 : TestResult { :>> id = "8e7b0870-310f-411e-9955-4d76fa04b15c"; :>> outcome = VerdictKind::pass; :>> judgedAgainst = "58f54f0"; :>> judgedAt = "2026-08-21"; :>> judgedBy = "claudeFable5"; }
        part writeApiDoDR14 : TestResult { :>> id = "2970428c-b4b1-4a97-81ab-364f992493bc"; :>> outcome = VerdictKind::pass; :>> judgedAgainst = "3c9645e"; :>> judgedAt = "2026-08-22"; :>> judgedBy = "claudeFable5"; }
        verification toolchainWatchDoD : Test { :>> id = "e08f7e87-bd2b-4702-be9f-b39a76dbb028"; :>> method = VerificationMethod::confirmation; :>> procedureText = "newer toolchain evaluated; expose/verify-by/derive adoption decided + recorded"; }
        part toolchainWatchDoDR1 : TestResult { :>> id = "c3d4e5f6-a7b8-4c9d-0e1f-2a3b4c5d6e7f"; :>> outcome = VerdictKind::pass; :>> judgedAgainst = "aba9e6f"; :>> judgedAt = "2026-06-16"; :>> judgedBy = "claudeSonnet46"; }

        action traceabilityView;    // Sprint 15+: process traceability dashboard tab — sprint-to-process linkage, process evolution timeline, item-to-decision trace, subversion highlighting (issue002, user request 2026-06-16)
        action specVersionRuntimeCheck; // sysmlv2 check --spec-version: report compiled grammar SHA vs current upstream at runtime; SYSML_V2_SPEC_OFFLINE=1 skips remote fetch (user request 2026-06-16)
        first baselineView then traceabilityView;
        first rustS4SpecCompat then specVersionRuntimeCheck;

        verification traceabilityViewDoD : Test { :>> id = "d4e5f6a7-b8c9-4d0e-1f2a-3b4c5d6e7f8a"; :>> method = VerificationMethod::demo; :>> procedureText = "report.py Traceability tab shows: (1) per-sprint process linkage (which skills/workflows each sprint used); (2) process evolution timeline (when skills/decisions changed); (3) item-to-decision trace (backlog items linked to their governing decisions); (4) subversion highlighting (sprints that skipped expected gates). Demonstrates full vertical traceability through the self-improving engine."; }
        part traceabilityViewDoDR1 : TestResult { :>> id = "21349c50-163b-4b49-8a67-c243cba0caeb"; :>> outcome = VerdictKind::pass; :>> judgedAgainst = "7ce9e8d"; :>> judgedAt = "2026-06-16"; :>> judgedBy = "claudeSonnet46"; }
        verification specVersionRuntimeCheckDoD : Test { :>> id = "f2a3b4c5-d6e7-4f8a-9b0c-1d2e3f4a5b6c"; :>> method = VerificationMethod::test; :>> procedureText = "sysmlv2 check --spec-version reports the grammar SHA baked at compile time (SYSML_V2_GRAMMAR_VERSION); optionally fetches current upstream manifest SHA and reports diff; SYSML_V2_SPEC_OFFLINE=1 skips remote fetch and exits 0; exits 0 when current or offline, exits 1 when stale; BDD scenarios cover: online-current, online-stale (exits 1 + prints diff), offline (skips fetch, exits 0); cargo test + clippy -D warnings green"; }
        part specVersionRuntimeCheckDoDR1 : TestResult { :>> id = "3a4b5c6d-7e8f-4012-0619-405162738402"; :>> outcome = VerdictKind::pass; :>> judgedAgainst = "ffb47b6"; :>> judgedAt = "2026-06-16"; :>> judgedBy = "claudeOpus"; }
        part specVersionRuntimeCheckDoDR2 : TestResult { :>> id = "e0d054fb-ce90-4c1a-9863-9b8cb691177a"; :>> outcome = VerdictKind::pass; :>> judgedAgainst = "168c590"; :>> judgedAt = "2026-06-16"; :>> judgedBy = "claudeOpus"; }
        part specVersionRuntimeCheckDoDR3 : TestResult { :>> id = "46bc2cd2-1ebe-4d79-bb5e-a1785a06ffaf"; :>> outcome = VerdictKind::pass; :>> judgedAgainst = "2c12483"; :>> judgedAt = "2026-06-17"; :>> judgedBy = "claudeOpus"; }
        part specVersionRuntimeCheckDoDR4 : TestResult { :>> id = "3be2ebf3-5bdb-448c-bef6-d4653fb608d4"; :>> outcome = VerdictKind::pass; :>> judgedAgainst = "edd7b75"; :>> judgedAt = "2026-06-25"; :>> judgedBy = "claudeOpus"; }

        // ---- 2026-06-16 process step-back: CAE+GQM+ATAM audit program (D0046, all 4 accepted) ----
        action rustToolchainFix;     // W1: repair sysmlv2 validate (schema preload) + orient (drop cursor, fix ready-list parse + count parity); add Python<->Rust parity gate; make no-kernel Rust the default validation path; update CLAUDE.md §5
        action deliverySkills;       // W3: build/compile + test/verify skills (cargo build, cargo test, validators) alongside repo-push
        action auditSkill;           // W2: create+register architectural-critique skill (CAE+GQM+ATAM); rewrite critique process to record findings as tracked Issues/Decisions
        action deliverableSuspicion; // W4: extend suspicion so Rust source-tree changes invalidate the parity TestResults (closes the regression-hiding hole)
        first rustToolchainFix then auditSkill;          // audit GQM metrics consume the parity check
        first rustToolchainFix then deliverableSuspicion; // suspicion extension needs the parity mechanism
        action ceremonyGateGuard;    // D0047/issue010: permanent guard — validate_ceremony.py fails commits where a ceremony gate passes while an earlier-ordered gate is unpassed
        action reviewInvocationGuard; // issue011: enforce that the sprint-review Phase-3 transcript scan ran before the review gate is recorded (guard design dispatched at retro)

        verification rustToolchainFixDoD : Test { :>> id = "a1b2c3d4-e5f6-4708-9a0b-1c2d3e4f5061"; :>> method = VerificationMethod::test; :>> procedureText = "sysmlv2 validate . exits 0 on a green tree (occurrence-def parse fix); sysmlv2 orient . matches query.py orient on in_progress_sprints/ready/suspect/invalidEvidence (no 'cursor' key, no phantom tasks); rust orient total == structural action-task count (92, the correct value); parity_check.py passes (query.py done-undercount tracked as issue012, tolerated); Rust promoted to authority (D0048): CLAUDE.md §1/§5 + pre-commit validate .tracking via sysmlv2 (kernel kept for .engine + as oracle), ending the JVM leak (issue004); cargo test + clippy -D warnings green"; }
        part rustToolchainFixDoDR1 : TestResult { :>> id = "a1b2c3d4-e5f6-4708-9a0b-1c2d3e4f6172"; :>> outcome = VerdictKind::pass; :>> judgedAgainst = "6bc1810"; :>> judgedAt = "2026-06-16"; :>> judgedBy = "claudeOpus"; }
        part rustToolchainFixDoDR2 : TestResult { :>> id = "4a77c202-f6cb-4c0b-b6b3-615d8c81714d"; :>> outcome = VerdictKind::pass; :>> judgedAgainst = "724b19e"; :>> judgedAt = "2026-06-16"; :>> judgedBy = "claudeOpus"; }
        part rustToolchainFixDoDR3 : TestResult { :>> id = "4f805bf7-df78-4ee8-8016-758a000ad090"; :>> outcome = VerdictKind::pass; :>> judgedAgainst = "ce746fb"; :>> judgedAt = "2026-06-16"; :>> judgedBy = "claudeOpus"; }
        part rustToolchainFixDoDR4 : TestResult { :>> id = "6a71b10f-1e9c-489a-9863-9b8cb2145252"; :>> outcome = VerdictKind::pass; :>> judgedAgainst = "168c590"; :>> judgedAt = "2026-06-16"; :>> judgedBy = "claudeOpus"; }
        part rustToolchainFixDoDR5 : TestResult { :>> id = "a29ae807-2141-42f9-bb5e-a17850c892ff"; :>> outcome = VerdictKind::pass; :>> judgedAgainst = "2c12483"; :>> judgedAt = "2026-06-17"; :>> judgedBy = "claudeOpus"; }
        part rustToolchainFixDoDR6 : TestResult { :>> id = "6b91f916-fb87-4427-9f44-b2965e587079"; :>> outcome = VerdictKind::pass; :>> judgedAgainst = "447effd"; :>> judgedAt = "2026-06-20"; :>> judgedBy = "claudeOpus"; }
        part rustToolchainFixDoDR7 : TestResult { :>> id = "4edc3622-4f80-452c-b607-09bae27c6f18"; :>> outcome = VerdictKind::pass; :>> judgedAgainst = "464d71b"; :>> judgedAt = "2026-06-20"; :>> judgedBy = "claudeOpus"; }
        part rustToolchainFixDoDR8 : TestResult { :>> id = "36a23863-b978-4239-90a2-87859380a997"; :>> outcome = VerdictKind::pass; :>> judgedAgainst = "0b11080"; :>> judgedAt = "2026-06-21"; :>> judgedBy = "claudeOpus"; }
        part rustToolchainFixDoDR9 : TestResult { :>> id = "631e9d97-4c65-4208-9bfd-50f6e2b0361a"; :>> outcome = VerdictKind::pass; :>> judgedAgainst = "edd7b75"; :>> judgedAt = "2026-06-25"; :>> judgedBy = "claudeOpus"; }
        part rustToolchainFixDoDR10 : TestResult { :>> id = "056e0ce1-4f81-4c68-9778-efbfcc41c124"; :>> outcome = VerdictKind::pass; :>> judgedAgainst = "f4fc380"; :>> judgedAt = "2026-06-29"; :>> judgedBy = "claudeOpus"; }
        part rustToolchainFixDoDR11 : TestResult { :>> id = "854a5ec4-e645-449d-a62e-dc2e5f554d5a"; :>> outcome = VerdictKind::pass; :>> judgedAgainst = "9391588"; :>> judgedAt = "2026-06-30"; :>> judgedBy = "claudeOpus"; }
        part rustToolchainFixDoDR12 : TestResult { :>> id = "c594f716-4894-4b9c-925a-e9d732eed16c"; :>> outcome = VerdictKind::pass; :>> judgedAgainst = "cb5720e"; :>> judgedAt = "2026-07-14"; :>> judgedBy = "claudeOpus"; }
        part rustToolchainFixDoDR13 : TestResult { :>> id = "d5becbdd-b87e-4f38-81b8-d246d5a8b1f7"; :>> outcome = VerdictKind::pass; :>> judgedAgainst = "1f1cd66"; :>> judgedAt = "2026-08-14"; :>> judgedBy = "claudeOpus5"; }
        part rustToolchainFixDoDR14 : TestResult { :>> id = "ac5ed0d0-9b27-4d4f-a2f2-b6061376eda6"; :>> outcome = VerdictKind::pass; :>> judgedAgainst = "98b78ba"; :>> judgedAt = "2026-08-14"; :>> judgedBy = "claudeOpus5"; }
        part rustToolchainFixDoDR15 : TestResult { :>> id = "b30a8a18-1e2e-4d17-9566-bcb1662dcdfd"; :>> outcome = VerdictKind::pass; :>> judgedAgainst = "e338eae"; :>> judgedAt = "2026-08-14"; :>> judgedBy = "claudeOpus5"; }
        part rustToolchainFixDoDR16 : TestResult { :>> id = "77646c2d-1b7c-420d-b379-93cb97eeaab5"; :>> outcome = VerdictKind::pass; :>> judgedAgainst = "d2e6874"; :>> judgedAt = "2026-08-14"; :>> judgedBy = "claudeOpus5"; }
        part rustToolchainFixDoDR17 : TestResult { :>> id = "368f0815-b2cd-4c83-b172-38e900a63390"; :>> outcome = VerdictKind::pass; :>> judgedAgainst = "a7b39f8"; :>> judgedAt = "2026-08-14"; :>> judgedBy = "claudeOpus5"; }
        part rustToolchainFixDoDR18 : TestResult { :>> id = "00d12226-7b08-410f-885d-45b71690f788"; :>> outcome = VerdictKind::pass; :>> judgedAgainst = "cfdca16"; :>> judgedAt = "2026-08-15"; :>> judgedBy = "claudeOpus5"; }
        part rustToolchainFixDoDR19 : TestResult { :>> id = "998b64d3-76cf-44ed-962c-54d469407c0f"; :>> outcome = VerdictKind::pass; :>> judgedAgainst = "3f3340f"; :>> judgedAt = "2026-08-17"; :>> judgedBy = "claudeOpus5"; }
        part rustToolchainFixDoDR20 : TestResult { :>> id = "3314e734-b8ff-4be1-86a3-0117cf5d5dd1"; :>> outcome = VerdictKind::pass; :>> judgedAgainst = "0a2e2cf"; :>> judgedAt = "2026-08-17"; :>> judgedBy = "claudeOpus5"; }
        part rustToolchainFixDoDR21 : TestResult { :>> id = "c7aa07f6-dce0-4261-ae04-75c2d3d84e88"; :>> outcome = VerdictKind::pass; :>> judgedAgainst = "0003524"; :>> judgedAt = "2026-08-17"; :>> judgedBy = "claudeOpus5"; }
        part rustToolchainFixDoDR22 : TestResult { :>> id = "a20358c7-d2ff-4871-944f-a15c6b57fdaa"; :>> outcome = VerdictKind::pass; :>> judgedAgainst = "322b82e"; :>> judgedAt = "2026-08-17"; :>> judgedBy = "claudeOpus5"; }
        part rustToolchainFixDoDR23 : TestResult { :>> id = "14ccbdca-5a31-4e42-9776-204257edfc72"; :>> outcome = VerdictKind::pass; :>> judgedAgainst = "c68bf8b"; :>> judgedAt = "2026-08-17"; :>> judgedBy = "claudeOpus5"; }
        part rustToolchainFixDoDR24 : TestResult { :>> id = "14ba5fe7-f4f2-4fe9-8366-863b5171f517"; :>> outcome = VerdictKind::pass; :>> judgedAgainst = "c9999aa"; :>> judgedAt = "2026-08-21"; :>> judgedBy = "claudeOpus5"; }
        part rustToolchainFixDoDR25 : TestResult { :>> id = "b9e2ab43-c1cd-40b4-aad5-557a0d0b8f98"; :>> outcome = VerdictKind::pass; :>> judgedAgainst = "0433ca6"; :>> judgedAt = "2026-08-21"; :>> judgedBy = "claudeFable5"; }
        part rustToolchainFixDoDR26 : TestResult { :>> id = "031efba6-2b47-40d3-b425-290bfc459089"; :>> outcome = VerdictKind::pass; :>> judgedAgainst = "2af2ac9"; :>> judgedAt = "2026-08-21"; :>> judgedBy = "claudeFable5"; }
        part rustToolchainFixDoDR27 : TestResult { :>> id = "682876bc-11e2-41c3-b7d1-d97d5e1ff9fe"; :>> outcome = VerdictKind::pass; :>> judgedAgainst = "40988a7"; :>> judgedAt = "2026-08-21"; :>> judgedBy = "claudeFable5"; }
        part rustToolchainFixDoDR28 : TestResult { :>> id = "afe6443e-2697-487b-9b5e-c7fab48a6866"; :>> outcome = VerdictKind::pass; :>> judgedAgainst = "58f54f0"; :>> judgedAt = "2026-08-21"; :>> judgedBy = "claudeFable5"; }
        part rustToolchainFixDoDR29 : TestResult { :>> id = "c8483bc8-d3da-402d-8385-6c26ba441d59"; :>> outcome = VerdictKind::pass; :>> judgedAgainst = "3c9645e"; :>> judgedAt = "2026-08-22"; :>> judgedBy = "claudeFable5"; }
        part rustToolchainFixDoDR30 : TestResult { :>> id = "a7f34022-f571-46bd-884e-8828ef89a06a"; :>> outcome = VerdictKind::pass; :>> judgedAgainst = "c116a61"; :>> judgedAt = "2026-08-22"; :>> judgedBy = "claudeFable5"; }
        verification deliverySkillsDoD : Test { :>> id = "b2c3d4e5-f607-4819-ab1c-2d3e4f506172"; :>> method = VerificationMethod::inspect; :>> procedureText = "build skill (cargo build + validators) and test/verify skill (cargo test + BDD + parity) created under .engine/skills/ and registered in skills-registry.sysml; each carries purpose/triggerCondition/writePolicy; repo-push reconciled to the main-only policy (issue009); doc-sync complete; validate_all green"; }
        part deliverySkillsDoDR1 : TestResult { :>> id = "c3d4e5f6-0718-492a-bc2d-3e4f50617294"; :>> outcome = VerdictKind::pass; :>> judgedAgainst = "14b7050"; :>> judgedAt = "2026-06-16"; :>> judgedBy = "claudeOpus"; }
        verification auditSkillDoD : Test { :>> id = "c3d4e5f6-0718-492a-bc2d-3e4f50617283"; :>> method = VerificationMethod::inspect; :>> procedureText = "architectural-critique SKILL.md created under .engine/skills/ and registered; encodes CAE (Goal->Strategy->Evidence) + GQM metric checks (gate-coverage, satisfy-coverage, deliverable-parity) + ATAM scenario walkthrough; critique process rewritten so findings are recorded as tracked Issue/Decision instances (not a prose doc); validate_all green"; }
        part auditSkillDoDR1 : TestResult { :>> id = "c3d4e5f6-0718-492a-bc2d-3e4f50617295"; :>> outcome = VerdictKind::pass; :>> judgedAgainst = "216b291"; :>> judgedAt = "2026-06-16"; :>> judgedBy = "claudeOpus"; }
        verification deliverableSuspicionDoD : Test { :>> id = "d4e5f607-1829-4a3b-cd3e-4f5061728394"; :>> method = VerificationMethod::test; :>> procedureText = "suspicion model extended: a change to the Rust source tree (by commit/hash) invalidates the parity TestResults that claim the deliverable works; demonstrated live (12 rust tasks suspect after Sprint 17 source changes); sysmlv2 orient suspect reflects it via .engine/deliverable-manifest.txt (D0050); cargo test + clippy green"; }
        part deliverableSuspicionDoDR1 : TestResult { :>> id = "d4e5f607-1829-4a3b-cd3e-4f5061720516"; :>> outcome = VerdictKind::pass; :>> judgedAgainst = "0b9e7a3"; :>> judgedAt = "2026-06-16"; :>> judgedBy = "claudeOpus"; }
        action reverifyDeliverable; // issue014 (autonomous retro S19): re-verify the rust deliverable tasks at HEAD (cargo test + parity_check) and append fresh TestResults to clear the 12 deliverable-suspect items (D0050)
        action backlogPrioritization; // D0052: rank the ready frontier by backlog declaration order so the AI auto-follows the top item (no more 'which one?')
        action decisionAnalysis;      // D0054/issue016: capture structured alternatives + selection criteria in Decision records (ISO 42010 / NPR 7123.1 Decision Analysis), not just the verdict
        action formalViewpointsSchema; // D0057: increment 1 — part def Viewpoint + declared registry (8 viewpoints) + validator wiring (DONE, schema sign-off given)
        action formalViewpoints;      // D0056/issue018: increment 2 — rewire report.py/orient as declaration-DRIVEN renderers + concern-coverage view (which concerns lack a viewpoint)
        first formalViewpointsSchema then formalViewpoints;
        action processDeployingSkills; // D0059: every process has a deploying skill — added doc-sync skill + principle (DONE this sprint)
        // attributionModel (D0060) decomposed into ordered sub-tasks (D0061). Pre-authorized breaking change; kick off in a fresh context.
        action attrModelSchema;          // 1: schema EXPAND (D0063) — ADD createdBy[0..1] (Element + 3 Tracked* bases) + decision[0..1]+rationale[0..1] (Decision), KEEP authoredBy/decisionText/context (additive, green); rename/retire deferred to attrModelContract
        action attrModelInstances;       // 2: MIGRATE (additive, D0063) — every instance +createdBy; every decision +decision+rationale (split from decisionText, KEEP context+decisionText); old fields removed at attrModelContract
        action attrModelTooling;         // 3: validate_actors(createdBy), query.py(read_issues/read_viewpoints), Rust parser/indexer+validate, report.py; re-verify deliverable
        action attrModelAcceptanceEvents;// 4: Decision acceptance as a confirmation TestResult (verify edge); migrate 'Accepted: X' prose to events
        action attrModelCoverageView;    // 5: process-required-attestation coverage view (items missing a required attestation); pairs with formalViewpoints
        action attrModelGuard;           // 6: guard — Decision acceptance is a TestResult, never prose (D0047)
        first attrModelSchema then attrModelInstances;
        first attrModelSchema then attrModelTooling;
        first attrModelInstances then attrModelAcceptanceEvents;
        first attrModelAcceptanceEvents then attrModelCoverageView;
        first attrModelAcceptanceEvents then attrModelGuard;
        first attrModelInstances then attrModelContract;
        first attrModelTooling then attrModelContract;
        verification reverifyDeliverableDoD : Test { :>> id = "e5f60718-293a-4b4c-de4f-506172830517"; :>> method = VerificationMethod::test; :>> procedureText = "at HEAD: cargo test + clippy + parity_check green; fresh passing TestResults appended (judged at HEAD) for the deliverable-manifest tasks; sysmlv2 orient suspect no longer lists them (deliverable drift cleared)"; }
        part reverifyDeliverableDoDR1 : TestResult { :>> id = "f6071829-3a4b-4c5d-ef50-617283050617"; :>> outcome = VerdictKind::pass; :>> judgedAgainst = "724b19e"; :>> judgedAt = "2026-06-16"; :>> judgedBy = "claudeOpus"; }
        verification backlogPrioritizationDoD : Test { :>> id = "07182939-4a5b-4c6d-f051-728394050618"; :>> method = VerificationMethod::test; :>> procedureText = "orient.rs ranks ready by TaskData.order (declaration order), not alphabetically; query.py aligned (insertion order); sysmlv2 orient ready returns trackedMetadata, specVersionRuntimeCheck, reviewInvocationGuard in backlog order; cargo test + clippy green; D0052 recorded"; }
        verification decisionAnalysisDoD : Test { :>> id = "4f506172-8394-4a51-0619-405162738403"; :>> method = VerificationMethod::inspect; :>> procedureText = "Decision authoring convention (and/or schema) gains optional structured alternatives-considered + selection-criteria + rejected-with-reason (ISO 42010 / ADR pattern); sysmlv2-syntax-notes Decision section updated; demonstrated on one Decision; validate_all green"; }
        part decisionAnalysisDoDR1 : TestResult { :>> id = "4f506172-8394-4a51-1719-40516273840a"; :>> outcome = VerdictKind::pass; :>> judgedAgainst = "2aa59b7"; :>> judgedAt = "2026-06-16"; :>> judgedBy = "claudeOpus"; }
        verification formalViewpointsSchemaDoD : Test { :>> id = "61728394-0a5b-4c6d-0619-405162738418"; :>> method = VerificationMethod::test; :>> procedureText = "schema sign-off recorded (D0057); part def Viewpoint :> Element added to computed.sysml (concern/audience/sources/renderer); .engine/views/viewpoint-registry.sysml declares >=8 viewpoints (orient/whats-next/traceability/safety/requirements/decisions/baselines/suspect); validate_instances extended to .engine/views/ + pre-commit + _ID_TYPES; validate_schema + validate_instances green"; }
        part formalViewpointsSchemaDoDR1 : TestResult { :>> id = "61728394-0a5b-4c6d-1719-405162738419"; :>> outcome = VerdictKind::pass; :>> judgedAgainst = "1224053"; :>> judgedAt = "2026-06-16"; :>> judgedBy = "claudeOpus"; }
        verification formalViewpointsDoD : Test { :>> id = "50617283-3940-4a51-0619-405162738405"; :>> method = VerificationMethod::test; :>> procedureText = "increment 2: tooling READS the viewpoint registry (query.py viewpoints = declaration-driven view of declared lenses + render status = the concern/render coverage; query.py orphans = the orphansVP renderer over needs/requirements/tasks/issues missing required edges); CLI views (orient/whats-next/suspect) correspond to declared viewpoints; read_issues brace-truncation bug fixed (issue019); lightweight (no Capella/Kitalpha); validate_all green. (report.py HTML dashboard tab = optional cosmetic follow-on.)"; }
        part formalViewpointsDoDR1 : TestResult { :>> id = "50617283-3940-4a51-1719-405162738406"; :>> outcome = VerdictKind::pass; :>> judgedAgainst = "b6b4144"; :>> judgedAt = "2026-06-17"; :>> judgedBy = "claudeOpus"; }
        verification processDeployingSkillsDoD : Test { :>> id = "61728394-0a5b-4c6d-e619-40516273841d"; :>> method = VerificationMethod::inspect; :>> procedureText = "D0059 recorded (process->skill principle); doc-sync skill created under .engine/skills/ + registered; CLAUDE.md §4 references the doc-sync skill + the principle; validate_instances green"; }
        part processDeployingSkillsDoDR1 : TestResult { :>> id = "61728394-0a5b-4c6d-f619-40516273841e"; :>> outcome = VerdictKind::pass; :>> judgedAgainst = "1c844af"; :>> judgedAt = "2026-06-17"; :>> judgedBy = "claudeOpus"; }
        verification attrModelSchemaDoD : Test { :>> id = "61728394-0a5b-4c6d-1819-405162738441"; :>> method = VerificationMethod::test; :>> procedureText = "EXPAND (D0063): ADD createdBy[0..1] to Element + 3 Tracked* bases + decision[0..1]+rationale[0..1] to Decision; KEEP authoredBy/decisionText/context (additive — existing instances stay valid, commit green); validate_schema 14/14 green; schema sign-off recorded (D0063). Rename(authoredBy->createdBy)/retire(decisionText) deferred to attrModelContract."; }
        part attrModelSchemaDoDR1 : TestResult { :>> id = "921583f2-f4d3-4b75-98ca-f386cc0e5c23"; :>> outcome = VerdictKind::pass; :>> judgedAgainst = "44e1e83"; :>> judgedAt = "2026-06-17"; :>> judgedBy = "claudeOpus"; }
        verification attrModelInstancesDoD : Test { :>> id = "61728394-0a5b-4c6d-1919-405162738442"; :>> method = VerificationMethod::test; :>> procedureText = "MIGRATE (D0063, additive — old fields KEPT, removed at attrModelContract): every .engine + .tracking instance gains createdBy (= authoredBy value, 330 sites via populate_created_by.py); every decision gains decision + rationale split from decisionText (KEEP context + decisionText verbatim, 63 files); validate_instances 71/71 + validate_tracking + validate_actors green; createdBy count == authoredBy count. (Removal of authoredBy/decisionText + 'no orphaned old-field refs' is attrModelContract.)"; }
        part attrModelInstancesDoDR1 : TestResult { :>> id = "a9c20b22-4b37-4cc6-bcb5-33fd09e88696"; :>> outcome = VerdictKind::pass; :>> judgedAgainst = "88b7727"; :>> judgedAt = "2026-06-17"; :>> judgedBy = "claudeOpus"; }
        verification attrModelToolingDoD : Test { :>> id = "61728394-0a5b-4c6d-1a19-405162738443"; :>> method = VerificationMethod::test; :>> procedureText = "MIGRATE-readers (D0063): validate_actors scans createdBy (added to its actor-value regex); query.py read_issues prefers createdBy (fallback authoredBy); report.py prefers `decision` (fallback decisionText). Rust parser/indexer/validate need NO change (generic, field-name-agnostic — confirmed by grep: zero authoredBy/decisionText refs in .rs); read_viewpoints reads none of these fields. No deliverable drift (.engine/tools not in deliverable-manifest), so no re-verify. Readers smoke-tested (actors PASS, issues + report render); validate_all green."; }
        part attrModelToolingDoDR1 : TestResult { :>> id = "cd0cc189-f0e9-4a5d-9896-b72d653907c7"; :>> outcome = VerdictKind::pass; :>> judgedAgainst = "fdf3d85"; :>> judgedAt = "2026-06-17"; :>> judgedBy = "claudeOpus"; }
        verification attrModelAcceptanceEventsDoD : Test { :>> id = "61728394-0a5b-4c6d-1b19-405162738444"; :>> method = VerificationMethod::test; :>> procedureText = "Decision acceptance = a confirmation event (dNNNNAccept Test + dNNNNAcceptR1 result) verifying the Decision by naming (D0066). ALL 65 accepted decisions migrated to events (migrate_acceptance_events.py); the status-only ones attested by the human's explicit directive (2026-06-17, judgedBy=wweatherholtz); superseded d0038 excluded. status=accepted kept as the structured fact (uniform tooling, no grandfather split). sysmlv2-syntax-notes convention updated; new decisions carry an event. validate_instances 74/74 green. (Coverage view + guard = attrModelCoverageView / attrModelGuard.)"; }
        part attrModelAcceptanceEventsDoDR1 : TestResult { :>> id = "518835d7-d06c-4155-b004-8159945e534f"; :>> outcome = VerdictKind::pass; :>> judgedAgainst = "db057b5"; :>> judgedAt = "2026-06-17"; :>> judgedBy = "claudeOpus"; }
        verification attrModelCoverageViewDoD : Test { :>> id = "61728394-0a5b-4c6d-1c19-405162738445"; :>> method = VerificationMethod::test; :>> procedureText = "query.py attestation-coverage (kernel-free) lists items whose governing process requires an attestation they lack — current rule: status=accepted Decision must have a passing acceptance event (dNNNNAccept, D0066); extensible. Declared as the attestation-coverage Viewpoint (D0056/D0057). Demonstrated: 66/66 accepted decisions covered, 0 missing. usage.md row added. validate_all green."; }
        part attrModelCoverageViewDoDR1 : TestResult { :>> id = "229a971e-eac7-4d31-8e53-f3a018233f43"; :>> outcome = VerdictKind::pass; :>> judgedAgainst = "853901b"; :>> judgedAt = "2026-06-17"; :>> judgedBy = "claudeOpus"; }
        verification attrModelGuardDoD : Test { :>> id = "61728394-0a5b-4c6d-1d19-405162738446"; :>> method = VerificationMethod::test; :>> procedureText = "validate_acceptance_events.py (kernel-free) flags a status=accepted Decision lacking a passing acceptance event (acceptance is a TestResult, not prose/status; D0066/D0047). --selftest passes (positive: accepted+event; negative: accepted-no-event flagged); 0 violations at HEAD (66 accepted); wired into pre-commit on .engine/decisions changes; CLAUDE.md §5 lists it. validate_all green."; }
        part attrModelGuardDoDR1 : TestResult { :>> id = "32db4b8f-b939-4d77-a576-40158699d285"; :>> outcome = VerdictKind::pass; :>> judgedAgainst = "0149606"; :>> judgedAt = "2026-06-17"; :>> judgedBy = "claudeOpus"; }
        part backlogPrioritizationDoDR1 : TestResult { :>> id = "18293a4b-5c6d-4e7f-0518-394051627390"; :>> outcome = VerdictKind::pass; :>> judgedAgainst = "724b19e"; :>> judgedAt = "2026-06-16"; :>> judgedBy = "claudeOpus"; }
        verification ceremonyGateGuardDoD : Test { :>> id = "e5f60718-293a-4b4c-de4f-506172839405"; :>> method = VerificationMethod::test; :>> procedureText = "validate_ceremony.py enforces 'no ceremony gate passes while an earlier-ordered defined gate is unpassed' across .tracking/delivery/*.sysml; pure-Python (no kernel); wired into pre-commit on delivery changes; hard-fails new violations; historical anomalies grandfathered as WARN; detected the sprint11 anomaly and (pre-fix) would have caught the Sprint 16 Standup skip; runs green (0 violations) at HEAD"; }
        part ceremonyGateGuardDoDR1 : TestResult { :>> id = "f6071829-3a4b-4c5d-ef50-617283940516"; :>> outcome = VerdictKind::pass; :>> judgedAgainst = "0f326b5"; :>> judgedAt = "2026-06-16"; :>> judgedBy = "claudeOpus"; }
        verification reviewInvocationGuardDoD : Test { :>> id = "07182939-4a5b-4c6d-f051-728394051627"; :>> method = VerificationMethod::test; :>> procedureText = "the review gate cannot be recorded without transcript-scan evidence: either (a) a guard requires improvement-scan artifact presence for any RviewGate result, or (b) the sprint-review skill records its Phase-3 output (improvement_items, even if 'none material') into the delivery file; demonstrated by a review gate lacking scan evidence being flagged; guard design accepted at retro (issue011); validate_all green"; }
        part reviewInvocationGuardDoDR1 : TestResult { :>> id = "50617283-9a5b-4c6d-0619-405162738404"; :>> outcome = VerdictKind::pass; :>> judgedAgainst = "b193c26"; :>> judgedAt = "2026-06-16"; :>> judgedBy = "claudeOpus"; }
        action bootstrapExitEval;
        verification bootstrapExitEvalDoD : Test { :>> id = "0fa1e985-0643-4b7c-8161-4146397eb294"; :>> method = VerificationMethod::inspect; :>> procedureText = "Assess whether the bootstrap runtime is in place against CLAUDE.md section 4's exit condition ('in force NOW, until the runtime exists'): inventory which runtime pieces exist (Rust toolchain authority orient/whats-next/validate, write API append-result/add-task, validators) vs missing (indexer, GUI); decide per-rule whether each bootstrap gap rule is still load-bearing. If the runtime is sufficiently in place, retire/trim the section-4 bootstrap-rules gap block via a recorded Decision + doc-sync; if not, record the remaining gating runtime components. Routed as CHANGE (needs human acceptance + Decision); not a silent doc edit."; }
        part bootstrapExitEvalDoDR1 : TestResult { :>> id = "ea9ebeb3-88d0-4718-a166-944e270b18ac"; :>> outcome = VerdictKind::pass; :>> judgedAgainst = "34fa14d"; :>> judgedAt = "2026-06-17"; :>> judgedBy = "claudeOpus"; }
        action processGovernanceLineage;
        verification processGovernanceLineageDoD : Test { :>> id = "cb159a36-85bd-4124-97bc-1a56ec3a0fb8"; :>> method = VerificationMethod::inspect; :>> procedureText = "EPIC (D0068) — charter-lineage governance resolving issue002. Decomposed into 3 ordered increments: pglCharterEdge (charter edge), pglProcessRef (process ref + retroactivity class + charter-time-freeze resolution), pglViews (governing-process/suspect/reprocess views). Done when all 3 are done. Design + per-increment criteria: D0068."; }
        part processGovernanceLineageDoDR1 : TestResult { :>> id = "082b60f3-c31e-44e8-b4d8-de19d01dc018"; :>> outcome = VerdictKind::pass; :>> judgedAgainst = "ea13ca9"; :>> judgedAt = "2026-06-18"; :>> judgedBy = "claudeOpus"; }
        action attrModelContract;
        verification attrModelContractDoD : Test { :>> id = "857f1056-0bb3-4c11-a1ba-95667921ac87"; :>> method = VerificationMethod::test; :>> procedureText = "CONTRACT (D0063 expand/migrate/contract, final step): once nothing authors or reads authoredBy/decisionText (attrModelInstances + attrModelTooling done), drop authoredBy from Element + 3 Tracked* bases and decisionText from Decision; decision/rationale -> [1..1]; createdBy stays [0..1] (D0065 — TestResult :> Element uses judgedBy, not a creator); validate_schema + validate_instances + validate_tracking + validate_actors green; 0 residual authoredBy/decisionText assignments; schema sign-off recorded (D0065)."; }
        part attrModelContractDoDR1 : TestResult { :>> id = "23c636c9-efd8-4774-93c7-20c3edb88424"; :>> outcome = VerdictKind::pass; :>> judgedAgainst = "0dbf2bd"; :>> judgedAt = "2026-06-17"; :>> judgedBy = "claudeOpus"; }
        action noSprintGuard;
        verification noSprintGuardDoD : Test { :>> id = "1f070591-55cb-4a5c-aa02-889ff9c1b458"; :>> method = VerificationMethod::test; :>> procedureText = "Guard (D0047, fixes issue020): a pure-Python kernel-free check flags substantive .tracking/.engine/schema work (a NextWork/EngineBuild task with a passing DoD, or a schema/decision change) not covered by a sprint delivery file; grandfathers pre-D0064 work by cutoff; wired into pre-commit; positive+negative tested; demonstrably would have caught the attribution migration committed without sprint28. validate_all green."; }
        part noSprintGuardDoDR1 : TestResult { :>> id = "4a0058e9-9a88-47ca-b948-24516596662a"; :>> outcome = VerdictKind::pass; :>> judgedAgainst = "0b6d416"; :>> judgedAt = "2026-06-17"; :>> judgedBy = "claudeOpus"; }
        action triageRouterSkill;
        verification triageRouterSkillDoD : Test { :>> id = "cf800b0f-a8fe-4f68-aa02-889ffeeca7bc"; :>> method = VerificationMethod::inspect; :>> procedureText = "Per-interaction triage router (D0064): engine-triage skill upgraded to break a request into parts, route each to its process (CHANGE/EXECUTE/RECORD/VIEW/ORIENT, sprinted), and FLAG parts that don't cleanly map; (5b) a UserPromptSubmit hook in settings.json fires triage every turn; CLAUDE.md §3 references it; registered in skills-registry; validate_all green."; }
        part triageRouterSkillDoDR1 : TestResult { :>> id = "5494ef60-5d47-43cd-9783-c611f0ea2e17"; :>> outcome = VerdictKind::pass; :>> judgedAgainst = "773126f"; :>> judgedAt = "2026-06-17"; :>> judgedBy = "claudeOpus"; }
        action queryDrivenViewpoints;
        verification queryDrivenViewpointsDoD : Test { :>> id = "3c9e5da4-4b4d-4bc3-ba03-4ff34453b151"; :>> method = VerificationMethod::inspect; :>> procedureText = "Reframe viewpoints as QUERIES, not prescribed Arcadia-style layers (user: 'Arcadia is a program, not a viewpoint schema'). A view = seed item(s) + a type/edge filter + downstream traversal, computed from authored facts: e.g. STPA view = items filtered to Loss/Hazard/Controller/Actuator/Sensor/ProcessModel + control/feedback edges; traceability view = a seed + its trace closure, irrelevant items excluded. Evaluate the current declared viewpoint-registry (D0056/D0057) against this seed+filter+traverse model; simplify/replace the Arcadia-flavored framing; keep it lightweight (no Capella). Routed as CHANGE: needs design + acceptance before schema/tooling work."; }
        part queryDrivenViewpointsDoDR1 : TestResult { :>> id = "a0af1856-de44-4b4d-a035-3b4a14bbc8bf"; :>> outcome = VerdictKind::pass; :>> judgedAgainst = "29db68a"; :>> judgedAt = "2026-06-19"; :>> judgedBy = "claudeOpus"; }
        action migrationProcess;
        verification migrationProcessDoD : Test { :>> id = "02ea10cf-1196-42d9-9624-b02b57a04093"; :>> method = VerificationMethod::inspect; :>> procedureText = "Safe bulk-migration process + deploying skill (D0059). .engine/processes/migration.sysml (Process + ProcessSteps for the 7 gates) + .engine/skills/migration/SKILL.md encoding: expand/migrate/contract spine; gates (justify+Decision -> committed-transform-script -> dry-run+reconcile control-totals -> EXPAND green -> MIGRATE idempotent/sharded -> reconcile-to-zero -> CONTRACT+guard); edge-case checklist (AST-over-regex; control totals balance + content hash; backfill-before-tighten; don't-hoist-unsatisfiable-constraint; idempotent; grandfather/backfill-with-basis NEVER fabricate provenance; dry-run+reversible). D0067 records the standard (research-grounded: Fowler ParallelChange, Ambler Refactoring Databases, Google LSC, event upcasting, Flyway/Liquibase). Skill registered; CLAUDE.md + engine-triage route bulk migrations to it; validate_instances green."; }
        part migrationProcessDoDR1 : TestResult { :>> id = "31e3072b-1f67-4ade-8b2e-f0d3ae5b193a"; :>> outcome = VerdictKind::pass; :>> judgedAgainst = "d8c67bf"; :>> judgedAt = "2026-06-17"; :>> judgedBy = "claudeOpus"; }
        action pglCharterEdge;
        verification pglCharterEdgeDoD : Test { :>> id = "c08cfd33-5820-4ba6-a09a-b5732f9d16ca"; :>> method = VerificationMethod::test; :>> procedureText = "Increment 1 (D0068): add a typed charteredBy edge (work item Story/backlog action -> originating Need/Requirement/Decision) to schema/core/relationships.sysml; demonstrate >=1 link (a sprint Story charteredBy its Decision); the work->charter lineage is traversable; validate_schema + validate_instances + validate . green. Resolves the core of issue002 (sprint->process linkage)."; }
        part pglCharterEdgeDoDR1 : TestResult { :>> id = "92ec633e-8319-4c0c-9d71-9abb36e1a814"; :>> outcome = VerdictKind::pass; :>> judgedAgainst = "6d639fc"; :>> judgedAt = "2026-06-17"; :>> judgedBy = "claudeOpus"; }
        action pglProcessRef;
        verification pglProcessRefDoD : Test { :>> id = "1dae0759-b00c-417a-a09a-b573355c98a6"; :>> method = VerificationMethod::test; :>> procedureText = "Increment 2a (D0068/D0069) — the AUTHORED layer: (1) #ProspectiveChange / #SafetyChange marker defs in schema/core/relationships.sysml; (2) the process-change edges authored in .tracking/process-governance.sysml (cross-package, so NOT in the Decision files — issue021) on the clear, unambiguous process-change Decisions (D0039/D0049/D0064 -> Delivery; D0067 -> migration) with their retroactivity class; effective commit = the Decision's acceptance-event judgedAgainst (no new field); (3) query.py process-changes reader (kernel-free, by name); (4) issue021 (kernel cross-package limit) recorded + doc-sync (usage cheatsheet, syntax-notes). work->process is by convention/kind (no per-item field). validate_all green. (ENFORCEMENT guards + DoR charter-authoring split to pglProcessChangeGuard; resolver = pglViews.)"; }
        part pglProcessRefDoDR1 : TestResult { :>> id = "2519da18-37fe-48d4-a1f8-5716deac4bcc"; :>> outcome = VerdictKind::pass; :>> judgedAgainst = "6531274"; :>> judgedAt = "2026-06-18"; :>> judgedBy = "claudeOpus"; }
        action pglProcessMarkerCarrier;
        verification pglProcessMarkerCarrierDoD : Test { :>> id = "73940516-2c7d-4e8f-d040-516273849565"; :>> method = VerificationMethod::test; :>> procedureText = "D0070 revision (supersedes D0069's stored-edge carrier; replaces sprint39's .tracking edge): record a process change by a #ProspectiveChange/#SafetyChange PREFIX MARKER on the Decision part (in-package, valid in both rust and the kernel — prefix form, not `{ @Marker; }` which rust rejects); delete .tracking/process-governance.sysml; annotate the historical process-change Decisions (D0039/D0049/D0064/D0067 — grandfathered for resolution, NO fabricated linkage per D0067); retarget query.py process-changes to read the marker (process linkage git-derived, Inc 3); record D0070 with acceptance event + flip D0069 status -> superseded; update relationships.sysml comment + usage/syntax docs + issue021. validate_all green (validate_schema 14/14, validate_instances, rust validate, actors/ceremony/coverage/parity)."; }
        part pglProcessMarkerCarrierDoDR1 : TestResult { :>> id = "66780ac5-201b-478a-a92d-05aa92313b4a"; :>> outcome = VerdictKind::pass; :>> judgedAgainst = "683b5ef"; :>> judgedAt = "2026-06-18"; :>> judgedBy = "claudeOpus"; }
        action pglProcessChangeGuard;
        verification pglProcessChangeGuardDoD : Test { :>> id = "73940516-2c7d-4e8f-d039-516273849564"; :>> method = VerificationMethod::test; :>> procedureText = "Increment 2c (D0068/D0070) — the KEYSTONE hard-lock guard (D0047): validate_process_change.py — a staged change to a process def (.engine/processes/* or .engine/workflows/*) MUST be co-committed with a Decision bearing a #ProspectiveChange/#SafetyChange prefix marker (D0070), or the commit fails (typos included, no intent interpretation). FORWARD-ONLY (enforces this commit's staged set), so NO grandfather set is needed — a pre-guard process def is never re-flagged unless changed again. --selftest covers positive (marked decision co-committed) + negative (unmarked / no decision) + neutral (no process-def) + prose-marker-doesn't-count; demonstrated live (staged a process-def change with no decision -> FAIL exit 1); wired into pre-commit on .engine/processes|workflows. validate_all green; --selftest pass. (Charter guard + DoR charter-authoring split to pglCharterEnforcement.)"; }
        part pglProcessChangeGuardDoDR1 : TestResult { :>> id = "7ab30750-5a07-4c11-a4f4-6aae3979debf"; :>> outcome = VerdictKind::pass; :>> judgedAgainst = "3d09307"; :>> judgedAt = "2026-06-18"; :>> judgedBy = "claudeOpus"; }
        action pglCharterEnforcement;
        verification pglCharterEnforcementDoD : Test { :>> id = "73940516-2c7d-4e8f-d041-516273849566"; :>> method = VerificationMethod::test; :>> procedureText = "Charter-edge enforcement (D0068/D0069): (1) a kernel-free charter guard — a Story (delivery sprint) with no #CharteredBy edge is flagged; grandfathers pre-charter-edge sprints (pre-sprint38) by a recorded cutoff; --selftest positive+negative; wired into pre-commit on .tracking/delivery. (2) charter-authoring folded into the sprint-planning / DoR skill (set #CharteredBy at work prep, not hoped). validate_all green; guard --selftest pass."; }
        part pglCharterEnforcementDoDR1 : TestResult { :>> id = "c185e368-5eea-491f-988f-894b78895315"; :>> outcome = VerdictKind::pass; :>> judgedAgainst = "03d6824"; :>> judgedAt = "2026-06-18"; :>> judgedBy = "claudeOpus"; }
        action pglViews;
        verification pglViewsDoD : Test { :>> id = "4cbdacfc-0e33-4076-a09a-b573394242fe"; :>> method = VerificationMethod::test; :>> procedureText = "Increment 3 (D0068/D0069) — the git-traversal RESOLVER (pure computation, no new authored facts), reusing query.py _is_ancestor + git show: governing-version(item) = latest #Changes Decision for the item's process whose effective commit is a git-ancestor of the item's commit; process-as-it-was via git show (audit/regenerate); valid-then? = item's recorded evidence satisfies THAT version's requirements (not today's); reprocess-candidates = items under a superseded version x downstream fan-out x criticality (mandatory iff retroactivity=safety); declared as viewpoints (D0056/D0057); demonstrated on a real process change (e.g. D0049 ceremony); validate_all green."; }
        part pglViewsDoDR1 : TestResult { :>> id = "1b12ba30-b4e5-492c-b4cc-e9e1012d7b20"; :>> outcome = VerdictKind::pass; :>> judgedAgainst = "ea13ca9"; :>> judgedAt = "2026-06-18"; :>> judgedBy = "claudeOpus"; }
        action auditAdherenceMetrics;
        verification auditAdherenceMetricsDoD : Test { :>> id = "73940516-2c7d-4e8f-d044-516273849662"; :>> method = VerificationMethod::test; :>> procedureText = "Operationalize the architectural-critique GQM adherence metrics (D0046) as one command: query.py audit — retrospective, kernel-free, computing charter coverage + ceremony completeness + estimation discipline + per-sitting-review currency, each split ACTIONABLE vs grandfathered (charter since sprint38; ceremony post-issue010) so it never cries wolf. Wired into the architectural-critique SKILL.md (GQM table + one-shot note). Run on the full history: actionable charter=0, actionable ceremony=0 (recent sprints comply); surfaced 2 cross-cutting findings (issue022 actualHours dormant, issue023 sitting-review informal). validate_all green."; }
        part auditAdherenceMetricsDoDR1 : TestResult { :>> id = "78a48ee6-318f-4c23-9adb-1750b9d81ad5"; :>> outcome = VerdictKind::pass; :>> judgedAgainst = "696bfd6"; :>> judgedAt = "2026-06-18"; :>> judgedBy = "claudeOpus"; }
        action actualHoursDisposition;
        verification actualHoursDispositionDoD : Test { :>> id = "73940516-2c7d-4e8f-d044-516273849663"; :>> method = VerificationMethod::confirmation; :>> procedureText = "Resolve issue022 (USER DECISION): formally retire actualHours for AI-autonomous sprints (estimatedPoints stays for sizing/velocity), OR revive it with a meaningful 'actual'. Record the choice as a Decision superseding D0038's actualHours clause; update sprint-planning skill + D0038 reference accordingly. Pending the human's decision (method=confirmation — not inferable)."; }
        part actualHoursDispositionDoDR1 : TestResult { :>> id = "fc05b7e5-febd-406d-a035-3b4a1a82a2af"; :>> outcome = VerdictKind::pass; :>> judgedAgainst = "29db68a"; :>> judgedAt = "2026-06-19"; :>> judgedBy = "wweatherholtz"; }
        action sittingReviewRecord;
        verification sittingReviewRecordDoD : Test { :>> id = "73940516-2c7d-4e8f-d044-516273849664"; :>> method = VerificationMethod::confirmation; :>> procedureText = "Resolve issue023 (USER DECISION + mechanism): define how the per-sitting sprint review (D0049 human gate) is RECORDED — a confirmation TestResult naming the sitting's sprints, recorded only on the human's explicit attestation (D0016/D0051); optionally a guard flagging a sitting of committed sprints with no recorded review. Then record the current sitting's review on the user's attestation. Pending the human's decision."; }
        part sittingReviewRecordDoDR1 : TestResult { :>> id = "d6adccb5-0a7e-43d1-a035-3b4a216c0bd3"; :>> outcome = VerdictKind::pass; :>> judgedAgainst = "29db68a"; :>> judgedAt = "2026-06-19"; :>> judgedBy = "wweatherholtz"; }
        action rustFailLoudLints;
        verification rustFailLoudLintsDoD : Test { :>> id = "73940516-2c7d-4e8f-d045-516273849680"; :>> method = VerificationMethod::test; :>> procedureText = "Migration M0 (D0074): establish fail-loud Rust lints. CLI crate roots (lib.rs + main.rs) deny clippy::unwrap_used/expect_used/panic/todo/unimplemented (CLI src already clean -> green); both crates #![forbid(unsafe_code)]. clippy::indexing_slicing + the parser's 32 restriction-lint sites deferred to parserLintCleanup (M0b) to avoid destabilizing the load-bearing parser. cargo clippy --workspace --all-targets -D warnings green. New CLI/view code (M1) is born under the denies."; }
        part rustFailLoudLintsDoDR1 : TestResult { :>> id = "dc989d98-a99c-40e4-88d4-5ff5ce4df7b4"; :>> outcome = VerdictKind::pass; :>> judgedAgainst = "ee7a9fb"; :>> judgedAt = "2026-06-19"; :>> judgedBy = "claudeOpus"; }
        action parserLintCleanup;
        verification parserLintCleanupDoD : Test { :>> id = "73940516-2c7d-4e8f-d045-516273849681"; :>> method = VerificationMethod::test; :>> procedureText = "Migration M0b (D0074): port the parser crate's 32 unwrap/expect/panic sites (lexer 2, parser 30) to Result-based errors; add clippy::indexing_slicing deny + fix the CLI indexing sites (main.rs windows, write.rs lines[insert_after]); promote the fail-loud lints to workspace-wide (forbid unsafe already global) with test-target allows for restriction lints; remove the parser grandfather note. cargo clippy --workspace --all-targets -D warnings green; cargo test green (parser behavior unchanged)."; }
        part parserLintCleanupDoDR1 : TestResult { :>> id = "d04637ce-b180-4fed-9fce-10c07a264a23"; :>> outcome = VerdictKind::pass; :>> judgedAgainst = "b085bc0"; :>> judgedAt = "2026-06-19"; :>> judgedBy = "claudeOpus"; }
        action tomlViewExecutor;
        verification tomlViewExecutorDoD : Test { :>> id = "73940516-2c7d-4e8f-d045-516273849682"; :>> method = VerificationMethod::test; :>> procedureText = "Migration M1 (D0074/D0075, resolves issue018): a Rust `sysmlv2 view <name>` executor reading .engine/views/<name>.view.toml (serde+toml, deny_unknown_fields, typed enums for direction/depth/edge-kind so bad view files fail at parse) over an enriched item-table (authored + computed attrs); select (type/eq/in/has-missing-edge) + traverse (edges/direction/depth + far-endpoint target predicate for ICD) + project; emits the induced subgraph as JSON. Requires typed-edge extraction in Rust (satisfy/verify/:>/#CharteredBy/dependency). 2-3 example .view.toml + an RWX skill. Velocity excluded (aggregation, not a view). cargo test + clippy green; demonstrated on a real view."; }
        part tomlViewExecutorDoDR1 : TestResult { :>> id = "9702b588-9c87-4e9f-8470-5f8beb705d19"; :>> outcome = VerdictKind::pass; :>> judgedAgainst = "95cf557"; :>> judgedAt = "2026-06-19"; :>> judgedBy = "claudeOpus"; }
        action parserMarkerFix;
        verification parserMarkerFixDoD : Test { :>> id = "73940516-2c7d-4e8f-d046-516273849691"; :>> method = VerificationMethod::test; :>> procedureText = "Fix issue024: parser.rs parse_hash_item silently dropped `#Marker part X : T` (skip_item for any non-first/dependency follower), so D0070-marked process-change Decisions vanished from views. Fix: delegate to parse_item, EMITTING the underlying Part (marker consumed; AST marker-retention deferred to M2). GUARD (D0047): parser unit test marker_prefixed_part_is_preserved. Verified: `view decisions-active-and-superseded` returns all 75 (was 70); cargo test --workspace --lib + parse_engine_files + clippy -D warnings green."; }
        part parserMarkerFixDoDR1 : TestResult { :>> id = "d40727e8-e729-4ac7-a0bd-cc461f7b2fe5"; :>> outcome = VerdictKind::pass; :>> judgedAgainst = "cf12cca"; :>> judgedAt = "2026-06-19"; :>> judgedBy = "claudeOpus"; }
        action markerRetention;
        verification markerRetentionDoD : Test { :>> id = "73940516-2c7d-4e8f-d050-516273849692"; :>> method = VerificationMethod::test; :>> procedureText = "Migration M2.0 (D0074/D0075): retain the #Marker prefix on a Part through the AST (Part.marker: Option<String>) + parser (parse_hash_item attaches the marker to the emitted Part) + view engine (ItemInfo.marker; Select.marker predicate). Prerequisite for governance views as TOML. Parser test asserts marker retained; view test select_by_marker; demonstrated: process-changes.view.toml (select Decision + marker in [ProspectiveChange,SafetyChange]) returns the same 5 decisions as query.py process-changes. cargo test --workspace + clippy -D warnings green."; }
        part markerRetentionDoDR1 : TestResult { :>> id = "49cd9f73-9c42-4952-839b-fd4f5b040baa"; :>> outcome = VerdictKind::pass; :>> judgedAgainst = "8788cc4"; :>> judgedAt = "2026-06-19"; :>> judgedBy = "claudeOpus"; }
        action portStructuralViews;
        verification portStructuralViewsDoD : Test { :>> id = "73940516-2c7d-4e8f-d050-516273849693"; :>> method = VerificationMethod::inspect; :>> procedureText = "Migration M2.1 (D0075): subsume query.py's STRUCTURAL views as .view.toml declarations where the enriched-select model covers them — process-changes (done, marker), orphans (missing_edge), issues (type=Issue), decisions (type/status). Retire the subsumed query.py commands (point at `sysmlv2 view` or remove). validate_all green; each TOML view matches its query.py output before retirement."; }
        part portStructuralViewsDoDR1 : TestResult { :>> id = "0fd544cb-7185-4483-bbdf-1149fd938f99"; :>> outcome = VerdictKind::pass; :>> judgedAgainst = "a7b70db"; :>> judgedAt = "2026-06-19"; :>> judgedBy = "claudeOpus"; }
        action portAttestationCoverage;
        verification portAttestationCoverageDoD : Test { :>> id = "73940516-2c7d-4e8f-d052-516273849695"; :>> method = VerificationMethod::test; :>> procedureText = "Migration M2.2a (D0074/D0075): port attestation-coverage (D0066) to Rust — `sysmlv2 attestation-coverage` reusing the view Model + a pure compute_attestation (accepted Decisions lacking a passing dNNNNAcceptR1). Establishes the algorithmic-port pattern (Rust subcommand + parity vs query.py). PARITY: output byte-identical to query.py attestation-coverage (72/72, missing []). Unit test attestation_flags_accepted_without_event; clippy --workspace -D warnings + cargo test green."; }
        part portAttestationCoverageDoDR1 : TestResult { :>> id = "c0fdc7c2-7ce0-45a3-86a0-e7d29de3c7e5"; :>> outcome = VerdictKind::pass; :>> judgedAgainst = "5cf2984"; :>> judgedAt = "2026-06-19"; :>> judgedBy = "claudeOpus"; }
        action portAlgorithmicViews;
        verification portAlgorithmicViewsDoD : Test { :>> id = "73940516-2c7d-4e8f-d050-516273849694"; :>> method = VerificationMethod::test; :>> procedureText = "Migration M2.2 umbrella (D0074/D0075): port the remaining ALGORITHMIC query.py views to Rust functions/subcommands (git-traversal + computation, not TOML filters). attestation-coverage = portAttestationCoverage (done, M2.2a, pattern established). REMAINING: orphans (per-type required-edge rules), audit (aggregate adherence), and the git-traversal trio governing-version/reprocess/suspect. Each matches its query.py output (parity); cargo test + clippy -D warnings green. Precedes M3 (port guards) + M4 (retire query.py, close issue012)."; }
        part portAlgorithmicViewsDoDR1 : TestResult { :>> id = "8bb3ebc6-666a-47bb-af12-5e48b735e1b1"; :>> outcome = VerdictKind::pass; :>> judgedAgainst = "967f018"; :>> judgedAt = "2026-06-19"; :>> judgedBy = "claudeOpus"; }
        first pglCharterEdge then pglProcessRef;
        first tomlViewExecutor then parserMarkerFix;
        first rustFailLoudLints then parserLintCleanup;
        first rustFailLoudLints then tomlViewExecutor;
        first pglProcessRef then pglProcessMarkerCarrier;
        first pglProcessMarkerCarrier then pglProcessChangeGuard;
        first pglProcessChangeGuard then pglCharterEnforcement;
        first pglCharterEnforcement then pglViews;
        first pglViews then processGovernanceLineage;
        action portOrphansAudit;
        verification portOrphansAuditDoD : Test { :>> id = "7565bdb8-1361-4a17-be64-95478858f171"; :>> method = VerificationMethod::test; :>> procedureText = "Migration M2.2b (D0074/D0075): port the no-git ALGORITHMIC views orphans (compute_orphans) + audit (audit_report) from query.py to Rust subcommands. sysmlv2 orphans + sysmlv2 audit. PARITY: each output byte-identical to query.py orphans / query.py audit. Unit tests for orphans (tasks_without_dod, issues_without_relatedTask, dangling relatedTask) + audit (charter coverage, ceremony completeness, estimation discipline, sitting-review currency, grandfather constants). cargo test --workspace + clippy --all-targets -D warnings green. Leaves the git-traversal trio (governing-version/reprocess/suspect) as M2.2c under the portAlgorithmicViews umbrella."; }
        part portOrphansAuditDoDR1 : TestResult { :>> id = "ab105387-35c4-43bc-a2ba-6bbd8f69bb40"; :>> outcome = VerdictKind::pass; :>> judgedAgainst = "c85d097"; :>> judgedAt = "2026-06-19"; :>> judgedBy = "claudeOpus"; }
        action portGuardsCoverage;
        verification portGuardsCoverageDoD : Test { :>> id = "a57efc1b-fe17-44e0-a874-5797cdd51560"; :>> method = VerificationMethod::test; :>> procedureText = "M3a (D0074): port the no-git forward GUARDS validate_actors + validate_acceptance_events + validate_sprint_coverage to Rust, each exposed via the sysmlv2 CLI and exiting non-zero on violation. PARITY: pass/fail verdict + violation output matches the python guard on the current repo AND on a synthetic violation. acceptance-events reuses the attestation-coverage compute (M2.2a). cargo test + clippy --workspace --all-targets -D warnings green."; }
        part portGuardsCoverageDoDR1 : TestResult { :>> id = "8250f1b4-734e-40ad-b959-67324775e08f"; :>> outcome = VerdictKind::pass; :>> judgedAgainst = "1fe773a"; :>> judgedAt = "2026-06-20"; :>> judgedBy = "claudeOpus"; }
        action portGuardsCeremonyCharter;
        verification portGuardsCeremonyCharterDoD : Test { :>> id = "4e4964a9-b23f-4c9c-a874-5797d3685c94"; :>> method = VerificationMethod::test; :>> procedureText = "M3b (D0074): port validate_ceremony (gate-ordering + retro-scan-evidence, issue011/D0047; reuse orient::gate_passed/GATE_ORDER + scan-evidence keywords + grandfather set) + validate_charter (every newly-added sprint Story carries #CharteredBy; git-derived newly-added set + sprint-since grandfather cutoff, D0068) to Rust, each exiting non-zero on violation. PARITY vs the python guards (current repo + synthetic violation). cargo test + clippy --workspace --all-targets -D warnings green."; }
        part portGuardsCeremonyCharterDoDR1 : TestResult { :>> id = "6a0b9c52-b519-4523-a36d-e882b0f26e11"; :>> outcome = VerdictKind::pass; :>> judgedAgainst = "3ecba70"; :>> judgedAt = "2026-06-20"; :>> judgedBy = "claudeOpus"; }
        action portGuardKeystone;
        verification portGuardKeystoneDoD : Test { :>> id = "e1310ece-da81-432c-a874-5797d8976610"; :>> method = VerificationMethod::test; :>> procedureText = "M3c (D0074): port validate_process_change (keystone hard-lock: a staged .engine/processes|workflows change MUST co-commit a #Prospective/#SafetyChange-marked Decision; git diff --cached + staged content; D0070) to Rust, AND add a unified sysmlv2 guard [ROOT] that runs all six ported guards and exits non-zero on any violation (replaces the conda run python validate_*.py calls). Parity harness vs the python guards; doc-sync CLAUDE.md sec5 + usage.md to the Rust guard path. cargo test + clippy --workspace --all-targets -D warnings green."; }
        part portGuardKeystoneDoDR1 : TestResult { :>> id = "6c5825d6-0406-4031-bb37-901449de0c77"; :>> outcome = VerdictKind::pass; :>> judgedAgainst = "09e0c4d"; :>> judgedAt = "2026-06-20"; :>> judgedBy = "claudeOpus"; }
        action retireQueryPy;
        verification retireQueryPyDoD : Test { :>> id = "3c2d9315-2693-4c6c-a874-5797de26e358"; :>> method = VerificationMethod::inspect; :>> procedureText = "M4 (D0074, closes issue012): retire query.py + the python guard scripts now that all algorithmic views (M2.2) + forward guards (M3) are Rust with proven parity. Remove/redirect the python tools; retire parity_check (its job is done); update CLAUDE.md sec1/sec5 + usage.md so the Rust path (sysmlv2 validate + sysmlv2 guard) is the SOLE gate. Verify orient done-count undercount (issue012) is closed. Depends on portGuardKeystone (the unified guard runner)."; }
        part retireQueryPyDoDR1 : TestResult { :>> id = "7c33675a-d5e6-497c-a993-bde6d859885c"; :>> outcome = VerdictKind::pass; :>> judgedAgainst = "0d60d03"; :>> judgedAt = "2026-06-20"; :>> judgedBy = "claudeOpus"; }
        first portGuardsCoverage then portGuardsCeremonyCharter;
        first portGuardsCeremonyCharter then portGuardKeystone;
        first portGuardKeystone then retireQueryPy;
        action issueResolveModel;
        verification issueResolveModelDoD : Test { :>> id = "1f99d709-f310-421f-bf33-6b55a8661be1"; :>> method = VerificationMethod::test; :>> procedureText = "IRL-a (D0077): add the #Resolves typed edge to frozen schema/core (relationships.sysml; §2.5 sign-off via D0077) + teach the Rust view engine to recognize 'resolves' as a KNOWN_EDGE (parse #Resolves dependency from <action|Decision> to <issueNNN>). Verify: kernel validate_schema + validate_instances green; rust validate clean; a view traversing #Resolves returns the edge; clippy --workspace -D warnings + cargo test green."; }
        part issueResolveModelDoDR1 : TestResult { :>> id = "c967db9f-6936-48e5-a9a7-8e6cdaafe1f3"; :>> outcome = VerdictKind::pass; :>> judgedAgainst = "766936d"; :>> judgedAt = "2026-06-20"; :>> judgedBy = "claudeOpus"; }
        action issueOpenView;
        verification issueOpenViewDoD : Test { :>> id = "d7dec749-6d2b-491f-bf33-6b55aec6e5a1"; :>> method = VerificationMethod::test; :>> procedureText = "IRL-b (D0077): Rust open-issues view — an Issue is RESOLVED iff a #Resolves resolver is complete (action done via the orient done-set OR Decision status=accepted), else OPEN. 'sysmlv2 open-issues' lists the OPEN issues + each resolver (or 'untriaged'); add an open_issues field (count + names) to 'sysmlv2 orient' output. Unit tests for the resolved/open compute; clippy -D warnings + cargo test green."; }
        part issueOpenViewDoDR1 : TestResult { :>> id = "c9a091cf-320f-4942-96e1-128990e1a99a"; :>> outcome = VerdictKind::pass; :>> judgedAgainst = "a29f76f"; :>> judgedAt = "2026-06-20"; :>> judgedBy = "claudeOpus"; }
        action issueGuard;
        verification issueGuardDoD : Test { :>> id = "0a8df7ec-f56f-412c-b3c6-21c535885038"; :>> method = VerificationMethod::test; :>> procedureText = "IRL-c (D0077/D0047): build 'sysmlv2 guard issues' — every Issue must carry a #Resolves edge (untriaged = violation) — added to guards::run_one so it is runnable. VERIFY it flags the untriaged set. ENFORCEMENT (hook wiring on .tracking/issues.sysml + inclusion in the 'guard all' GUARD_NAMES set) is DEFERRED to IRL-d, turned on once backfill triages the existing issues — enforcing before triage would block every commit (chicken-and-egg). clippy -D warnings + cargo test green."; }
        part issueGuardDoDR1 : TestResult { :>> id = "7e0de2ae-262b-410c-ae6e-f4feb8cdfb08"; :>> outcome = VerdictKind::pass; :>> judgedAgainst = "0cc6968"; :>> judgedAt = "2026-06-20"; :>> judgedBy = "claudeOpus"; }
        action issueBackfill;
        verification issueBackfillDoD : Test { :>> id = "42511a28-8e8b-4230-b3c6-21c53ab7c64c"; :>> method = VerificationMethod::inspect; :>> procedureText = "IRL-d (D0077/D0067 migration): add #Resolves edges to ALL existing issues — resolved-by-work -> their done action; resolved-by-design -> the Decision; OPEN ones (014, 025, + audit every issue) -> a new OPEN resolving action OR a wontfix Decision. Gated migration: committed reasoning, dry-run reconcile (every issue has >=1 #Resolves; the computed OPEN set matches the audit), never fabricate. THEN turn on enforcement (IRL-c guard): wire 'sysmlv2 guard issues' into the pre-commit hook + add 'issues' to GUARD_NAMES. 'sysmlv2 guard issues' green; 'sysmlv2 open-issues' shows the true open set; the secretly-open issues become tracked work."; }
        part issueBackfillDoDR1 : TestResult { :>> id = "2aa9ede2-95c2-45fa-a2a9-e5f4dd278a06"; :>> outcome = VerdictKind::pass; :>> judgedAgainst = "3d3da35"; :>> judgedAt = "2026-06-20"; :>> judgedBy = "claudeOpus"; }
        action issueResolutionSkill;
        verification issueResolutionSkillDoD : Test { :>> id = "555fd538-566f-4e7c-b3c6-21c53fe804c4"; :>> method = VerificationMethod::inspect; :>> procedureText = "IRL-e (D0077/D0059): an issue-resolution PROCESS def (.engine/processes/issue-resolution.sysml) + deploying SKILL — record issue -> link #Resolves to a resolving action (create one if none) or a wontfix/by-design Decision -> resolution computes when the resolver completes. Co-commit a #ProspectiveChange-marked Decision (D0070 keystone) with the process-def. doc-sync CLAUDE.md + usage. validate green."; }
        part issueResolutionSkillDoDR1 : TestResult { :>> id = "2070b655-8155-4466-a49f-f74892640c4a"; :>> outcome = VerdictKind::pass; :>> judgedAgainst = "9f7d0ec"; :>> judgedAt = "2026-06-20"; :>> judgedBy = "claudeOpus"; }
        first issueResolveModel then issueOpenView;
        first issueOpenView then issueGuard;
        first issueGuard then issueBackfill;
        first issueBackfill then issueResolutionSkill;
        action suspectDiagnostics;
        verification suspectDiagnosticsDoD : Test { :>> id = "23661ec7-50e4-43b5-8939-c2b21a93d2c7"; :>> method = VerificationMethod::test; :>> procedureText = "Resolves issue014. Add sysmlv2 orient/suspect diagnostics: an --explain / log-level flag printing per-suspect-task WHY (which manifest path drifted, at which commit, vs the task verified-at commit). Refine .engine/deliverable-manifest.txt to PER-TASK source paths so a lexer task flags only on parser/lexer source (not any Rust change) — stops the coarse over-flagging. THEN re-verify the genuinely-stale deliverable tasks at HEAD (cargo test + clippy, append fresh TestResults) to clear them. clippy --workspace -D warnings + cargo test green; orient --explain shows accurate per-task drift."; }
        part suspectDiagnosticsDoDR1 : TestResult { :>> id = "8dcd1a03-4a19-4487-a888-020401c8e5e5"; :>> outcome = VerdictKind::pass; :>> judgedAgainst = "447effd"; :>> judgedAt = "2026-06-20"; :>> judgedBy = "claudeOpus"; }
        action readdDroppedViews;
        verification readdDroppedViewsDoD : Test { :>> id = "9d9d03e4-f3ce-4c6d-8939-c2b22059bc7b"; :>> method = VerificationMethod::test; :>> procedureText = "Resolves issue025. Re-add the seven query.py subcommands dropped at M4 (workflows, trace, trace-need, item, outstanding, downstream, viewpoints-listing) as TOML views or Rust subcommands where each fits (trace/downstream = traverse; item/outstanding = select; workflows = a small Rust subcommand over the workflow action defs). Each verified vs its intended output; clippy -D warnings + cargo test green."; }
        part readdDroppedViewsDoDR1 : TestResult { :>> id = "aeb497a1-5087-4f1a-8386-64fc1696258e"; :>> outcome = VerdictKind::pass; :>> judgedAgainst = "bef381a"; :>> judgedAt = "2026-06-20"; :>> judgedBy = "claudeOpus"; }
        action safeTrackingFallback;
        verification safeTrackingFallbackDoD : Test { :>> id = "f008127b-7d6e-4d77-b265-6a2b524e0219"; :>> method = VerificationMethod::test; :>> procedureText = "Resolves issue026. Fix the pre-commit hook: when the rust binary is missing, do NOT fall back to kernel validate_tracking (it per-file false-fails the 31 #CharteredBy charter-bearing tracking files + baselines — cross-package refs to .engine Decisions/schema it cannot resolve); instead SKIP .tracking validation with a clear warning (matching guard_run), since the rust authority D0048 is the sole correct validator. Verify: hook with binary present still validates; the unsafe kernel fallback is removed."; }
        part safeTrackingFallbackDoDR1 : TestResult { :>> id = "1324c886-157c-4610-82aa-267238527ab0"; :>> outcome = VerdictKind::pass; :>> judgedAgainst = "f361630"; :>> judgedAt = "2026-06-20"; :>> judgedBy = "claudeOpus"; }
        action assuranceCoverage;
        verification assuranceCoverageDoD : Test { :>> id = "db34e98e-48a8-4953-a049-1326c59003fd"; :>> method = VerificationMethod::test; :>> procedureText = "D0079 (C): sysmlv2 coverage computes per-element assurance coverage for each Need / SystemRequirement / accepted Decision from verifiers (strongest-first): explicit-test (verify edge -> Test; 0 today, none authored), accept-event (Decision attestation pass, D0066), charter-dod (a #CharteredBy work item done+non-stale via the orient done/suspect authorities + the Story->action name bridge), satisfy (Need transitive through a covered requirement). State covered/suspect/uncovered + basis; emits per-type summary + the flat gap set; honest by construction (never fabricates coverage). Reuses orient done/suspect; no stored verdict. Implements computed-state.md coverageState/satisfaction/coverageGaps. VERIFY (live): Decisions 76/76 covered (accept-event); SystemRequirements 14/14 + Needs 14/14 uncovered = the real gap (zero verify edges, zero charter to requirements) -> 28 gaps. clippy --workspace -D warnings + cargo test (32 lib) + rust validate green."; }
        part assuranceCoverageDoDR1 : TestResult { :>> id = "e27e1392-eb21-4a7e-b9e0-d775970b205a"; :>> outcome = VerdictKind::pass; :>> judgedAgainst = "c813eae"; :>> judgedAt = "2026-06-20"; :>> judgedBy = "claudeOpus"; }
        action critiqueMechanism;
        verification critiqueMechanismDoD : Test { :>> id = "0bca4a24-8048-4c73-a049-1326cb0d2b85"; :>> method = VerificationMethod::inspect; :>> procedureText = "D0080 (frozen-schema, keystone): antagonistic critique = a LENS-TAGGED VERIFICATION. schema/core: VerificationMethod::critique + enums Severity {Critical/High/Medium/Low}, CriticKind {aiModel/human/tool}, CritiqueLens {completeness/correctness/ambiguity/testability/feasibility/consistency/necessity}; lens/critiquedBy/severity[0..1] on Test; severity[0..1] on Issue (additive — existing instances parse). New EngineElementCritique process-def (.engine/processes/element-critique.sysml: scope->critique->finding->disposition->staleness; DISTINCT from the engine-level architectural-critique) + element-critique deploying skill (D0059) + skills-registry entry. D0080 #ProspectiveChange-marked, human-accepted (schema-freeze), co-committed with the process-def (D0070 keystone). VERIFY: kernel validate_schema 14/14 + validate_instances 91/91 green; rust validate 79 clean; guard all (incl process-change) PASS; sysmlv2 coverage ingests d0080 (covered). doc-sync: CLAUDE.md method list + usage.md (coverage/critique rows, guard count six->seven+issues, add-task method)."; }
        part critiqueMechanismDoDR1 : TestResult { :>> id = "1f0663c0-e8da-4810-890e-8ab53bff4eb4"; :>> outcome = VerdictKind::pass; :>> judgedAgainst = "3c93a66"; :>> judgedAt = "2026-06-20"; :>> judgedBy = "claudeOpus"; }
        action critiqueCoverage;
        verification critiqueCoverageDoD : Test { :>> id = "07387778-86e9-4ba7-a049-1326d1378fe1"; :>> method = VerificationMethod::test; :>> procedureText = "D0079/D0080: critique-coverage analysis — `sysmlv2 critique-coverage` computes, per element (Need/SystemRequirement/accepted Decision) x required lens, whether an INDEPENDENT method=critique verification (#Verify-linked, result judgedBy != element author) exists; per-type summary + gap set. Required-lens policy = Core-3 (human-accepted): Need/Requirement = completeness/correctness/testability; Decision = completeness/correctness/feasibility. `sysmlv2 guard critique` fails any element missing a required lens — RUNNABLE via run_one but NOT yet in the enforced GUARD_NAMES (hard pre-commit gate is the accepted target; wiring waits for a genuine critique pass, else 0 critiques block all commits). VERIFY (live): 105 elements all uncovered (0 critiques) -> guard critique FAIL 105; guard all PASS (critique not enforced); clippy --workspace -D warnings + cargo test (33 lib, +critique_coverage_requires_independent_lens_critiques) + rust validate green. doc-sync: usage.md critique-coverage row. STALENESS (reuse suspect) deferred to assuranceReadiness."; }
        part critiqueCoverageDoDR1 : TestResult { :>> id = "4546829a-5e1b-4c25-880f-6a1fa22b189b"; :>> outcome = VerdictKind::pass; :>> judgedAgainst = "1f70e34"; :>> judgedAt = "2026-06-20"; :>> judgedBy = "claudeOpus"; }
        action assuranceReadiness;
        verification assuranceReadinessDoD : Test { :>> id = "0333798b-603b-4aaf-a049-1326d740c551"; :>> method = VerificationMethod::test; :>> procedureText = "D0079 (c): composite assurance-readiness gate — `sysmlv2 assured` (+ runnable `guard assured`) computes one verdict: READY iff coverage complete (compute_coverage) AND critique complete (compute_critique_coverage) AND no stale verification (orient suspect) AND every >=Medium finding dispositioned (no open >=Medium finding Issue) AND no Critical finding open AND invariants green (guards::run_all). NOT-READY lists exact per-category blockers (count + sample). guard assured runnable via run_one, NOT in enforced GUARD_NAMES (a readiness verdict, not a per-commit lock). VERIFY (live): READY=false with blockers coverage_gaps=28, critique_gaps=105, stale_verifications=5, undispositioned=0, unfixed_critical=0, invariant_violations=0 -> honest composite. clippy --workspace -D warnings + cargo test + rust validate + guard all green. doc-sync usage.md."; }
        part assuranceReadinessDoDR1 : TestResult { :>> id = "e8863247-121c-4047-8d46-7e9d2df45709"; :>> outcome = VerdictKind::pass; :>> judgedAgainst = "504ef71"; :>> judgedAt = "2026-06-20"; :>> judgedBy = "claudeOpus"; }
        first modelIngestRequirements then assuranceCoverage;
        first assuranceCoverage then critiqueMechanism;
        first critiqueMechanism then critiqueCoverage;
        first critiqueCoverage then assuranceReadiness;
        first assuranceReadiness then charterTimeAssuranceGates;
        first charterTimeAssuranceGates then threeTierCoverage;
        first threeTierCoverage then orientPerf;
        first orientPerf then faststartTargetRevision;
        first faststartTargetRevision then parserPackageGuard;
        first parserPackageGuard then critiqueLoadBearingBatch1;
        first critiqueLoadBearingBatch1 then loadBearingReport;
        first loadBearingReport then elementContentSuspicion;
        first elementContentSuspicion then critiqueLoadBearingBatch2;
        first critiqueLoadBearingBatch2 then critiqueLoadBearingBatch3;
        first critiqueLoadBearingBatch3 then diagramView;
        first diagramView then diagramRenderFix;
        action diagramRenderFix;
        verification diagramRenderFixDoD : Test { :>> id = "af2806b3-152d-4e6f-a890-12345678901b"; :>> method = VerificationMethod::test; :>> procedureText = "Resolves issue028 (diagram rendered blank). Fix two defects in `sysmlv2 diagram`: (1) INLINE cytoscape.js (vendored sysmlv2-cli/assets/cytoscape.min.js via include_str!) instead of a CDN <script src> — truly self-contained + offline; (2) constructor uses a fast grid layout + cose runs only on the VISIBLE subset (cy.elements(':visible').layout) instead of cose over all ~2500 nodes (which froze the browser). VERIFY: emitted HTML has 0 CDN refs + inlined lib + ':visible').layout + no unreplaced placeholders; regression test diagram_is_self_contained_and_layouts_visible_only; ~896KB self-contained HTML, 2519 nodes/275 edges; clippy --workspace -D warnings + cargo test (33 lib) + rust validate + guard all (9) green. (Browser render-confirmation is the human's; structural fixes machine-verified.)"; }
        part diagramRenderFixDoDR1 : TestResult { :>> id = "b03917c4-263e-4f70-b901-23456789012c"; :>> outcome = VerdictKind::pass; :>> judgedAgainst = "bd7dd07"; :>> judgedAt = "2026-06-21"; :>> judgedBy = "claudeOpus"; }
        action diagramView;
        verification diagramViewDoD : Test { :>> id = "8e17fa29-1425-46d7-e678-90123456789a"; :>> method = VerificationMethod::test; :>> procedureText = "D0085: comprehensive traceability diagram as a computed interactive-HTML #View. `sysmlv2 diagram` (view.rs diagram_html + main.rs cmd_diagram): whole Model -> typed nodes + authored metadata + every typed edge -> self-contained cytoscape HTML with type/edge filters, search, click-to-focus, fit; Test/TestResult default-off; dangling edges dropped. Process-def .engine/processes/diagram.sysml (regenerate-don't-commit) + diagram skill + skills-registry entry + 'diagram' viewpoint; /*.html git-ignored. D0085 #ProspectiveChange (keystone co-commit) + dogfood-critiqued. VERIFY (live): 2485 nodes / 270 edges, valid HTML (~515KB), zero dangling, cytoscape + controls present; clippy --workspace -D warnings + cargo test (32 lib) + rust validate + kernel validate_instances (97/97) + guard all (9) green. doc-sync usage.md."; }
        part diagramViewDoDR1 : TestResult { :>> id = "9f28fb3a-2536-47e8-f789-0123456789ab"; :>> outcome = VerdictKind::pass; :>> judgedAgainst = "e39e035"; :>> judgedAt = "2026-06-21"; :>> judgedBy = "claudeOpus"; }
        action critiqueLoadBearingBatch3;
        verification critiqueLoadBearingBatch3DoD : Test { :>> id = "6cf5e807-9203-44b5-d456-7e8f90123456"; :>> method = VerificationMethod::inspect; :>> procedureText = "Element-critique batch 3 (2 decisions): D0077 (issue-resolution loop) + D0068 (process-governance charter-time freeze). 6 Core-3 critiques, independent critic claudeOpus, #Verify-linked. VERIFY: critique-coverage covers d0077 + d0068 (3/3 lenses); both SURVIVE; D0077 clean (the supersede-reopens-issue behavior is elegant); D0068 carries honest superseded_in_part-by-D0070 notes (its supersede-chain mechanism + advisory class + increment-2 .tracking edge were refined by D0070 — core charter-time freeze stands) — matching the report flag. No >=Medium defect. rust validate + guard all (9) green; uncritiqued 71 -> 69."; }
        part critiqueLoadBearingBatch3DoDR1 : TestResult { :>> id = "7d06f918-0314-45c6-e567-8f9012345678"; :>> outcome = VerdictKind::pass; :>> judgedAgainst = "1a2ea0a"; :>> judgedAt = "2026-06-21"; :>> judgedBy = "claudeOpus"; }
        action critiqueLoadBearingBatch2;
        verification critiqueLoadBearingBatch2DoD : Test { :>> id = "4ad3c695-7081-4293-c234-5c6d7e8f9012"; :>> method = VerificationMethod::inspect; :>> procedureText = "Element-critique batch 2 (small-batch cadence, 2 decisions): D0018 (model-only state) + D0070 (process-change keystone). 6 genuine Core-3 critiques by an INDEPENDENT critic (claudeOpus != author wweatherholtz), #Verify-linked. VERIFY: critique-coverage covers d0018 + d0070 (3/3 lenses); both SURVIVE with honest notes (D0018 text cites retired query.py — matches the report's references_retired flag; D0070's git-derivation guarantee is hook-conditional — a general guard property, CI would harden). No >=Medium defect. rust validate + guard all (9) green; uncritiqued worklist 73 -> 71."; }
        part critiqueLoadBearingBatch2DoDR1 : TestResult { :>> id = "5be4d706-8192-43a4-d345-6d7e8f901234"; :>> outcome = VerdictKind::pass; :>> judgedAgainst = "4c1c020"; :>> judgedAt = "2026-06-21"; :>> judgedBy = "claudeOpus"; }
        action elementContentSuspicion;
        verification elementContentSuspicionDoD : Test { :>> id = "28c1a473-5e6f-4071-c012-3a4b5c6d7e8f"; :>> method = VerificationMethod::test; :>> procedureText = "D0084 (D0005 disposition, option b): targeted element-content suspicion. view.rs compute_stale_verifications (build_element_files + semantic_field + extract_field + latest_result, reusing orient::batch_cat_blobs) -> a verify/critique of a Need/Requirement/accepted-Decision goes suspect when its primary semantic field (statement/decision) changed since the verification's latest result commit AND it existed then; direct_verifiers explicit-test suspect = element-stale, charter-dod suspect = task-suspect (un-conflated); compute_critique_coverage drops a stale critique's lens. Align computed-state.md rule 2 to the two-tier proxy. VERIFY (live): sr11Verify flagged stale (statement amended after its commit) -> sr11 verified->addressed -> re-verified at HEAD (R2) -> verified again; d0081-83 NOT falsely flagged (existed-then guard); coverage 14/14+14/14 verified + 80 attested; clippy --workspace -D warnings + cargo test (32 lib) + rust validate + guard all (9) green. D0084 dogfood-critiqued."; }
        part elementContentSuspicionDoDR1 : TestResult { :>> id = "39d2b584-6f70-4182-d123-4b5c6d7e8f90"; :>> outcome = VerdictKind::pass; :>> judgedAgainst = "96584de"; :>> judgedAt = "2026-06-21"; :>> judgedBy = "claudeOpus"; }
        action loadBearingReport;
        verification loadBearingReportDoD : Test { :>> id = "06af9261-3d4e-4f50-b890-1234253647ac"; :>> method = VerificationMethod::test; :>> procedureText = "Formalize the load-bearing-decisions report (no more ad-hoc python): `sysmlv2 decisions` ranks accepted Decisions by charters-to x2 + cross-citations and flags uncritiqued / references_retired / superseded_in_part (zombies out of scope). New view.rs decisions_report + main.rs cmd_decisions. VERIFY (live): top = d0066(65)/d0070(27)/d0077(23)/d0048(22)..., flags populated (retired:query.py/parity_check; superseded_in_part heuristic); a find_decision_name `?`-returns-None bug (first comment line aborted parsing -> citations all 0) caught + fixed; clippy --workspace -D warnings + cargo test (32 lib, +decision_name_and_mentions_helpers) + rust validate green. doc-sync usage.md."; }
        part loadBearingReportDoDR1 : TestResult { :>> id = "17b0a372-4e5f-4061-c901-23425364758d"; :>> outcome = VerdictKind::pass; :>> judgedAgainst = "2033dd7"; :>> judgedAt = "2026-06-21"; :>> judgedBy = "claudeOpus"; }
        action critiqueLoadBearingBatch1;
        verification critiqueLoadBearingBatch1DoD : Test { :>> id = "e4bf9506-1c2d-4e3f-a678-90213425364a"; :>> method = VerificationMethod::inspect; :>> procedureText = "Deploy the element-critique process (D0080) on the first batch of load-bearing decisions: D0001 (text-is-truth), D0005 (computed-state), D0048 (Rust authority), D0079 (assurance doctrine). 12 genuine Core-3 critiques (completeness/correctness/feasibility) by an INDEPENDENT critic (claudeOpus != author wweatherholtz), #Verify-linked. VERIFY: critique-coverage shows all 4 covered (3/3 lenses each); all survived (outcome=pass) with sharpening NOTES surfaced (sharpest: D0005's material-change mechanism is a proxy vs the contract's field-hashing — doc-precision, surfaced for human disposition); rust validate + guard all (9) green. Load-bearing ranking computed from charter + citation counts."; }
        part critiqueLoadBearingBatch1DoDR1 : TestResult { :>> id = "f5c0a617-2d3e-4f40-b789-013425364a5b"; :>> outcome = VerdictKind::pass; :>> judgedAgainst = "13cafbc"; :>> judgedAt = "2026-06-21"; :>> judgedBy = "claudeOpus"; }
        action parserPackageGuard;
        verification parserPackageGuardDoD : Test { :>> id = "c29e7384-9fa0-4b12-c456-708192031425"; :>> method = VerificationMethod::test; :>> procedureText = "Resolves issue027 (D0047): the Rust parser silently dropped items after the top-level package. Fix parse() to require the token stream be exhausted after parse_package — error (ParseError::Expected 'end of file; one package per file') on any trailing/out-of-package item. The parser IS the guard: every `sysmlv2 validate`/`check`/`orient` parses, so it's enforced everywhere incl pre-commit. VERIFY: a stray-brace file (item after package) now FAILS `sysmlv2 check` with a clear message (was silently clean); regression test content_after_package_is_rejected; all 88 real .tracking + .engine files still parse clean (no false positives); clippy --workspace -D warnings + cargo test (31 lib) green."; }
        part parserPackageGuardDoDR1 : TestResult { :>> id = "d3af8495-a0b1-4c23-d567-819203142536"; :>> outcome = VerdictKind::pass; :>> judgedAgainst = "492c5e6"; :>> judgedAt = "2026-06-21"; :>> judgedBy = "claudeOpus"; }
        action faststartTargetRevision;
        verification faststartTargetRevisionDoD : Test { :>> id = "a07c5162-7d8e-4f90-b234-5e6f70819203"; :>> method = VerificationMethod::inspect; :>> procedureText = "D0083: revise the FastStart target after orientPerf — split the conflated <500ms into parse/validate <500ms (met ~110ms) + full orient-with-suspicion <1.5s (met ~0.85s). Amend n11FastStart (business.sysml) + sr11FastStart (requirements.sysml) statements; author sr11Verify (.tracking/verification, method=test) citing live measurements -> sr11 VERIFIED, n11 verified transitively. D0083 #critiqued (dogfood). VERIFY: coverage = 14/14 needs verified, 14/14 reqs verified, 80 decisions attested, ZERO gaps; attestation-coverage missing=[]; guard all (9) PASS; rust validate + kernel validate_instances green."; }
        part faststartTargetRevisionDoDR1 : TestResult { :>> id = "b18d6273-8e9f-4a01-c345-6f7081920314"; :>> outcome = VerdictKind::pass; :>> judgedAgainst = "324ab15"; :>> judgedAt = "2026-06-21"; :>> judgedBy = "claudeOpus"; }
        action orientPerf;
        verification orientPerfDoD : Test { :>> id = "9e5a3f4c-6b7d-4e8f-a012-3c4d5e6f7081"; :>> method = VerificationMethod::test; :>> procedureText = "orientPerf (serves sr11FastStart): cut `orient` wall-clock by collapsing per-task git spawns into batched git. orient.rs: valid_commits (one `git cat-file --batch-check` for ALL passing-result SHAs) + batch_cat_blobs (one `git cat-file --batch` for ALL historical DoD blobs, replacing per-(task,dep) ls-tree+show scans) + criterion_suspects (single batched blob fetch) + apply_deliverable_suspicion batched to one `git diff` per DISTINCT verified-commit. VERIFY: orient wall-clock 13.6s -> ~0.9s (>14x) on the live repo; suspect/ready/done outputs unchanged; clippy --workspace -D warnings + cargo test (31 lib) + rust validate green."; }
        part orientPerfDoDR1 : TestResult { :>> id = "af6b4051-7c8e-4f90-b123-4d5e6f708192"; :>> outcome = VerdictKind::pass; :>> judgedAgainst = "2a20503"; :>> judgedAt = "2026-06-21"; :>> judgedBy = "claudeOpus"; }
        action threeTierCoverage;
        verification threeTierCoverageDoD : Test { :>> id = "7c3e1d2a-4b5c-4d6e-8f90-1a2b3c4d5e6f"; :>> method = VerificationMethod::test; :>> procedureText = "D0082: coverage reports three tiers (verified > attested > addressed > uncovered) instead of flat 'covered'. view.rs tier_of/tier_for_kind/is_covered_tier; explicit-test completeness from the Test's own R1 result (not the action done-set) + method=critique excluded; needs verified transitively iff their requirement verified; coverage view emits tier + per-tier summary; gate = verified|attested. PLUS objective verification authored for 13/14 requirements (real re-runnable evidence: clippy/cargo test/build.rs/validate/trace-need/timing) -> verified; needs verified transitively; sr11FastStart a measured GAP (orient ~13.6s vs <500ms) -> tracked, not faked. VERIFY (live): coverage = SR 13 verified/1 uncovered, Need 13 verified/1 uncovered, Decision 78 attested; clippy -D warnings + cargo test (31 lib, coverage_tiers_and_transitive_verification) + rust validate green; D0082 critiqued (dogfood)."; }
        part threeTierCoverageDoDR1 : TestResult { :>> id = "8d4f2e3b-5c6d-4e7f-9a01-2b3c4d5e6f70"; :>> outcome = VerdictKind::pass; :>> judgedAgainst = "0941e97"; :>> judgedAt = "2026-06-21"; :>> judgedBy = "claudeOpus"; }
        action charterTimeAssuranceGates;
        verification charterTimeAssuranceGatesDoD : Test { :>> id = "5e0a1b2c-3d4e-4f50-9617-2839a4b5c6d7"; :>> method = VerificationMethod::test; :>> procedureText = "D0081: scope the assurance gates by charter-time freeze (D0068) — coverage(D0079)/critique(D0080) bind only elements created after the governing decision's intro commit; grandfather pre-decision work. govern.rs grandfathered_under/decision_intro_commit/names_present_at; view.rs governed scoping of critique_gaps+readiness + governed flags + assured blocking/advisory split + recursion break; guards.rs GUARD_NAMES 7->9 (critique+assured ENFORCED). Dogfood: d0081 critiqued (3 lenses, independent). VERIFY: guard all (9) PASS, d0081 governed+covered, clippy -D warnings + cargo test + rust validate green."; }
        part charterTimeAssuranceGatesDoDR1 : TestResult { :>> id = "6f1b2c3d-4e5f-4061-a728-3940b5c6d7e8"; :>> outcome = VerdictKind::pass; :>> judgedAgainst = "5b90663"; :>> judgedAt = "2026-06-20"; :>> judgedBy = "claudeOpus"; }
        action modelIngestRequirements;
        verification modelIngestRequirementsDoD : Test { :>> id = "bba06d6e-1d69-451e-9355-12a3ee3efb22"; :>> method = VerificationMethod::test; :>> procedureText = "Prerequisite for assurance-coverage + critique (D0079): teach the Rust view Model to ingest requirement/need USAGES (requirement X : T) as items — parser.rs emits Item::Part with type_name for a requirement usage (previously skipped; only requirement def -> TypeDef). Verify: the Model sees 14 Need + 14 SystemRequirement items (was 0); rust validate clean; cargo test + clippy --workspace -D warnings green."; }
        part modelIngestRequirementsDoDR1 : TestResult { :>> id = "ee9864fd-8758-4510-a128-1b73175784fc"; :>> outcome = VerdictKind::pass; :>> judgedAgainst = "8b7bb0b"; :>> judgedAt = "2026-06-20"; :>> judgedBy = "claudeOpus"; }

        // ── load-bearing critique campaign batch-1 ACT dispositions (resolve issue029/030/031) ──
        action frictionMetric; // D0054 finding (issue029): make authoring-friction a VERIFIABLE first-class requirement.
        verification frictionMetricDoD : Test { :>> id = "a1c70029-0029-4029-9029-516273840001"; :>> method = VerificationMethod::analyze; :>> procedureText = "D0054 completeness finding (issue029): adoption-friction is a first-class requirement with no verification. Define + compute an authoring-friction metric — e.g. steps/keystrokes/seconds to record a representative fact via the write API (append-result/add-task/apply-review) vs a spreadsheet baseline — and surface it (a report card and/or a SystemRequirement with a verify edge), so 'the write path beats a spreadsheet' becomes measurable + regression-checkable. VERIFY: a computed friction metric exists + is reported; the first-class requirement gains a verification criterion."; }
        part frictionMetricDoDR1 : TestResult { :>> id = "7feefc8b-adf7-4f25-b434-0f3a041ab903"; :>> outcome = VerdictKind::pass; :>> judgedAgainst = "24e12bc"; :>> judgedAt = "2026-06-22"; :>> judgedBy = "claudeOpus"; }

        action critiqueRigorCheck; // D0080 finding (issue030): guard critique QUALITY, not just coverage.
        verification critiqueRigorCheckDoD : Test { :>> id = "a1c70030-0030-4030-9030-516273840002"; :>> method = VerificationMethod::analyze; :>> procedureText = "D0080 completeness finding (issue030): critique coverage is enforced but rigor is not (a shallow SURVIVED counts as a real attack — gameable). Design + implement a second-order critique-quality check: e.g. meta-critique sampling, a rigor heuristic (attack/finding density, length floor is insufficient), or independent re-judgement of a sample, so going-through-the-motions is detectable. VERIFY: a critique-rigor check exists + flags a deliberately shallow critique in a self-test."; }
        part critiqueRigorCheckDoDR1 : TestResult { :>> id = "59eceecb-5f2b-4e11-b434-0f39fd19e363"; :>> outcome = VerdictKind::pass; :>> judgedAgainst = "24e12bc"; :>> judgedAt = "2026-06-22"; :>> judgedBy = "claudeOpus"; }

        action criticIndependenceRule; // D0080 finding (issue031): cognition-distinct independence for high-stakes elements.
        verification criticIndependenceRuleDoD : Test { :>> id = "a1c70031-0031-4031-9031-516273840003"; :>> method = VerificationMethod::analyze; :>> procedureText = "D0080 correctness finding (issue031): independence is identity-distinct (judgedBy != author), not cognition-distinct (aiModel-vs-aiModel shares blind spots). Require a human or tool critic (not only aiModel) for high-stakes elements (Critical-severity targets and/or the most load-bearing decisions), so independence is cognition-distinct where it matters most. VERIFY: a guard/check requires a non-aiModel critic for the high-stakes set; aiModel-only critique of such an element is flagged."; }
        part criticIndependenceRuleDoDR1 : TestResult { :>> id = "cad7891d-5f4f-4485-b434-0f39f6bfe387"; :>> outcome = VerdictKind::pass; :>> judgedAgainst = "24e12bc"; :>> judgedAt = "2026-06-22"; :>> judgedBy = "claudeOpus"; }

        // ── load-bearing critique campaign batch-2 ACT dispositions (resolve issue033/034) ──
        action manifestCoverageGuard; // D0050 finding (issue033): guard deliverable-manifest completeness.
        verification manifestCoverageGuardDoD : Test { :>> id = "a1c70033-0033-4033-9033-516273840004"; :>> method = VerificationMethod::test; :>> procedureText = "D0050 completeness finding (issue033): deliverable-suspicion only guards manifest-listed tasks (a hand-maintained allow-list). Add a check that every deliverable-dependent Rust-verification task is listed in .engine/deliverable-manifest.txt (or flag the unlisted), so the allow-list cannot silently miss a task. VERIFY: the check flags a deliverable-verification task absent from the manifest in a self-test; runs in the guard set."; }
        part manifestCoverageGuardDoDR1 : TestResult { :>> id = "e40fc7fa-59bb-4b32-b79b-37d6648686ae"; :>> outcome = VerdictKind::pass; :>> judgedAgainst = "b577f9c"; :>> judgedAt = "2026-06-21"; :>> judgedBy = "claudeOpus"; }

        action viewpointRendererGuard; // D0056 finding (issue034): guard viewpoint<->renderer correspondence.
        verification viewpointRendererGuardDoD : Test { :>> id = "a1c70034-0034-4034-9034-516273840005"; :>> method = VerificationMethod::test; :>> procedureText = "D0056 completeness finding (issue034): the viewpoint registry is descriptive, not generative — registry entries + bespoke renderers can drift. Add a check that every declared viewpoint has a renderer (a subcommand or TOML view) and every renderer/subcommand has a viewpoint entry (no orphan either way). VERIFY: the check flags a viewpoint with no renderer and a renderer with no viewpoint in a self-test; runs in the guard set."; }
        part viewpointRendererGuardDoDR1 : TestResult { :>> id = "683c78a2-8d02-4f1d-891e-f1baa73c2cef"; :>> outcome = VerdictKind::pass; :>> judgedAgainst = "ff4a54d"; :>> judgedAt = "2026-06-21"; :>> judgedBy = "claudeOpus"; }

        // ── load-bearing critique campaign batch-3 ACT disposition (resolves issue035 + issue036, unified) ──
        action coverageAudits; // D0057 (issue035) + D0059 (issue036): the "which X lacks its required Y" coverage audits.
        verification coverageAuditsDoD : Test { :>> id = "a1c70035-0035-4035-9035-516273840006"; :>> method = VerificationMethod::test; :>> procedureText = "D0057 finding (issue035): no concern-coverage view (which stakeholder concerns lack a serving viewpoint). D0059 finding (issue036): no process<->skill coverage audit (a process lacking a deploying skill is unflagged). Build BOTH as the same 'declared correspondence => coverage audit' pattern (cf. viewpointRendererGuard, manifestCoverageGuard): (a) concern-coverage = surface Viewpoints whose renderer is unbuilt/'(planned)' + concerns with no viewpoint; (b) process-skill = every process-def has a deploying AISkill (own or consuming ceremony skill), flag orphan processes + orphan skills. VERIFY: each audit flags a deliberately-introduced gap (a viewpoint with no renderer; a process with no skill) in a self-test; runs in the guard/view set; green on the current model after any backfill."; }
        part coverageAuditsDoDR1 : TestResult { :>> id = "c78166d8-83d4-4006-8554-e3f0e9b221a6"; :>> outcome = VerdictKind::pass; :>> judgedAgainst = "213e496"; :>> judgedAt = "2026-06-22"; :>> judgedBy = "claudeOpus"; }

        // ── D0090 tracked refinement: full report<->indicator de-dup (the scalar cards source from metric_value) ──
        action reportIndicatorRender; // D0090: reports render the indicator group directly (full de-dup of the scalar cards' inline computation).
        verification reportIndicatorRenderDoD : Test { :>> id = "a1c70090-0090-4090-9090-516273840090"; :>> method = VerificationMethod::test; :>> procedureText = "D0090 incremental refinement: the canonical indicator layer + shared metric_value + report --trend sourcing are built, but the report SCALAR cards still compute their numbers inline (a card also shows a richer breakdown). Refactor so each report renders its concern's INDICATORS (value via metric_value + direction-aware status) for the scalar cards, keeping the structural cards (verdicts/breakdowns/lists) — full de-dup, a metric computed in exactly one place AND declared once as an indicator. VERIFY: report scalar values come from metric_value (no inline pct duplication); reports still show their structural context; clippy + cargo test + guard all green."; }
        part reportIndicatorRenderDoDR1 : TestResult { :>> id = "4ecb8395-c9bd-4544-8ddc-b43249f81240"; :>> outcome = VerdictKind::pass; :>> judgedAgainst = "9919a24"; :>> judgedAt = "2026-06-22"; :>> judgedBy = "claudeOpus"; }

        // ── D0091 critique ACT dispositions (resolves issue037 + issue038, unified) — DONE in Sprint 94/95 ──
        action indicatorBankGuardrail; // D0091 findings: latest=live (calculated, not stale) + drift guardrail (live authoritative over the bank).
        verification indicatorBankGuardrailDoD : Test { :>> id = "a1c70091-0091-4091-9091-516273840091"; :>> method = VerificationMethod::test; :>> procedureText = "D0091 completeness finding (issue037): bank-first 'latest' goes stale vs live. D0091 correctness finding (issue038): snapshotting computed metrics is a compute-don't-store exception with no guardrail. FIX (indicators view): for computed indicators `latest` is CALCULATED as the LIVE recompute (metric_value now) — authoritative, never stale; the bank stores only (value, timestamp), no 'latest' label; `live`/`banked_latest`/`drift` fields expose the live-vs-last-snapshot divergence (the bank is historical record, NEVER overrides live); snapshots stored at higher precision so drift flags only real changes. VERIFY: `sysmlv2 indicators` shows live (computed) + banked_latest + drift; coverageIndicator latest=live (not stale); velocity drift detected when live != snapshot; clippy + cargo test + guard all green."; }
        part indicatorBankGuardrailDoDR1 : TestResult { :>> id = "8d7db48d-30eb-4e60-8f8f-77a6d6a3d1dc"; :>> outcome = VerdictKind::pass; :>> judgedAgainst = "55ab7c3"; :>> judgedAt = "2026-06-22"; :>> judgedBy = "claudeOpus"; }

        // ── load-bearing critique campaign batch-4 findings (CANDIDATE resolvers — PENDING human disposition) ──
        action correctionGuardCoverage; // D0047 (issue039): a meta-audit that recurrable-defect Issues carry a resolving guard.
        verification correctionGuardCoverageDoD : Test { :>> id = "a1c70039-0039-4039-9039-516273840039"; :>> method = VerificationMethod::test; :>> procedureText = "D0047 finding (issue039): the corrections-become-guards rule is enforced by vigilance — no meta-audit links a recurrable process-defect Issue to a resolving guard. CANDIDATE resolution (pending ACT): an audit/view that, for each Issue tagged as a recurrable process defect, flags the absence of a resolving guard (a #Resolves to a guard/check), so 'defect => guard' becomes machine-checkable rather than vigilance. VERIFY: the audit flags a deliberately-introduced unresolved process-defect; runs in the guard/view set; green on the current model. (Design open: how a process-defect Issue is marked — to be settled at disposition.)"; }
        part correctionGuardCoverageDoDR1 : TestResult { :>> id = "5bbcb44b-f43a-4ba0-aa0d-cd04bf5d3d60"; :>> outcome = VerdictKind::pass; :>> judgedAgainst = "46f0a5a"; :>> judgedAt = "2026-06-22"; :>> judgedBy = "claudeOpus"; }

        // ── D0092 formalize-disposition-lifecycle milestones ──
        action dispositionSchema; // D0092 m1: DispositionKind enum + optional Test.disposition attr (frozen-core, human-accepted, re-frozen).
        verification dispositionSchemaDoD : Test { :>> id = "a1c70092-0092-4092-9092-516273840092"; :>> method = VerificationMethod::test; :>> procedureText = "D0092 milestone 1 (schema): add `enum def DispositionKind { act; acceptRisk; dismiss; }` (element.sysml) + optional `attribute disposition : DispositionKind[0..1]` to verification def Test (verification.sysml). Frozen-core change, human-accepted (d0092Accept) + re-frozen. VERIFY: kernel validate_schema 15/15; kernel validate_instances 107/107 (d0092 PASS); rust validate clean; guard all PASS (d0092 carries its Core-3 critiques)."; }
        part dispositionSchemaDoDR1 : TestResult { :>> id = "92a3b4c5-1d6e-4f70-d829-516273849592"; :>> outcome = VerdictKind::pass; :>> judgedAgainst = "3126545"; :>> judgedAt = "2026-06-22"; :>> judgedBy = "claudeOpus"; }

        action dispositionWritePath; // D0092 m2: extend apply-review to write a #Dispositions confirmation; computed disposition/undispositioned view; retrofit assured + open-issues.
        verification dispositionWritePathDoD : Test { :>> id = "a1c70093-0093-4093-9093-516273840093"; :>> method = VerificationMethod::test; :>> procedureText = "D0092 milestone 2 (write path + computed): extend `apply-review` to accept act/acceptRisk/dismiss verdicts targeting a finding Issue, writing a method=confirmation disposition Test+TestResult #Dispositions-linked to the finding; add a computed view (which >= Medium findings are dispositioned vs not, reading the typed verdict) and retrofit `assured` (retire the finding_blockers proxy) + open-issues resolution (acceptRisk/dismiss close; act needs its resolver done). VERIFY: apply-review writes a disposition; the view + assured read it; clippy + cargo test + guard all green."; }
        part dispositionWritePathDoDR1 : TestResult { :>> id = "5caf9dc7-3072-4fba-ab34-e23080435fb6"; :>> outcome = VerdictKind::pass; :>> judgedAgainst = "21a3c5f"; :>> judgedAt = "2026-06-22"; :>> judgedBy = "claudeOpus"; }

        action dispositionBackfill; // D0092 m3: backfill the recent prose dispositions (issue035..040) as typed Disposition records (recorded basis; never fabricated).
        verification dispositionBackfillDoD : Test { :>> id = "a1c70094-0094-4094-9094-516273840094"; :>> method = VerificationMethod::test; :>> procedureText = "D0092 milestone 3 (backfill, migration discipline D0067): convert the recent PROSE dispositions (issue035/036 ACT, issue037/038 ACT, issue039/040 ACT) into typed #Dispositions confirmation records with their RECORDED basis (the human's prior attestation date/verdict) — never fabricated; grandfather older ones if basis is absent. VERIFY: each backfilled disposition reconciles to its prose basis (control total: N prose dispositions -> N typed records); the computed undispositioned view agrees with reality; green."; }
        part dispositionBackfillDoDR1 : TestResult { :>> id = "0ea9a520-6c78-4b3e-9089-d93bf0274a9a"; :>> outcome = VerdictKind::pass; :>> judgedAgainst = "d4bb4b0"; :>> judgedAt = "2026-06-22"; :>> judgedBy = "claudeOpus"; }

        action sittingModel; // D0049 (issue040): model the sitting + review->sprints coverage so the human gate's unit is computable.
        verification sittingModelDoD : Test { :>> id = "a1c70040-0040-4040-9040-516273840040"; :>> method = VerificationMethod::test; :>> procedureText = "D0049 finding (issue040): 'sitting' (the unit of the sole human gate) has no model representation; review->sprints coverage is uncomputable. CANDIDATE resolution (pending ACT): record a per-sitting review's coverage as an authored edge (review -> the sprints it attests) + a computed view that surfaces sprints with no covering sitting-review (the human-gate analogue of coverage). VERIFY: the view computes which sprints a given review covers and flags any closed sprint with no covering review; green on the current model. (Design open: Sitting item vs marker-edge — to be settled at disposition.)"; }
        part sittingModelDoDR1 : TestResult { :>> id = "74b0e555-fda2-49fb-a1c9-9e2c9e11313d"; :>> outcome = VerdictKind::pass; :>> judgedAgainst = "fa18c22"; :>> judgedAt = "2026-06-22"; :>> judgedBy = "claudeOpus"; }

        // ── D0093 engine-as-product spin-up UX milestones (introduction prioritized; each a normal sprint) ──
        action engineInit; // D0093: `sysmlv2 init [DIR]` cold start — binary-embedded engine tree + starter .tracking + getting-started.
        verification engineInitDoD : Test { :>> id = "a1c70095-0095-4095-9095-516273840095"; :>> method = VerificationMethod::test; :>> procedureText = "D0093 cold start: `sysmlv2 init [DIR]` scaffolds a NEW project — the reusable engine (.engine schema/processes/skills + the binary's own presence + CLAUDE.md), a STARTER/empty .tracking, and a printed getting-started. Engine tree BINARY-EMBEDDED (include_dir!/include_str!, the cytoscape-vendoring precedent). RESOLVE the engine/instance boundary concretely: the engine's architecture decisions ship as READ-ONLY reference WITHOUT polluting the new project's instance views (decisions/coverage/critique/assured) — a separate reference location or an exclusion marker (the d0093 correctness critique's delegated concern). VERIFY: `sysmlv2 init /tmp/p` produces a fresh project where `sysmlv2 validate` + `guard` are green and `orient` runs with an empty/starter backlog; reference decisions do NOT appear as the new project's own decisions; clippy + cargo test green."; }
        part engineInitDoDR1 : TestResult { :>> id = "12488e51-299f-48c7-91d1-db35bf34b769"; :>> outcome = VerdictKind::pass; :>> judgedAgainst = "10fd40e"; :>> judgedAt = "2026-06-23"; :>> judgedBy = "claudeOpus"; }

        action introductionProcess; // D0093: a guided, project-based onboarding process + deploying skill (the FIRST-VALUE step).
        verification introductionProcessDoD : Test { :>> id = "a1c70096-0096-4096-9096-516273840096"; :>> method = VerificationMethod::test; :>> procedureText = "D0093 first value: add `.engine/processes/introduction.sysml` (a Process with steps: orient the newcomer -> capture the project's FIRST business need -> run the first refine->sprint -> show orient) + a deploying `introduction` AISkill (D0059, registered in skills-registry; named by the process-skill guard). Project-based (learn by doing the first real item), NOT a doc dump. VERIFY: kernel validate_instances PASS (process + skill); process-skill guard PASS (introduction process has its deploying skill); the skill walks a newcomer to first value; doc-sync (CLAUDE.md spin-up section, skills-registry)."; }
        part introductionProcessDoDR1 : TestResult { :>> id = "2d23d5f2-8561-44a6-a5ec-c6efb35b1c16"; :>> outcome = VerdictKind::pass; :>> judgedAgainst = "90b29b8"; :>> judgedAt = "2026-06-23"; :>> judgedBy = "claudeOpus"; }

        action orientDashboard; // D0093: `sysmlv2 orient --html` — the human's recurring oversight dashboard.
        verification orientDashboardDoD : Test { :>> id = "a1c70097-0097-4097-9097-516273840097"; :>> method = VerificationMethod::test; :>> procedureText = "D0093 human home: `sysmlv2 orient --html` emits a self-contained HTML dashboard (status + ready frontier + open findings + assurance readiness) extending the render/report HTML emitter (D0086/D0087) — a computed #View (regenerate-don't-commit), drilling down to the CLI/JSON authority. HTML renders views only (never a second store; the dual-surface invariant). VERIFY: `sysmlv2 orient --html > x.html` is self-contained + opens offline; values match `sysmlv2 orient` JSON; orient viewpoint gains the html renderer (viewpoint-renderer guard PASS); clippy + cargo test + guard all green."; }
        part orientDashboardDoDR1 : TestResult { :>> id = "cac634c0-6c94-499a-a315-6487ee138dea"; :>> outcome = VerdictKind::pass; :>> judgedAgainst = "5a8d9fb"; :>> judgedAt = "2026-06-23"; :>> judgedBy = "claudeOpus"; }

        // ── D0094 interactive console + agent-bridge milestones (built straight through) ──
        action serveReadConsole; // D0094 m1: `sysmlv2 serve` tokio/axum localhost + embedded frontend + the live READ console.
        verification serveReadConsoleDoD : Test { :>> id = "a1c70094-0094-4194-9194-516273840194"; :>> method = VerificationMethod::test; :>> procedureText = "D0094 m1: add `sysmlv2 serve [--port] [ROOT]` — a localhost (127.0.0.1) tokio+axum server + an embedded self-contained frontend (include_str!, the cytoscape precedent) serving the live READ console: recent decisions (context/rationale/alternatives), processes-in-use, test results, the orient dashboard, reports, the model graph, AND a read-only AI<->user INTERACTION-HISTORY view that renders the Claude Code session transcripts (~/.claude/projects/<cwd>/*.jsonl) cross-linked to the commits/decisions they produced (NOT copied into .tracking). SSE keeps it live. ONE truth — read via the existing view computations; no second store. VERIFY: `sysmlv2 serve` binds localhost + serves the console; each view's data matches its CLI/JSON authority; the interaction-history renders + links; clippy + cargo test + guard all green (tokio+axum added to the serve path)."; }
        part serveReadConsoleDoDR1 : TestResult { :>> id = "b60f1602-e5c0-4e71-bb36-2a7e5c215ea3"; :>> outcome = VerdictKind::pass; :>> judgedAgainst = "e33148b"; :>> judgedAt = "2026-06-23"; :>> judgedBy = "claudeOpus"; }

        action serveActions; // D0094 m2: deterministic actions from the console (report/render/disposition via the write API).
        verification serveActionsDoD : Test { :>> id = "a1c70094-0094-4294-9294-516273840294"; :>> method = VerificationMethod::test; :>> procedureText = "D0094 m2: the console performs DETERMINISTIC actions by invoking `sysmlv2` / the write API server-side — instantiate a report, render a view, record a disposition (act/acceptRisk/dismiss via apply-review). No agent yet. ONE truth (writes go through the existing write API + guards). VERIFY: a UI action produces the same result as the CLI equivalent; writes are guard-valid; clippy + cargo test + guard all green."; }
        part serveActionsDoDR1 : TestResult { :>> id = "e7dc0fb7-b792-41e6-b30d-a879649b475a"; :>> outcome = VerdictKind::pass; :>> judgedAgainst = "ec35576"; :>> judgedAt = "2026-06-23"; :>> judgedBy = "claudeOpus"; }

        action serveAgentBridge; // D0094 m3: UI -> headless Claude Code (claude -p stream-json) -> SSE; critique/investigate/draft + review/override.
        verification serveAgentBridgeDoD : Test { :>> id = "a1c70094-0094-4394-9394-516273840394"; :>> method = VerificationMethod::test; :>> procedureText = "D0094 m3 (the agent-bridge): UI actions ('critique this process/test/decision', 'investigate a finding', 'draft a report') spawn Claude Code headless (`claude -p --output-format stream-json --include-partial-messages`, scoped tools, setting_sources=project to load CLAUDE.md, resumable session), STREAMING the agent's work to the UI over SSE (not polling). AUTH: pipe to the LOCALLY-AUTHENTICATED `claude` CLI (the user's subscription/ENTERPRISE session); the server MUST NOT set ANTHROPIC_API_KEY (it overrides the subscription + forces pricier API-rate billing) — D0094. The agent runs under the engine's EXISTING discipline (skills + write API + guards + >=Medium human-disposition); NO new permission policy; the agent NEVER auto-commits (commits/acceptance stay the human's gate, D0016); per-action cost/turn CAP + a concurrency limit; localhost-only. The UI exposes OBVIOUS review/override hooks (see the work, accept/finding/override via apply-review, re-run). Degrades gracefully if the `claude` CLI is absent. VERIFY: a UI 'critique' streams a real headless-agent critique into the console; the result lands as a tracked critique via the write path; cost is metered + capped; no auto-commit; clippy + cargo test + guard all green."; }
        part serveAgentBridgeDoDR1 : TestResult { :>> id = "21098487-e92a-4426-874e-938be07df162"; :>> outcome = VerdictKind::pass; :>> judgedAgainst = "e619ced"; :>> judgedAt = "2026-06-23"; :>> judgedBy = "claudeOpus"; }

        // ── D0094 console DEEPENING (perf + event-driven + generic introspect/act; built in order) ──
        action serveLiveCache; // D0094: content-hash view cache (perf/pre-load) + SSE change-push (event-driven, not polling).
        verification serveLiveCacheDoD : Test { :>> id = "a1c70094-0094-4494-9494-516273840494"; :>> method = VerificationMethod::test; :>> procedureText = "D0094 perf+events: a content FINGERPRINT (path+len+mtime over .tracking + .engine .sysml) drives (a) a per-view JSON cache keyed by fingerprint — recompute a view ONLY when the model changes (kills the per-request ~2s on unchanged data; warms via frontend pre-load); (b) GET /api/events SSE that polls the fingerprint server-side (~1.5s) and pushes `changed` ONLY when it flips, so the UI refetches EVENT-DRIVEN, not on a blind timer (hash unchanged => files unchanged; catches out-of-purview edits). A materialized #View cache (regenerable, section-2.1). Request log also appended to keel-serve.log. VERIFY (live): orient cold ~2s -> warm ~0.1s; /api/events emits hello/ping then `changed` on a file touch; keel-serve.log written; clippy + cargo test + keel validate + guard all green."; }
        part serveLiveCacheDoDR1 : TestResult { :>> id = "82239327-d2a4-4f4e-927c-0014358e07f2"; :>> outcome = VerdictKind::pass; :>> judgedAgainst = "90e6493"; :>> judgedAt = "2026-06-23"; :>> judgedBy = "claudeOpus"; }

        action serveItemIntrospect; // D0094: GET /api/item/:name (attrs + edges + up/down neighbors) + click-to-expand any item.
        verification serveItemIntrospectDoD : Test { :>> id = "a1c70094-0094-4594-9594-516273840594"; :>> method = VerificationMethod::test; :>> procedureText = "D0094 generic introspection: GET /api/item/:name returns an item's full detail uniformly (type + authored attrs + incoming/outgoing typed edges + up/downstream neighbors), computed from the Model (the uniform item/edge substrate — one endpoint for ALL types). Frontend: any item shown anywhere (orient suspect/stale, processes, decisions, findings, the graph) is CLICK-TO-EXPAND into its detail panel. ONE truth (read-only view). VERIFY: /api/item/<id> returns attrs+edges+neighbors for a Decision, a process, an Issue; the console expands any listed item; clippy + cargo test + guard green."; }
        part serveItemIntrospectDoDR1 : TestResult { :>> id = "b3bdd366-a62d-4ab9-bade-117a7ba9d89b"; :>> outcome = VerdictKind::pass; :>> judgedAgainst = "1a8d007"; :>> judgedAt = "2026-06-23"; :>> judgedBy = "claudeOpus"; }

        action serveItemActions; // D0094: per-item action panel — Critique (agent), Add TestResult downstream, Disposition.
        verification serveItemActionsDoD : Test { :>> id = "a1c70094-0094-4694-9694-516273840694"; :>> method = VerificationMethod::test; :>> procedureText = "D0094 generic actions: the expanded item detail (serveItemIntrospect) gains an action panel wiring the write-API verbs to THAT item — Critique (agent-bridge target=item), Add TestResult downstream (append-result on a chosen action/DoD), Disposition (for a finding). Same discipline (write API + guards + >=Medium human-disposition; agent never auto-commits). VERIFY: from an item, a critique streams + lands as a tracked critique; a downstream TestResult is appended via the write path; clippy + cargo test + guard green."; }
        part serveItemActionsDoDR1 : TestResult { :>> id = "51e2f2f1-11d0-4e24-8900-afebc93dc440"; :>> outcome = VerdictKind::pass; :>> judgedAgainst = "7642f1c"; :>> judgedAt = "2026-06-23"; :>> judgedBy = "claudeOpus"; }
        part serveItemActionsDoDR2 : TestResult { :>> id = "cf80c4c5-5420-434a-ad7a-12ae10f7d237"; :>> outcome = VerdictKind::pass; :>> judgedAgainst = "edd7b75"; :>> judgedAt = "2026-06-25"; :>> judgedBy = "claudeOpus"; }
        part serveItemActionsDoDR3 : TestResult { :>> id = "31f71e44-504f-4cde-a3d7-ab8e63543d71"; :>> outcome = VerdictKind::pass; :>> judgedAgainst = "cb5720e"; :>> judgedAt = "2026-07-14"; :>> judgedBy = "claudeOpus"; }
        part serveItemActionsDoDR4 : TestResult { :>> id = "ed6647e7-c81e-4b83-95cc-50eacc2b59de"; :>> outcome = VerdictKind::pass; :>> judgedAgainst = "1f1cd66"; :>> judgedAt = "2026-08-14"; :>> judgedBy = "claudeOpus5"; }
        part serveItemActionsDoDR5 : TestResult { :>> id = "bf657edd-e0e5-44e9-a136-3a965ab49170"; :>> outcome = VerdictKind::pass; :>> judgedAgainst = "3f3340f"; :>> judgedAt = "2026-08-17"; :>> judgedBy = "claudeOpus5"; }
        part serveItemActionsDoDR6 : TestResult { :>> id = "90df1bce-e8fa-4e5f-b1aa-f9c033685757"; :>> outcome = VerdictKind::pass; :>> judgedAgainst = "322b82e"; :>> judgedAt = "2026-08-17"; :>> judgedBy = "claudeOpus5"; }
        part serveItemActionsDoDR7 : TestResult { :>> id = "785b101e-c44b-4fcd-8c01-9f7185b31cd6"; :>> outcome = VerdictKind::pass; :>> judgedAgainst = "c68bf8b"; :>> judgedAt = "2026-08-17"; :>> judgedBy = "claudeOpus5"; }
        part serveItemActionsDoDR8 : TestResult { :>> id = "872fa15d-12df-4394-a36b-2b26addbcb69"; :>> outcome = VerdictKind::pass; :>> judgedAgainst = "c9999aa"; :>> judgedAt = "2026-08-21"; :>> judgedBy = "claudeOpus5"; }
        part serveItemActionsDoDR9 : TestResult { :>> id = "75796f5c-4d1d-4439-bacf-6132dff0ad64"; :>> outcome = VerdictKind::pass; :>> judgedAgainst = "0433ca6"; :>> judgedAt = "2026-08-21"; :>> judgedBy = "claudeFable5"; }
        part serveItemActionsDoDR10 : TestResult { :>> id = "3eb9c916-d925-4592-8f33-3ed597a9b053"; :>> outcome = VerdictKind::pass; :>> judgedAgainst = "2af2ac9"; :>> judgedAt = "2026-08-21"; :>> judgedBy = "claudeFable5"; }
        part serveItemActionsDoDR11 : TestResult { :>> id = "4ea2965c-d7c5-48ab-8a0e-7ccd15a3a283"; :>> outcome = VerdictKind::pass; :>> judgedAgainst = "40988a7"; :>> judgedAt = "2026-08-21"; :>> judgedBy = "claudeFable5"; }
        part serveItemActionsDoDR12 : TestResult { :>> id = "bf2934da-4c8a-45e8-b36c-7e262c9dbbd0"; :>> outcome = VerdictKind::pass; :>> judgedAgainst = "58f54f0"; :>> judgedAt = "2026-08-21"; :>> judgedBy = "claudeFable5"; }
        part serveItemActionsDoDR13 : TestResult { :>> id = "d5e5ef5d-df72-42ff-8887-53760a92e38b"; :>> outcome = VerdictKind::pass; :>> judgedAgainst = "3c9645e"; :>> judgedAt = "2026-08-22"; :>> judgedBy = "claudeFable5"; }

        // ── D0095 deferred rename (its own gated D0067 migration) ──
        action engineRename; // D0095: rename sysmlv2 -> keel (binary/package/docs/scaffold/CLAUDE.md) as a gated bulk migration.
        verification engineRenameDoD : Test { :>> id = "a1c70095-0095-4195-9195-516273840195"; :>> method = VerificationMethod::test; :>> procedureText = "D0095: rename the engine `sysmlv2` -> `keel` across the binary name, the cargo package, all docs, the engineInit embedded scaffold, and CLAUDE.md, as a D0067 expand/migrate/contract bulk migration with reconciled control totals (count of `sysmlv2` references before == references migrated + intentionally-retained), green at every step. 'sysmlv2' (the methodology) stays referenced where it denotes SysML v2 the language; only the PRODUCT name changes. VERIFY: `keel <subcommand>` works; the scaffold + docs say Keel; control totals reconcile; clippy + cargo test + validate + guard all green. (Deferred — chartered as its own sprint, not part of the D0094 arc.)"; }
        part engineRenameDoDR1 : TestResult { :>> id = "3860a987-5bcd-4c80-bf02-8866ac5259fc"; :>> outcome = VerdictKind::pass; :>> judgedAgainst = "98d2c74"; :>> judgedAt = "2026-06-23"; :>> judgedBy = "claudeOpus"; }

        // ── post-D0094 forward items (perf + robustness + coverage; from the console-arc retros) ──
        action assurancePerf; // D0048: kill the per-task git spawn in done_names so the assurance report + guard (a pre-commit gate) are fast.
        verification assurancePerfDoD : Test { :>> id = "a1c70113-0113-4113-9113-516273840113"; :>> method = VerificationMethod::test; :>> procedureText = "D0048 (the Rust toolchain is the FAST kernel-free authority): `report assurance` was ~27s cold, `guard`/`assured` ~15s (and `guard` runs in the pre-commit hook, so this taxes EVERY commit). Profiling pinned it to orient::done_names spawning one `git cat-file` PER task (~N=120 process spawns on Windows). FIX: batch-validate all distinct passing-result SHAs in ONE `git cat-file --batch-check` (the same `valid_commits` helper orient::compute already uses) — identical semantics (empty SHA -> done; else commit-validity, conservative-true on git failure). VERIFY (measured): report assurance 27s->~4.7s, assured 14.9s->~3.6s, guard 15.5s->~3.7s; assured verdict + blocker counts + orient done count BYTE-IDENTICAL before/after; clippy --workspace -D warnings + cargo test (46 lib + all BDD) + keel validate + guard all (13) green."; }
        part assurancePerfDoDR1 : TestResult { :>> id = "5db339ce-f271-4030-8a7f-3707032d6f7c"; :>> outcome = VerdictKind::pass; :>> judgedAgainst = "d9dbba2"; :>> judgedAt = "2026-06-23"; :>> judgedBy = "claudeOpus"; }

        action serveAgentCancel; // D0094: process-TREE kill on cancel so a stopped agent reaps its claude.exe grandchild (Windows).
        verification serveAgentCancelDoD : Test { :>> id = "a1c70114-0114-4114-9114-516273840114"; :>> method = VerificationMethod::test; :>> procedureText = "D0094 agent-bridge robustness: on Windows the agent is `cmd /C claude` -> `claude.exe`, and tokio's kill_on_drop reaps only the direct `cmd` child on client disconnect/Stop, ORPHANING the `claude.exe` grandchild (no process-tree kill; #![forbid(unsafe_code)] rules out a Win32 Job Object). FIX: a TreeKiller Drop-guard captures the cmd PID at spawn and runs `taskkill /T /F /PID <pid>` (whole-tree) when the SSE stream is dropped, declared AFTER `child` so it drops first; DISARMED on normal exit so it never targets a reaped/recycled PID. Unix spawns `claude` directly so kill_on_drop already reaps it (guard is a no-op). Never blanket-kills (specific PID tree, not /IM — the user's own session is safe). VERIFY (LIVE): spawn an agent (claude.exe appears, count 14->15), disconnect, confirm the agent's claude.exe PID is reaped (back to 14) while the user's session is untouched; clippy --workspace -D warnings + cargo test + keel validate + guard all (13) green."; }
        part serveAgentCancelDoDR1 : TestResult { :>> id = "345650b0-d783-43ec-8b0e-a9b113912f60"; :>> outcome = VerdictKind::pass; :>> judgedAgainst = "b10fc70"; :>> judgedAt = "2026-06-23"; :>> judgedBy = "claudeOpus"; }

        action initSmokeTest; // D0093: an automated end-to-end smoke test that `keel init` scaffolds a WORKING green project.
        verification initSmokeTestDoD : Test { :>> id = "a1c70115-0115-4115-9115-516273840115"; :>> method = VerificationMethod::test; :>> procedureText = "D0093 spin-up regression guard: the cold-start path (`keel init`) had no automated test, so a scaffold regression (embedded engine drift, engine/instance remap break) would only surface manually. FIX: keel-cli/tests/init_smoke.rs drives the REAL `keel` binary (CARGO_BIN_EXE_keel) end-to-end against a temp dir: init -> assert .engine/ + CLAUDE.md + .tracking/ + reference/decisions/ (read-only arch) + fresh empty decisions/; then `keel validate` clean, `keel guard all` ALL PASS (the D0093 'spin up green' promise), `keel orient` works, and a re-init REFUSES to overwrite (exit!=0). Hermetic (owns its temp dir, atomic-counter naming, cleaned on drop). VERIFY: cargo test --test init_smoke passes; clippy --workspace --all-targets -D warnings + full cargo test + keel validate + guard all (13) green."; }
        part initSmokeTestDoDR1 : TestResult { :>> id = "9f6c2795-1beb-45b0-8242-e47c0f827ee4"; :>> outcome = VerdictKind::pass; :>> judgedAgainst = "a1588d7"; :>> judgedAt = "2026-06-23"; :>> judgedBy = "claudeOpus"; }

        action manifestServeCoverage; // D0050: add serve.rs + console.html to the deliverable-manifest (per-task suspicion coverage for the console).
        verification manifestServeCoverageDoD : Test { :>> id = "a1c70116-0116-4116-9116-516273840116"; :>> method = VerificationMethod::test; :>> procedureText = "D0050 per-task suspicion coverage: the console source (keel-cli/src/serve.rs + keel-cli/assets/console.html) had only the COARSE catch-all coverage of `rustToolchainFix | keel-cli` — no PER-TASK precision tying a console verification to its own source. FIX: add `task: serveItemActions | keel-cli/src/serve.rs keel-cli/assets/console.html` to .engine/deliverable-manifest.txt (instance DATA under unchanged suspicion semantics; not a process-def/schema change — EXECUTE, no kernel/keystone). VERIFY: `keel guard manifest-coverage` PASS (14 scanned, task + both paths exist, 0 violations); `keel suspect --explain` now flags serveItemActions with reason 'deliverable source [serve.rs, console.html] drifted since verified at 7642f1c' — the D0050 drift signal live on first use (advisory, non-blocking for `assured`; re-verify-at-HEAD clears it, consistent with the other Rust milestone tasks). clippy + cargo test + keel validate + guard all (13) green."; }
        part manifestServeCoverageDoDR1 : TestResult { :>> id = "65d3e4ef-9025-4d2c-b057-ac83ca046f90"; :>> outcome = VerdictKind::pass; :>> judgedAgainst = "06001e1"; :>> judgedAt = "2026-06-23"; :>> judgedBy = "claudeOpus"; }

        // ── critique backfill toward 100% (D0080) — batches of 5 elements/pass, human go/no-go between ──
        action critiqueNeeds1; // D0080: Core-3 critique backfill, Needs batch 1 (n01-n05).
        verification critiqueNeeds1DoD : Test { :>> id = "a1c70117-0117-4117-9117-516273840117"; :>> method = VerificationMethod::test; :>> procedureText = "D0080 critique backfill toward 100% coverage. Independent critic claudeOpus (aiModel; targets authored by wweatherholtz) records Core-3 critiques (completeness/correctness/testability) for 5 Needs: n01AtomicItems, n02DecisionsFirstClass, n03VerificationTraced, n04ComputedState, n05GitNative — 15 method=critique verifications + results, each #Verify-linked to its Need, each lens genuinely ATTACKING (not affirming). All 15 survived (outcome=pass); no >=Medium finding raised, so no disposition pending. VERIFY: critique-coverage rises 35->40/120 (29%->33%) with n01-n05 covered; keel validate clean; guard critique + critique-rigor PASS (no shallow/affirming-only flags); guard all (13) green."; }
        part critiqueNeeds1DoDR1 : TestResult { :>> id = "2c35a590-39cf-4aa2-822a-54f5beae4542"; :>> outcome = VerdictKind::pass; :>> judgedAgainst = "5e14b01"; :>> judgedAt = "2026-06-23"; :>> judgedBy = "claudeOpus"; }

        action critiqueBatch2; // D0080: Core-3 critique backfill, pass 2 — Needs n06-n14 + sr01TypedItems (10 items).
        verification critiqueBatch2DoD : Test { :>> id = "a1c70118-0118-4118-9118-516273840118"; :>> method = VerificationMethod::critique; :>> procedureText = "D0080 critique backfill pass 2 (10 items): independent critic claudeOpus (aiModel) records Core-3 critiques for the remaining 9 Needs (n06ProcessAsData, n07AgentAutonomy, n08TraceQueryable, n09SelfHosting, n10NoJvm, n11FastStart, n12PanicFree, n13SpecPin, n14TddBdd) + sr01TypedItems — 30 method=critique verifications + results, each #Verify-linked, each lens genuinely ATTACKING. ONE genuine finding: n14TddBdd x testability FAIL (issue042, Medium) — cargo test is not in the automated commit gate (only clippy is) and there is no CI, so a failing test can reach main; raised + dispositioned by the human (ACT/ACCEPT-RISK/DISMISS, never self-signed). All 29 others survived (pass). VERIFY: critique-coverage rises 40->50/120 (all 14 Needs + sr01 covered); keel validate clean; guard critique PASS; the >=Medium finding carries a human disposition (guard assured READY); guard all (13) green."; }
        part critiqueBatch2DoDR1 : TestResult { :>> id = "f658f81b-8618-4bd1-b48e-f9572a7985c7"; :>> outcome = VerdictKind::pass; :>> judgedAgainst = "701bfa8"; :>> judgedAt = "2026-06-23"; :>> judgedBy = "claudeOpus"; }

        action cargoTestGate; // resolver candidate for issue042 (if ACT): add `cargo test` to the commit gate / CI so a failing test cannot reach main (D0047).
        verification cargoTestGateDoD : Test { :>> id = "a1c70119-0119-4119-9119-516273840119"; :>> method = VerificationMethod::test; :>> procedureText = "Resolver for issue042 (only if the human dispositions ACT): close the gap where `cargo test` is not in the automated gate. Add `cargo test --workspace` to .githooks/pre-commit for staged Rust (gated on rust_staged), OR a .github/workflows CI job, accepting the ~15s latency (weigh vs n11/D0054 friction — a CI job avoids per-commit cost). Makes the n14 'reject where cargo test fails' clause a real automated control (D0047: corrections become guards), not manual vigilance. VERIFY: a deliberately failing test is rejected by the gate; clippy + cargo test + keel validate + guard all green. (Not started — pending issue042 disposition.)"; }
        part cargoTestGateDoDR1 : TestResult { :>> id = "f8ff9ce7-a96c-4713-998b-304a136a22ad"; :>> outcome = VerdictKind::pass; :>> judgedAgainst = "608529f"; :>> judgedAt = "2026-06-23"; :>> judgedBy = "claudeOpus"; }

        action critiqueBatch3; // D0080: Core-3 critique backfill, pass 3 — SystemRequirements sr02-sr11 (10 items).
        verification critiqueBatch3DoD : Test { :>> id = "a1c70120-0120-4120-9120-516273840120"; :>> method = VerificationMethod::critique; :>> procedureText = "D0080 critique backfill pass 3 (10 items): independent critic claudeOpus (aiModel) records Core-3 critiques for SystemRequirements sr02DecisionRecord, sr03AppendResults, sr04ComputedViews, sr05GitNative, sr06ProcessModel, sr07AgentLoop, sr08TraceQuery, sr09SelfBuild, sr10RustCli, sr11FastStart — 30 method=critique verifications + results, each #Verify-linked, each lens genuinely ATTACKING. TWO findings (both Low, issue043): sr07 x correctness (names retired 'validate_all.py') + sr10 x correctness (names renamed binary 'sysmlv2' -> keel, D0095) — living requirement statements with stale artifact names; capabilities met; resolver refreshRequirementText; AI-dispositioned (Low, no human gate). 28 others survived. VERIFY: critique-coverage 50->60/120; keel validate clean; guard issues PASS (issue043 triaged); guard critique-rigor PASS; guard assured READY (no undispositioned >=Medium); guard all (13) green."; }
        part critiqueBatch3DoDR1 : TestResult { :>> id = "f9164c2d-f9c3-481c-8fbd-2d329e9a2698"; :>> outcome = VerdictKind::pass; :>> judgedAgainst = "112554c"; :>> judgedAt = "2026-06-23"; :>> judgedBy = "claudeOpus"; }

        action refreshRequirementText; // resolver for issue043 (D0095 completion): update the 3 living requirement statements (sr07/sr10/sr11) to current artifact names; history preserved.
        verification refreshRequirementTextDoD : Test { :>> id = "a1c70121-0121-4121-9121-516273840121"; :>> method = VerificationMethod::test; :>> procedureText = "Resolver for issue043 (AI-dispositioned ACT): update the LIVING SystemRequirement statements to current artifact names — sr07AgentLoop 'validate_all.py' -> 'keel validate/guard via the .githooks pre-commit hook'; sr10RustCli binary '(sysmlv2)' -> '(keel)'; sr11FastStart 'The sysmlv2 CLI' -> 'The keel CLI'; sr12DenyWarnings 'sysmlv2-parser and sysmlv2-cli crates' -> 'keel-parser and keel-cli crates'; sr13SpecPin 'The sysmlv2-parser crate' -> 'The keel-parser crate'. A doc-accuracy completion of the D0095 rename for living contracts; historical sprint records keep 'sysmlv2' as point-in-time fact (never rewrite history). Editing the statements re-suspects the affected critiques -> re-critique at HEAD (the normal D0084 cycle). VERIFY: no 'sysmlv2'/'validate_all.py' in the living statements; keel validate clean; the affected critiques re-run pass; guard all green. (Not started — tracked resolver.)"; }
        part refreshRequirementTextDoDR1 : TestResult { :>> id = "0a9352d6-530e-4ef8-bf47-a56986c02104"; :>> outcome = VerdictKind::pass; :>> judgedAgainst = "8c49b9c"; :>> judgedAt = "2026-06-23"; :>> judgedBy = "claudeOpus"; }

        // critique backfill passes 4+ (autonomous run to 100%, 5 items/batch); each pass is its own sprint.
        action critiqueBatch4; // D0080: sr12-sr14 + d0002, d0004 (d0003 deferred to end-of-run signoff).
        verification critiqueBatch4DoD : Test { :>> id = "a1c70122-0122-4122-9122-516273840122"; :>> method = VerificationMethod::critique; :>> procedureText = "D0080 backfill pass 4 (5 items): Core-3 critiques for sr12DenyWarnings, sr13SpecPin, sr14TddBdd, d0002 (schema governance), d0004 (atomic items) — 15 method=critique verifications, each #Verify-linked, independent critic claudeOpus. Findings fold into ALREADY-DISPOSITIONED issues (no new blockers): sr12/sr13 correctness (stale crate names sysmlv2-parser/cli -> keel) -> issue043; sr14 testability (CI/cargo-test gap, the SR mirror of n14) -> issue042. d0002/d0004 survived all lenses (sound, in-force, demonstrated). d0003 DEFERRED to the end-of-run signoff batch (its 'writePolicy ENFORCED by the API' claim is unrealized -> a >=Medium finding the human must disposition). VERIFY: critique-coverage 60->65/120; keel validate clean; guard assured READY (no NEW undispositioned >=Medium); guard all (13) green."; }
        part critiqueBatch4DoDR1 : TestResult { :>> id = "85465a26-42e1-4133-b125-ae0cbb31f59d"; :>> outcome = VerdictKind::pass; :>> judgedAgainst = "ceb0920"; :>> judgedAt = "2026-06-23"; :>> judgedBy = "claudeOpus"; }

        action critiqueBatch5; // D0080: Decisions d0006-d0010 (Core-3 each).
        verification critiqueBatch5DoD : Test { :>> id = "a1c70123-0123-4123-9123-516273840123"; :>> method = VerificationMethod::critique; :>> procedureText = "D0080 backfill pass 5 (5 items): Core-3 critiques (completeness/correctness/feasibility) for Decisions d0006 (verification-by-method), d0007 (reusable engine/two models), d0008 (STPA first-class, HARA/ASIL out), d0009 (workflow states as data), d0010 (ceremonies as discipline) — 15 method=critique verifications, independent critic claudeOpus, each #Verify-linked. All 15 survived (pass); several early-decision specifics (d0006 method enum, d0009 currentState clause, d0010 ceremony list) noted as governed decision-evolution (later refined by D0016/D0018/D0049 etc.), not live defects. No findings/deferrals. VERIFY: critique-coverage 65->70/120; keel validate clean; guard all (13) green."; }
        part critiqueBatch5DoDR1 : TestResult { :>> id = "bf5b60ce-8886-4fe2-aab3-b3dda4d56c2a"; :>> outcome = VerdictKind::pass; :>> judgedAgainst = "768ccbf"; :>> judgedAt = "2026-06-23"; :>> judgedBy = "claudeOpus"; }

        action critiqueBatch6; // D0080: Decisions d0011-d0015 (Core-3 each).
        verification critiqueBatch6DoD : Test { :>> id = "a1c70124-0124-4124-9124-516273840124"; :>> method = VerificationMethod::critique; :>> procedureText = "D0080 backfill pass 6 (5 items): Core-3 critiques for Decisions d0011 (native metaclasses), d0012 (native method-tagged verification + first-class confirmation), d0013 (git-ancestry clock), d0014 (main-only branch), d0015 (materialized views sanctioned) — 15 method=critique verifications, critic claudeOpus, each #Verify-linked. All survived (d0012 method enum noted as later-extended by D0080; d0014's CI/test-gate caveat cross-refs issue042 but the branch decision itself is sound). No findings/deferrals. VERIFY: critique-coverage 70->75/120; keel validate clean; guard all (13) green."; }
        part critiqueBatch6DoDR1 : TestResult { :>> id = "d16124ed-30d1-4d2a-bd52-3b2a9348091e"; :>> outcome = VerdictKind::pass; :>> judgedAgainst = "e71a779"; :>> judgedAt = "2026-06-23"; :>> judgedBy = "claudeOpus"; }

        action critiqueBatch7; // D0080: Decisions d0016,d0017,d0019,d0020,d0021 (Core-3 each).
        verification critiqueBatch7DoD : Test { :>> id = "a1c70125-0125-4125-9125-516273840125"; :>> method = VerificationMethod::critique; :>> procedureText = "D0080 backfill pass 7 (5 items): Core-3 critiques for Decisions d0016 (confirmation sign-off), d0017 (13 CRs accepted), d0019 (batch confirmation gates), d0020 (skillsRefresh), d0021 (specRefresh+contractAlign) — 15 method=critique verifications, critic claudeOpus, each #Verify-linked. All survived; doc-sync/CR-record decisions treated as immutable historical records (naming query.py/sysmlv2 was accurate at their time — not a staleness defect like a living contract). No findings. VERIFY: critique-coverage 75->80/120; keel validate clean; guard all (13) green."; }
        part critiqueBatch7DoDR1 : TestResult { :>> id = "4535d00d-d858-4cef-9fed-c56949598ac9"; :>> outcome = VerdictKind::pass; :>> judgedAgainst = "3208351"; :>> judgedAt = "2026-06-23"; :>> judgedBy = "claudeOpus"; }

        action critiqueBatch8; // D0080: Decisions d0022-d0026 (Core-3 each).
        verification critiqueBatch8DoD : Test { :>> id = "a1c70126-0126-4126-9126-516273840126"; :>> method = VerificationMethod::critique; :>> procedureText = "D0080 backfill pass 8 (5 items): Core-3 critiques for Decisions d0022 (S6 docSync), d0023 (S7 done-detection align + whats-next), d0024 (S7 docSync), d0025 (S8 is_ordering_only AST), d0026 (S8 docSync) — 15 method=critique verifications, critic claudeOpus, each #Verify-linked. All 15 critiques authored + survived. FINDING (deferred to end-of-run signoff): d0023's 3 critiques are present + valid but show UNCOVERED because d0023's `decision` field has regex backslash-escapes (\\s/\\w/\\d) and compute_stale_verifications/extract_field reads the raw git blob without the parser's string-unescaping -> blob != model -> false-stale -> excluded (view.rs:1362). A genuine engine Medium bug (-> issue044 at signoff + a staleUnescape fix); blocks coverage for any escaped-content element. VERIFY: critique-coverage 80->84/120 (d0023 critiqued but uncounted pending the fix); keel validate clean; guard all (13) green."; }
        part critiqueBatch8DoDR1 : TestResult { :>> id = "b1b5f986-b53b-4b18-b951-f4733f190968"; :>> outcome = VerdictKind::pass; :>> judgedAgainst = "1427491"; :>> judgedAt = "2026-06-23"; :>> judgedBy = "claudeOpus"; }

        action critiqueBatch9; // D0080: Decisions d0027-d0031 (Core-3 each).
        verification critiqueBatch9DoD : Test { :>> id = "a1c70127-0127-4127-9127-516273840127"; :>> method = VerificationMethod::critique; :>> procedureText = "D0080 backfill pass 9 (5 items): Core-3 critiques for d0027 (write API), d0028 (S9 docSync), d0029 (Issue.relatedTask), d0030 (S10 docSync), d0031 (stateDef spike NOT GREEN) — 15 method=critique verifications, critic claudeOpus, each #Verify-linked. All survived (CR/spike/docSync records; d0029 relatedTask noted as later elevated to #Resolves by D0077). No findings. VERIFY: critique-coverage 84->89/120; keel validate clean; guard all (13) green."; }
        part critiqueBatch9DoDR1 : TestResult { :>> id = "195fa0b0-3ac5-4e5b-b3c3-1a7c4c842f4d"; :>> outcome = VerdictKind::pass; :>> judgedAgainst = "1f88158"; :>> judgedAt = "2026-06-23"; :>> judgedBy = "claudeOpus"; }

        action critiqueBatch10; // D0080: Decisions d0032-d0036 (Core-3 each).
        verification critiqueBatch10DoD : Test { :>> id = "a1c70128-0128-4128-9128-516273840128"; :>> method = VerificationMethod::critique; :>> procedureText = "D0080 backfill pass 10 (5 items): Core-3 critiques for d0032 (TestResult->occurrence def), d0033 (S11 docSync), d0034 (CR versioning via git), d0035 (Need/Requirement by type), d0036 (safety-case views, no new types) — 15 method=critique verifications, critic claudeOpus, each #Verify-linked. All survived. No findings. VERIFY: critique-coverage 89->94/120; keel validate clean; guard all (13) green."; }
        part critiqueBatch10DoDR1 : TestResult { :>> id = "770d7f95-6561-448d-8ad9-72b9000b4777"; :>> outcome = VerdictKind::pass; :>> judgedAgainst = "85bc93c"; :>> judgedAt = "2026-06-23"; :>> judgedBy = "claudeOpus"; }

        action critiqueBatch11; // D0080: Decisions d0037,d0039,d0040,d0041,d0042 (Core-3 each).
        verification critiqueBatch11DoD : Test { :>> id = "a1c70129-0129-4129-9129-516273840129"; :>> method = VerificationMethod::critique; :>> procedureText = "D0080 backfill pass 11 (5 items): Core-3 critiques for d0037 (validated authorship), d0039 (ceremony skills), d0040 (recurring-task-skill rule), d0041 (defer 3 toolchain features), d0042 (Release occurrence def) — 15 method=critique verifications, critic claudeOpus, each #Verify-linked. All survived. No findings. VERIFY: critique-coverage 94->99/120; keel validate clean; guard all (13) green."; }
        part critiqueBatch11DoDR1 : TestResult { :>> id = "1275ecdd-ca4e-49b5-a67f-8457279a0477"; :>> outcome = VerdictKind::pass; :>> judgedAgainst = "82f42ea"; :>> judgedAt = "2026-06-23"; :>> judgedBy = "claudeOpus"; }

        action critiqueBatch12; // D0080: Decisions d0043,d0044,d0045,d0046,d0051 (Core-3 each).
        verification critiqueBatch12DoD : Test { :>> id = "a1c70130-0130-4130-9130-516273840130"; :>> method = VerificationMethod::critique; :>> procedureText = "D0080 backfill pass 12 (5 items): Core-3 critiques for d0043 (anti-drift validator guards), d0044 (cap ≤8 pts), d0045 (drop StateCursor, compute ceremony status), d0046 (CAE+GQM+ATAM audit framework), d0051 (per-sitting confirms non-test-verifiable only) — 15 method=critique verifications, critic claudeOpus, each #Verify-linked. All survived. No findings. VERIFY: critique-coverage 99->104/120; keel validate clean; guard all (13) green."; }
        part critiqueBatch12DoDR1 : TestResult { :>> id = "08857c3c-978b-4bc1-8b50-fcf1692ec09b"; :>> outcome = VerdictKind::pass; :>> judgedAgainst = "de46c58"; :>> judgedAt = "2026-06-23"; :>> judgedBy = "claudeOpus"; }

        action critiqueBatch13; // D0080: Decisions d0052,d0053,d0055,d0058,d0060 (Core-3 each).
        verification critiqueBatch13DoD : Test { :>> id = "a1c70131-0131-4131-9131-516273840131"; :>> method = VerificationMethod::critique; :>> procedureText = "D0080 backfill pass 13 (5 items): Core-3 critiques for d0052 (ordered backlog), d0053 (defer trackedMetadata, re-freeze), d0055 (engine IS systems modeling), d0058 (Decision Analysis convention), d0060 (settled item model) — 15 method=critique verifications, critic claudeOpus, each #Verify-linked. All survived. No findings. VERIFY: critique-coverage 104->109/120; keel validate clean; guard all (13) green."; }
        part critiqueBatch13DoDR1 : TestResult { :>> id = "cfc418e2-9a0c-431c-b264-58200623867c"; :>> outcome = VerdictKind::pass; :>> judgedAgainst = "41a9743"; :>> judgedAt = "2026-06-23"; :>> judgedBy = "claudeOpus"; }

        action critiqueBatch14; // D0080: Decisions d0061,d0063,d0064,d0065,d0067 (Core-3 each).
        verification critiqueBatch14DoD : Test { :>> id = "a1c70132-0132-4132-9132-516273840132"; :>> method = VerificationMethod::critique; :>> procedureText = "D0080 backfill pass 14 (5 items): Core-3 critiques for d0061 (Decision field set), d0063 (attr-model migration), d0064 (bootstrap over, sprint discipline), d0065 (attr-model contract), d0067 (safe-migration process) — 15 method=critique verifications, critic claudeOpus, each #Verify-linked. All survived. No findings. VERIFY: critique-coverage 109->114/120; keel validate clean; guard all (13) green."; }
        part critiqueBatch14DoDR1 : TestResult { :>> id = "c38265a5-27b7-4cc7-abc2-8d0d8c9eb429"; :>> outcome = VerdictKind::pass; :>> judgedAgainst = "a316942"; :>> judgedAt = "2026-06-23"; :>> judgedBy = "claudeOpus"; }

        action critiqueBatch15; // D0080: Decisions d0072,d0073,d0078 (the last 3 normal decisions; Core-3 each).
        verification critiqueBatch15DoD : Test { :>> id = "a1c70133-0133-4133-9133-516273840133"; :>> method = VerificationMethod::critique; :>> procedureText = "D0080 backfill pass 15 (3 items — the last NORMAL decisions): Core-3 critiques for d0072 (actualHours=AI time), d0073 (per-sitting review confirmation), d0078 (issue-resolution process) — 9 method=critique verifications, critic claudeOpus, each #Verify-linked. All survived. No findings. After this, only the 3 SPECIAL items remain: d0023+d0076 (need the staleUnescape fix to count) + d0003 (writePolicy human disposition). VERIFY: critique-coverage 114->117/120; keel validate clean; guard all (13) green."; }
        part critiqueBatch15DoDR1 : TestResult { :>> id = "22e3ffdb-396f-4b8c-851a-c7de968da660"; :>> outcome = VerdictKind::pass; :>> judgedAgainst = "c5e48db"; :>> judgedAt = "2026-06-23"; :>> judgedBy = "claudeOpus"; }

        action staleUnescapeFix; // D0084: fix the extract_field staleness false-positive on escaped semantic fields (issue044) + critique d0076.
        verification staleUnescapeFixDoD : Test { :>> id = "a1c70134-0134-4134-9134-516273840134"; :>> method = VerificationMethod::test; :>> procedureText = "Resolver for issue044 (Medium engine bug) + finishes the escaped-content critiques. view.rs: replace extract_field's raw end-quote scan with decode_string_body — unescape exactly like the lexer's lex_string (backslash-backslash/backslash-quote/\\n/\\t) + stop at the first UNESCAPED quote, so blob-extract == model-attr and escaped semantic fields no longer false-flag stale. Permanent guard (D0047): unit tests extract_field_unescapes_like_the_lexer + extract_field_plain_value. Then critique d0076 (escaped `\\\"` content — now counts). VERIFY (measured): d0023 + d0076 now COVERED; critique-coverage 117->119/120; clippy --workspace -D warnings + cargo test (48 lib + BDD) + keel validate + guard all (13) green; assured READY (issue044 closed by this resolver, no new undispositioned >=Medium)."; }
        part staleUnescapeFixDoDR1 : TestResult { :>> id = "fad4bd51-9c15-4c89-8ce7-6c7e32960633"; :>> outcome = VerdictKind::pass; :>> judgedAgainst = "0b94355"; :>> judgedAt = "2026-06-23"; :>> judgedBy = "claudeOpus"; }

        action critiqueD0003; // D0080: Core-3 critique of d0003 (the last element); surfaces issue045 (writePolicy enforcement, human disposition).
        verification critiqueD0003DoD : Test { :>> id = "a1c70135-0135-4135-9135-516273840135"; :>> method = VerificationMethod::critique; :>> procedureText = "D0080 backfill — the FINAL element (d0003), reaching 120/120 critique coverage. Core-3 critiques (critic claudeOpus): completeness pass, correctness FAIL (d0003's 'writePolicy ENFORCED by the API, no self-promotion' is unrealized — one CLI write path, no per-skill authz; superseded in practice by the D0093/D0094 human commit-gate) -> issue045 (Medium), feasibility pass-with-note. issue045 needs the HUMAN's typed disposition (ACT/ACCEPT-RISK/DISMISS) before this can commit (undispositioned >=Medium blocks assured). VERIFY: critique-coverage 119->120/120 (100%); issue045 dispositioned via apply-review; keel validate + guard all (13) green."; }
        part critiqueD0003DoDR1 : TestResult { :>> id = "365ecc61-356c-403d-96c6-22cecefbd47b"; :>> outcome = VerdictKind::pass; :>> judgedAgainst = "ba841c7"; :>> judgedAt = "2026-06-23"; :>> judgedBy = "claudeOpus"; }

        action writePolicyResolve; // resolver candidate for issue045 (if ACT): enforce per-skill writePolicy OR formally supersede d0003 to the commit-gate authz model (D0093/D0094).
        verification writePolicyResolveDoD : Test { :>> id = "a1c70136-0136-4136-9136-516273840136"; :>> method = VerificationMethod::test; :>> procedureText = "Resolver for issue045 (only if the human dispositions ACT): EITHER implement per-skill writePolicy enforcement in the write path (read the calling skill's policy, gate read-only|pr-only|direct, block self-promotion), OR — more likely — author a Decision that formally supersedes/revises d0003 to state the realized authorization model (the human commit-gate: CLI is authority, agent never auto-commits, D0093/D0094). VERIFY per the chosen path; guard all green. (Not started — pending issue045 disposition.)"; }
        part writePolicyResolveDoDR1 : TestResult { :>> id = "7cfeef03-3c05-47c5-bbfe-c5f28d243747"; :>> outcome = VerdictKind::pass; :>> judgedAgainst = "64d2135"; :>> judgedAt = "2026-06-23"; :>> judgedBy = "claudeOpus"; }

        action ciClippyGreen; // make the new CI gate (cargoTestGate) actually pass: fix 7 clippy lints the CI's newer toolchain (1.96) flags.
        verification ciClippyGreenDoD : Test { :>> id = "a1c70137-0137-4137-9137-516273840137"; :>> method = VerificationMethod::test; :>> procedureText = "The CI gate added by cargoTestGate FAILED on its first GitHub run: the runner's stable clippy (1.96) flags 7 lints the local toolchain (1.94) did not (map_unwrap_or x3: govern.rs/orient.rs/serve.rs; unnecessary_sort_by x2: serve.rs/view.rs; manual_checked_ops: view.rs pct; collapsible_match: write.rs). FIX: rewrite each to the canonical forms (is_ok_and / map_or / sort_by_key+Reverse / checked_div / match-guard) — valid on both 1.94 and 1.96. Bumped the LOCAL toolchain to 1.96 to match CI + re-ran clippy --all-targets clean. LESSON (D0047): keep local rustup current so the pre-commit clippy matches the floating-stable CI; the CI is the backstop that caught the drift on its first use. VERIFY: cargo clippy --workspace --all-targets -D warnings clean on 1.96; cargo test 48 lib + BDD + parser pass; keel validate 148 + guard all (13) green; the GitHub CI run goes green."; }
        part ciClippyGreenDoDR1 : TestResult { :>> id = "cf8b62b2-d132-40e0-bd75-70c08a03e210"; :>> outcome = VerdictKind::pass; :>> judgedAgainst = "7e92726"; :>> judgedAt = "2026-06-23"; :>> judgedBy = "claudeOpus"; }

        // ── DEPLOYMENT READINESS (planned; not started — captured per D0018, ordered by D0052 declaration=priority).
        //    Model (D0093): distributable = the `keel` binary (embeds .engine); downstream = `keel init`. Channel
        //    (human-chosen 2026-06-23): GitHub Releases — a v* tag builds win/mac/linux binaries. This repo stays
        //    the engine source-of-record + self-build evidence. NOT a feature-freeze commitment; deploy is "soon". ──
        action scaffoldEngineDevExclude; // exclude engine-dev cruft from the embedded keel-init scaffold (D0093 boundary).
        verification scaffoldEngineDevExcludeDoD : Test { :>> id = "a1c70140-0140-4140-9140-516273840140"; :>> method = VerificationMethod::test; :>> procedureText = "D0093 engine/instance boundary: the binary embeds ALL of .engine via include_dir!, so `keel init` currently ships ~30 engine-DEV-only python files (.engine/tools/validate/*.py kernel validators + _kernel.py + spikes + probes + __pycache__ + migrations/) that downstream projects neither need nor can run (no conda/JVM; D0048 = Rust path is the authority). FIX: exclude .engine/tools/ (and any __pycache__) from the scaffolded copy in main.rs (scaffold_engine/write_engine_file) — ship only the REUSABLE engine (schema/workflows/processes/skills/decisions->reference/docs/views/contracts). VERIFY: a fresh `keel init` DIR has no .engine/tools + no .py + no __pycache__; init_smoke.rs asserts the exclusion; `keel validate`/`guard` on the fresh scaffold still PASS; clippy + cargo test + guard all green."; }
        part scaffoldEngineDevExcludeDoDR1 : TestResult { :>> id = "77137c4f-2ff2-4f9b-a2d1-9d04b7ae13cd"; :>> outcome = VerdictKind::pass; :>> judgedAgainst = "888a5df"; :>> judgedAt = "2026-06-23"; :>> judgedBy = "claudeOpus"; }

        action scaffoldCommitGate; // keel init scaffolds a Rust-only commit gate so downstream has an automated gate day one.
        verification scaffoldCommitGateDoD : Test { :>> id = "a1c70141-0141-4141-9141-516273840141"; :>> method = VerificationMethod::test; :>> procedureText = "A fresh `keel init` project has NO commit gate (the engine-dev .githooks/pre-commit is conda-dependent + lives outside .engine, so it does not ship). FIX: `keel init` scaffolds a RUST-ONLY gate — a .githooks/pre-commit running `keel validate .` + `keel guard` (no conda/kernel) + sets core.hooksPath (or prints the one-liner), and optionally a .github/workflows/ci.yml template (cargo test + clippy, mirroring this repo's gate). VERIFY: a fresh `keel init` project's pre-commit rejects an invalid .sysml + a guard violation, with zero conda dependency; init_smoke asserts the gate exists + is kernel-free; guard all green."; }
        part scaffoldCommitGateDoDR1 : TestResult { :>> id = "690d5b34-50ba-412c-8ea4-82783233d774"; :>> outcome = VerdictKind::pass; :>> judgedAgainst = "184bbfc"; :>> judgedAt = "2026-06-23"; :>> judgedBy = "claudeOpus"; }

        action cargoReleaseMetadata; // crate metadata for release + discoverability (prereq for releaseWorkflow).
        verification cargoReleaseMetadataDoD : Test { :>> id = "a1c70142-0142-4142-9142-516273840142"; :>> method = VerificationMethod::test; :>> procedureText = "keel-cli/Cargo.toml lacks description/repository/readme/keywords/categories (not release- or crates.io-ready). FIX: add description, repository, readme, keywords, categories to keel-cli (+ keel-parser) [workspace.package] or per-crate. VERIFY: `cargo package --list` / `cargo publish --dry-run` clean (metadata present); cargo build --release + clippy + cargo test green."; }
        part cargoReleaseMetadataDoDR1 : TestResult { :>> id = "836683e9-9503-4ebc-86d3-c5ecbb57a104"; :>> outcome = VerdictKind::pass; :>> judgedAgainst = "36f38c0"; :>> judgedAt = "2026-06-23"; :>> judgedBy = "claudeOpus"; }

        action releaseWorkflow; // GitHub Releases: v* tag -> build win/mac/linux keel binaries -> attach to a Release.
        verification releaseWorkflowDoD : Test { :>> id = "a1c70143-0143-4143-9143-516273840143"; :>> method = VerificationMethod::test; :>> procedureText = "Distribution (human-chosen): GitHub Releases of prebuilt binaries so downstream users need no Rust toolchain. FIX: add .github/workflows/release.yml triggered on `v*` tags — build `keel` for x86_64 windows-msvc / macos / linux (matrix), attach the artifacts to a GitHub Release (softprops/action-gh-release or gh release). VERIFY (CI): the workflow is well-formed + builds keel --release on each target; on a test tag it produces downloadable keel-{win,mac,linux} binaries; depends on cargoReleaseMetadata."; }
        part releaseWorkflowDoDR1 : TestResult { :>> id = "eb42e489-18d6-4f9b-b4ff-55ad809e122d"; :>> outcome = VerdictKind::pass; :>> judgedAgainst = "0706cc8"; :>> judgedAt = "2026-06-24"; :>> judgedBy = "claudeOpus"; }

        action consumerReadme; // split/refresh README for downstream consumers; fix stale refs (doc-sync).
        verification consumerReadmeDoD : Test { :>> id = "a1c70144-0144-4144-9144-516273840144"; :>> method = VerificationMethod::inspect; :>> procedureText = "The README is engine-DEV-focused + stale ('decisions (0001-0018)' [now 0001-0096], 'state cursor' [dropped D0045], 'query.py/report.py' [retired M4]). FIX (doc-sync skill): a CONSUMER quickstart — download keel from a GitHub Release -> `keel init myproject` -> run the `introduction` skill -> `keel orient` — separated from the engine-dev/self-build narrative; correct every stale ref. VERIFY: README quickstart works against a fresh `keel init`; no stale 0001-0018/state-cursor/query.py refs; doc-sync grep clean."; }
        part consumerReadmeDoDR1 : TestResult { :>> id = "94e38a91-ee4d-473a-8bb7-2cdc55843976"; :>> outcome = VerdictKind::pass; :>> judgedAgainst = "58609fe"; :>> judgedAt = "2026-06-23"; :>> judgedBy = "claudeOpus"; }

        action introductionDryRun; // walk the introduction onboarding skill end-to-end in a fresh init project.
        verification introductionDryRunDoD : Test { :>> id = "a1c70145-0145-4145-9145-516273840145"; :>> method = VerificationMethod::demo; :>> procedureText = "D0093 first-value: init_smoke proves `keel init` scaffolds + validates, but not the ONBOARDING UX. FIX: run the `introduction` skill end-to-end in a fresh `keel init` project as a newcomer (orient -> capture first Need -> first refine->sprint -> orient), fixing any friction/gaps found. VERIFY: a newcomer reaches first-value (a tracked Need + first sprint) following only the introduction skill + README; gaps logged + fixed; guard all green."; }
        part introductionDryRunDoDR1 : TestResult { :>> id = "4dfffbed-63a4-44f3-b80d-90c1178b7359"; :>> outcome = VerdictKind::pass; :>> judgedAgainst = "7bd115f"; :>> judgedAt = "2026-06-23"; :>> judgedBy = "claudeOpus"; }

        action serveDownstreamDegrade; // verify/doc keel serve graceful degradation downstream (agent-bridge without claude CLI).
        verification serveDownstreamDegradeDoD : Test { :>> id = "a1c70146-0146-4146-9146-516273840146"; :>> method = VerificationMethod::test; :>> procedureText = "`keel serve` (the D0094 console) ships in the binary; downstream users may lack the locally-authenticated `claude` CLI the agent-bridge needs. FIX: verify the read console + deterministic actions work in a fresh `keel init` project, and the agent-bridge degrades gracefully (clear message) when `claude` is absent; document the enterprise-auth requirement. VERIFY: `keel serve` on a fresh project serves the read console + introspect; an agent action without `claude` shows the graceful error (confirm + document); guard all green."; }
        part serveDownstreamDegradeDoDR1 : TestResult { :>> id = "5926c20c-56ae-46d5-873b-44009da9f8bf"; :>> outcome = VerdictKind::pass; :>> judgedAgainst = "354447d"; :>> judgedAt = "2026-06-23"; :>> judgedBy = "claudeOpus"; }

        action releaseTag010; // tag v0.1.0 — the engine source-of-record snapshot + the release trigger (sequence LAST).
        verification releaseTag010DoD : Test { :>> id = "a1c70147-0147-4147-9147-516273840147"; :>> method = VerificationMethod::confirmation; :>> procedureText = "CAPTURE the engine work + trigger the first release. After the deployment-readiness tasks are green, tag v0.1.0 on main (the durable engine source-of-record snapshot; this repo retains the full self-build history + decisions for future engine modifications) + brief release notes/CHANGELOG. The tag fires releaseWorkflow -> the first GitHub Release of keel binaries. HUMAN sign-off required (a release is outward-facing; confirmation method). VERIFY: v0.1.0 tag on main; GitHub Release published with downloadable keel binaries; `keel init` from the released binary scaffolds a clean, green project. (Sequenced last.)"; }
        part releaseTag010DoDR1 : TestResult { :>> id = "1a9697fe-680a-4eaf-bec8-100a9b831fe9"; :>> outcome = VerdictKind::pass; :>> judgedAgainst = "a0f5afc"; :>> judgedAt = "2026-06-29"; :>> judgedBy = "wweatherholtz"; }

        action serveRequirementsTrace; // author the serve Needs + SystemRequirements (the 3 use cases) + retro-charter the existing serve work — resolves issue046.
        verification serveRequirementsTraceDoD : Test { :>> id = "a1c70148-0148-4148-9148-516273840148"; :>> method = VerificationMethod::inspect; :>> procedureText = "keel serve (D0094) was built decision-first with NO driving Need/SystemRequirement (issue046). FIX (Business -> Architecture): author the 3 serve Needs from the stakeholder use cases — (1) strong introspection into work state, esp. RECENT decisions with context; (2) ad-hoc element critique that is RECORDED, IMPLEMENTED, and REMEMBERED; (3) CONCISE section-local critique + AI white-box system-boundary analysis driving concision/purer requirements/better indicators — each accepted by the human; derive SystemRequirements with satisfy edges; add verify edges to Tests; RETRO-CHARTER the existing serve delivery work (the D0094 milestones) to these requirements (satisfy/#CharteredBy). VERIFY: keel trace-need shows each serve Need -> requirement -> verification; keel coverage includes the serve requirements; orphans view clean for them; guard all green. Then re-run the serve gap analysis as a COVERAGE computation (not code-reading)."; }
        part serveRequirementsTraceDoDR1 : TestResult { :>> id = "69bcd8ad-08e3-4b05-9efd-3cb574ee8c9f"; :>> outcome = VerdictKind::pass; :>> judgedAgainst = "c4106d0"; :>> judgedAt = "2026-06-24"; :>> judgedBy = "claudeOpus"; }

        action requirementRootednessGuard; // enforce that chartered work/capabilities trace to a driving Need — requirement-rootedness as a permanent guard, not vigilance. Resolves issue047. CHANGE (Decision + guard).
        verification requirementRootednessGuardDoD : Test { :>> id = "a1c70149-0149-4149-9149-516273840149"; :>> method = VerificationMethod::test; :>> procedureText = "GENERAL gap (issue047): nothing prevents/flags chartered work / a user-facing capability built with NO driving Need — requirement-rootedness is enforced only by vigilance, and serve slipped through (issue046). A KEY, un-ignorable process control is needed (D0047: corrections become guards). TRIAGE + CHANGE (record a Decision + human acceptance), covering THREE things: (1) UPWARD rootedness — every Decision that charters delivery work / every shipped capability must trace (satisfy/derive) to a Need; a guard FAILS on an un-rooted capability (scope + exemptions, e.g. pure engine-internal refactors, are part of the Decision). (2) DOWNWARD comprehensiveness — each tier is cleanly + COMPREHENSIVELY satisfied by its downstream items (Need fully decomposed into SRs; SR fully implemented + verified); surface incomplete downstream satisfaction as a LEADING INDICATOR of insufficient implementation (a tier-satisfaction view/indicator), and make it the first chained white-box analysis target. (3) REQUIREMENT-FIRST SUPPORT — the enforced `guard assured` currently flags any governed uncovered Need/SR as a readiness gap, blocking requirement-first authoring; make a governed gap-requirement that carries a resolver / gap-Issue legitimate honest WIP (track-don't-fake), NOT an assurance failure. VERIFY: the guard flags a synthetic un-rooted capability + passes once rooted; a requirement-first gap-requirement-with-resolver no longer blocks assured; the tier-comprehensiveness view computes; doc-sync (CLAUDE.md interaction-loop + validation); guard joins the enforced set. PREREQUISITE for serveRequirementsTrace. #ProcessDefect -> d0047."; }
        part requirementRootednessGuardDoDR1 : TestResult { :>> id = "ad619623-755d-456b-841e-9e7c25c19ec5"; :>> outcome = VerdictKind::pass; :>> judgedAgainst = "c6664cc"; :>> judgedAt = "2026-06-24"; :>> judgedBy = "claudeOpus"; }

        action serveSettings; // persistent serve settings toggle to enable/disable the claude -p agent bridge (billing control) — resolves issue049.
        verification serveSettingsDoD : Test { :>> id = "a1c70151-0151-4151-9151-516273840151"; :>> method = VerificationMethod::test; :>> procedureText = "issue049: the agent bridge drives `claude -p` whose headless billing is in flux (D0094). FIX: a PERSISTENT settings toggle (`.keel-serve.json`, gitignored, default ON) for the agent bridge; GET/POST /api/settings; /api/agent/stream refuses when OFF (no `claude -p` spawned) with a clear message; console Settings tab + the Critique button hidden when OFF. VERIFY (live): GET /api/settings default {agentBridge:true}; POST {agentBridge:false} persists; critique stream when OFF returns the bridge-OFF error (no claude); Settings tab present; clippy + validate + guard green."; }
        part serveSettingsDoDR1 : TestResult { :>> id = "c1bdf7c7-bad5-4bc9-8316-fa84d134b9e7"; :>> outcome = VerdictKind::pass; :>> judgedAgainst = "7f9e635"; :>> judgedAt = "2026-06-24"; :>> judgedBy = "claudeOpus"; }

        action localGateMatchesCi; // make the local pre-commit gate run the FULL `keel guard` so it matches CI — resolves issue048.
        verification localGateMatchesCiDoD : Test { :>> id = "a1c70150-0150-4150-9150-516273840150"; :>> method = VerificationMethod::test; :>> procedureText = "issue048: the local pre-commit hook ran a CURATED per-path guard subset (omitting viewpoint-renderer/manifest-coverage/critic-independence/process-skill/actors), so a viewpoint-renderer violation passed the hook + only failed CI (init_smoke `guard all`). FIX (D0047, lightweight): the hook runs the FULL `keel guard` (all enforced honest-state guards — kernel-free, <1s) whenever any .sysml changes, so the LOCAL gate matches CI. VERIFY: hook runs `keel guard` (12 ALL PASS); a synthetic viewpoint-renderer/etc. violation is now caught locally, not just in CI. (The cherry-picked-git-add root cause is behavioral — addressed via memory: stage with `git add -A` + check `gh run` after every push.)"; }
        part localGateMatchesCiDoDR1 : TestResult { :>> id = "0a288500-f8e2-43df-9853-9555cb7e2799"; :>> outcome = VerdictKind::pass; :>> judgedAgainst = "fc87492"; :>> judgedAt = "2026-06-24"; :>> judgedBy = "claudeOpus"; }

        // ── SERVE GRANULAR WHITE-BOX (Need n17ServeGranularWhitebox) — the two remaining unverified serve SRs
        //    authored by serveRequirementsTrace (sprint149) but not yet delivered (tier-satisfaction burndown gaps,
        //    D0098). Sequenced sr18 then sr19. ──
        action sr18Deliver; // section-local render + recorded section-scoped critique — delivers sr18ServeSectionCritique.
        verification sr18DeliverDoD : Test { :>> id = "a1c70152-0152-4152-9152-516273840152"; :>> method = VerificationMethod::test; :>> procedureText = "Delivers sr18ServeSectionCritique (Need n17ServeGranularWhitebox): whole-model views are too coarse for local 'does X make sense' critique. FIX: the console renders a BOUNDED section — either a declared view (keel render/view) OR a named element plus its typed-edge neighbourhood — and records SECTION-SCOPED critique findings against that section's elements (the element-critique skill via the agent bridge), each finding a severity-carrying Issue linked to the element (reusing the sr16 critique-loop write path: Issue + disposition + #Resolves resolver + re-verify suspicion). VERIFY (live): a section endpoint returns the bounded element set (a view's exposed elements, or an element + its 1-hop typed-edge neighbours); a section critique records Issues scoped to exactly those elements; clippy + keel validate + guard all green; sr18Verify (#Verify -> sr18ServeSectionCritique) records it. Builds on the directed-critique surface (sr16/sr17)."; }
        part sr18DeliverDoDR1 : TestResult { :>> id = "d1832bd6-a955-4b4f-b123-92b543036e31"; :>> outcome = VerdictKind::pass; :>> judgedAgainst = "665aa4d"; :>> judgedAt = "2026-06-24"; :>> judgedBy = "claudeOpus"; }
        action sr19Deliver; // white-box (internal) + black-box (interface) critique over existing boundaries — delivers sr19ServeWhiteboxBoundary (D0100).
        verification sr19DeliverDoD : Test { :>> id = "a1c70153-0153-4153-9153-516273840153"; :>> method = VerificationMethod::demo; :>> procedureText = "Delivers sr19ServeWhiteboxBoundary (Need n17ServeGranularWhitebox), per D0100 (researched: interconnects are typed edges not ports; boundaries from existing structure, not AI clustering; no schema change). FIX: white-box + black-box critique over a BOUNDARY taken from existing strong structure — a Need-slice (a Need + its satisfying SRs + allocated Components + verifying Tests) or a declared view (sr18); boundaries are RECURSIVE/hierarchical (a subsystem is a System-of-Interest at a lower tier). WHITE-BOX = critique the boundary's INTERNAL elements, reusing the existing CritiqueLens (correctness/completeness/consistency/necessity) — NO new lenses. BLACK-BOX = critique the boundary's CUT EDGES (interfaces) for necessity/minimality/completeness; a black-box finding is an Issue referencing the cut edge (endpoints + kind); cut-edge count is a free coupling signal. The tier-satisfaction (driver) comprehensiveness analysis (D0098) is the FIRST sweep target (per Need-slice). AI-proposed graph clustering is DESCOPED (D0100); ports are NOT used (deliverable-domain, D0054). VERIFY (demo): a Need-slice boundary computes its internal set + cut edges; the white-box + black-box critiques record Issues (white-box on elements, black-box referencing cut edges); the tier-satisfaction sweep produces recorded findings (not just a printed view); guard all green; sr19Verify (#Verify -> sr19ServeWhiteboxBoundary) records it. Reuses sr18 (boundary render) + sr16 (recording)."; }
        part sr19DeliverDoDR1 : TestResult { :>> id = "0be19b3b-3d99-4c0d-88ad-09b49713c6fb"; :>> outcome = VerdictKind::pass; :>> judgedAgainst = "0fd9d32"; :>> judgedAt = "2026-06-24"; :>> judgedBy = "claudeOpus"; }

        // ── PRE-v0.1.0 ASSURANCE GAP CLOSURE (from the full-report review 2026-06-24; nothing broken —
        //    evidence-freshness + critique-coverage of recent work). Sequenced A3 (quick) -> A1 -> A2; B1/B2 hygiene. ──
        action reverifyDeliverableAtHead; // A1: re-verify the stale Rust deliverable verifications at HEAD (clears the 14 drift suspects).
        verification reverifyDeliverableAtHeadDoD : Test { :>> id = "a1c70154-0154-4154-9154-516273840154"; :>> method = VerificationMethod::test; :>> procedureText = "A1 (pre-release evidence freshness): 14 deliverable-source-drift suspects (rustS1Lexer..rustS9writeApi, runtimeParser, writeApi, serveItemActions, specVersionRuntimeCheck, rustToolchainFix) + the Rust SRs/Needs they back (sr07/sr10-sr13; n07/n10-n13) carry STALE verification evidence (verified at old commits; source since changed — D0050). This is why coverage reads 73% SR-verified / 70% Needs / 92% assurance while tier-satisfaction (structural) reads 100%. FIX: re-run each verification's actual check at HEAD (cargo test/clippy/parser+BDD, faststart perf timing, spec-pin build.rs, write-API behavior) and append a FRESH TestResult judgedAgainst HEAD per task (write API append-result / append-gate-result) — re-verify, never fabricate. VERIFY: `keel suspect` drift set -> 0; coverage SR-verified -> ~100%, Needs-verified up; assurance report verification-coverage ~100%; guard all green."; }
        part reverifyDeliverableAtHeadDoDR1 : TestResult { :>> id = "a409f3b4-aa6d-4372-a8e1-b3fb9b44ca92"; :>> outcome = VerdictKind::pass; :>> judgedAgainst = "edd7b75"; :>> judgedAt = "2026-06-25"; :>> judgedBy = "claudeOpus"; }

        action critiqueServeRedesign; // A2: Core-3 element-critique the 11 uncritiqued recent elements (serve redesign + latest decisions).
        verification critiqueServeRedesignDoD : Test { :>> id = "a1c70155-0155-4155-9155-516273840155"; :>> method = VerificationMethod::critique; :>> procedureText = "A2 (critique coverage; the sole reason `assured`=NOT READY): 11 elements lack Core-3 element-critique — d0098, d0099, d0100, n15ServeIntrospect, n16ServeCritiqueLoop, n17ServeGranularWhitebox, sr15ServeIntrospect, sr16ServeCritiqueLoop, sr17ServeDirectedNoChat, sr18ServeSectionCritique, sr19ServeWhiteboxBoundary. FIX (element-critique skill, smaller-critique-batches: ~5 elements/pass, one sprint/pass, author critiques.sysml directly, PAUSE per batch for human go/no-go + disposition of any >=Medium finding): run the required lenses per critique-policy (Need/SR -> completeness/correctness/testability; Decision -> completeness/correctness/feasibility) as an INDEPENDENT critic. VERIFY: `keel critique-coverage` -> 100% (0 uncovered); `keel assured` -> READY; every >=Medium finding dispositioned; guard all green."; }
        part critiqueServeRedesignDoDR1 : TestResult { :>> id = "2a9e963f-6d9d-4aba-adec-bbf736d210aa"; :>> outcome = VerdictKind::pass; :>> judgedAgainst = "5cfa65f"; :>> judgedAt = "2026-06-25"; :>> judgedBy = "claudeOpus"; }

        action criticalFindingGatingReview; // resolver for issue050 (A2-batch1 finding): REVIEW the Critical-gating question + record a typed disposition.
        verification criticalFindingGatingReviewDoD : Test { :>> id = "a1c7015a-015a-415a-915a-51627384015a"; :>> method = VerificationMethod::inspect; :>> procedureText = "Resolve issue050 (the d0098 x correctness Medium finding) by REVIEWING the Critical-gating question + recording a typed human disposition. If ACT: revise D0098 so an open CRITICAL finding is a HARD honest-state gate (a left-un-acted Critical IS dishonest state), keeping mere incompleteness non-blocking; add the guard + doc-sync + a revising Decision. If ACCEPT-RISK/DISMISS: record the disposition, no change (the visibility-only posture stands). OUTCOME: the human dispositioned ACCEPT-RISK (issue050Disp1, 2026-06-25) — the visibility-only posture is risk-accepted; D0098 unchanged. The review is complete; the finding is closed by the disposition. VERIFY: issue050 carries a typed disposition (acceptRisk); keel dispositions shows it; guard green."; }
        part criticalFindingGatingReviewDoDR1 : TestResult { :>> id = "a1c7015a-015a-415a-915a-51627384015b"; :>> outcome = VerdictKind::pass; :>> judgedAgainst = "22aa11c"; :>> judgedAt = "2026-06-25"; :>> judgedBy = "claudeOpus"; }

        action sr19StatementAlignD0100; // candidate resolver for issue052 — IF ACT: revise sr19's statement to match the D0100 clustering descope.
        verification sr19StatementAlignD0100DoD : Test { :>> id = "a1c7015b-015b-415b-915b-51627384015b"; :>> method = VerificationMethod::inspect; :>> procedureText = "Resolver for issue052 (sr19 x correctness Medium). The human dispositioned ACT, directing resolution by LINKING (not a statement edit): D0100 was recorded but sr19-linked only in prose. DONE: added a typed `#DependsOn dependency from sr19ServeWhiteboxBoundary to d0100` in requirements.sysml, making the clustering descope traceable from sr19; sr19's statement is preserved as the original intent, governed by the linked D0100. VERIFIED: the typed edge exists; sr19 correctness re-critique (R2) passes (overclaim contextualized by the link); issue052 closed by the ACT disposition; keel validate + guard green."; }
        part sr19StatementAlignD0100DoDR1 : TestResult { :>> id = "a1c7015b-015b-415b-915b-51627384015c"; :>> outcome = VerdictKind::pass; :>> judgedAgainst = "5cfa65f"; :>> judgedAt = "2026-06-25"; :>> judgedBy = "claudeOpus"; }

        action resolveFailingCritiques; // A3: resolve/disposition the 3 unresolved failing critiques (critique_suspect).
        verification resolveFailingCritiquesDoD : Test { :>> id = "a1c70156-0156-4156-9156-516273840156"; :>> method = VerificationMethod::inspect; :>> procedureText = "A3 (quick): 3 elements carry an unresolved FAILING critique (critique_suspect, D0086) holding suspicion — d0003, n14TddBdd, sr14TddBdd. FIX: inspect each failing critique finding; for each, either resolve it (#Resolves resolver if ACT-worthy) or record a typed disposition (acceptRisk/dismiss via apply-review) — never prose. VERIFY: `keel suspect` critique_suspect set -> 0; the 3 elements no longer suspect; guard all green."; }
        part resolveFailingCritiquesDoDR1 : TestResult { :>> id = "fac368f4-a95b-4d3f-ae7d-4f5a0120c449"; :>> outcome = VerdictKind::pass; :>> judgedAgainst = "8227e43"; :>> judgedAt = "2026-06-24"; :>> judgedBy = "claudeOpus"; }

        action autoReverifyReproducible; // IMPROVEMENT (CHANGE): auto-re-verify reproducible method=test verifications at HEAD to lower re-verify friction.
        verification autoReverifyReproducibleDoD : Test { :>> id = "a1c70157-0157-4157-9157-516273840157"; :>> method = VerificationMethod::test; :>> procedureText = "IMPROVEMENT surfaced by the 'why isn't suspicion auto-fixed?' question (2026-06-24). Suspicion is correctly NOT auto-cleared (the engine refuses to fabricate evidence — honest-state D0098); clearing requires actually re-running the check. GAP: for method=test verifications whose evidence is a REPRODUCIBLE command (cargo test/clippy/keel validate/guard), the engine COULD re-run the command at HEAD and append a fresh TestResult automatically — honest (it really ran) + low-friction (D0054). FIX (CHANGE — Decision + acceptance; alters re-verify automation): a `keel reverify [--task T | --all-drift]` that, for drift-suspect reproducible method=test tasks, runs the recorded command, and on green appends a fresh judged-at-HEAD TestResult (on red, leaves it suspect + reports). confirmation/inspect/analyze/demo stay manual (need judgment). VERIFY: `keel reverify --all-drift` re-runs + clears the reproducible drift suspects; a red check stays suspect; never fabricates; doc-sync; guard all green. Supersedes the manual A1 toil going forward."; }
        part autoReverifyReproducibleDoDR1 : TestResult { :>> id = "cfa211f9-218b-45aa-a8e1-b3fb9369d452"; :>> outcome = VerdictKind::pass; :>> judgedAgainst = "edd7b75"; :>> judgedAt = "2026-06-25"; :>> judgedBy = "claudeOpus"; }

        action charterDebtGateCoverage; // B1: gate-cover (or formally accept) the 10 grandfathered pre-D0079 elements.
        verification charterDebtGateCoverageDoD : Test { :>> id = "a1c70158-0158-4158-9158-516273840158"; :>> method = VerificationMethod::inspect; :>> procedureText = "B1 (hygiene; pre-existing debt): 10 grandfathered elements remain not gate-covered (pre-D0079 rigor backlog; quality-debt report 'charter debt (coverage) = 10'). FIX: enumerate them (`keel coverage` uncovered non-governed set), and for each either add reproducible verify evidence OR record a Decision formally accepting the grandfather (scope it out with rationale) — no fabrication. VERIFY: charter-debt (coverage) -> 0; quality-debt report clean; guard all green. (Low release relevance — post-v0.1.0 candidate.)"; }
        part charterDebtGateCoverageDoDR1 : TestResult { :>> id = "1b296977-0545-4648-9e92-5520ff4cb528"; :>> outcome = VerdictKind::pass; :>> judgedAgainst = "a342cac"; :>> judgedAt = "2026-06-25"; :>> judgedBy = "claudeOpus"; }

        action orphanStoryCharterBackfill; // B2: backfill #CharteredBy on the 38 orphan (pre-convention) sprint Stories.
        verification orphanStoryCharterBackfillDoD : Test { :>> id = "a1c70159-0159-4159-9159-516273840159"; :>> method = VerificationMethod::inspect; :>> procedureText = "B2 (hygiene; pre-existing debt): 38 orphan sprint Stories carry no #CharteredBy edge (rootedness burndown orphan=38; pre-D0068 charter convention). The hard gate is clean (0 unrooted #Capability), so non-blocking. FIX (migration skill if bulk): backfill a #CharteredBy edge from each orphan Story to its driving Decision/Need/backlog item (read each sprint's intent; charter to the real origin) — grandfather any with no recoverable origin via a recorded basis, never fabricate. VERIFY: `keel rootedness` orphan -> 0 (or a recorded residual with basis); guard all green. (Low release relevance — post-v0.1.0 candidate.)"; }
        part orphanStoryCharterBackfillDoDR1 : TestResult { :>> id = "2e54d086-e811-4455-9ceb-d96f9e88bc4b"; :>> outcome = VerdictKind::pass; :>> judgedAgainst = "b268730"; :>> judgedAt = "2026-06-25"; :>> judgedBy = "claudeOpus"; }

        action guardRootArgFix; // post-v0.1.0: fix `keel guard <ROOT>` arg parsing (resolves issue053).
        verification guardRootArgFixDoD : Test { :>> id = "a1c7015c-015c-415c-915c-51627384015c"; :>> method = VerificationMethod::test; :>> procedureText = "Resolves issue053 (release-smoke find): `keel guard <ROOT>` misread ROOT as a guard name. FIX: classify_guard_args (main.rs) - a known guard name runs that guard; 'all'/absent/a non-name path runs ALL guards on that ROOT (parity with `keel validate <ROOT>`). VERIFY: `keel guard .` -> ALL PASS (was 'unknown guard .'); `keel guard ceremony` -> runs the one guard; `keel guard ceremony <root>` -> name+root; unit test guard_args_distinguish_name_from_root (D0047 permanent control); clippy + cargo test + keel validate + guard all (14) green."; }
        part guardRootArgFixDoDR1 : TestResult { :>> id = "a1c7015c-015c-415c-915c-51627384015d"; :>> outcome = VerdictKind::pass; :>> judgedAgainst = "8b048fa"; :>> judgedAt = "2026-06-30"; :>> judgedBy = "claudeOpus"; }

        action needsFirstOrderingGuard; // issue054 (downstream-use find): needs-first ordering guard + add-decision write path + point-of-decision capture (PROCESS CHANGE -> CR path).
        verification needsFirstOrderingGuardDoD : Test { :>> id = "0355bd02-7b31-4417-9970-f5362480dce7"; :>> method = VerificationMethod::test; :>> procedureText = "Resolves issue054: Business->Architecture ordering is DEFINED but UNENFORCED + no low-friction decision write path. FIX: (C1) DONE as `keel record decision` (the D0105/D0106 RMWX `record` axis) — scaffolds a PROPOSED Decision file (auto NNNN + UUID) in one call, killing point-of-decision friction (D0054); D0106-corrected: it does NOT emit an acceptance event (acceptance is a SEPARATE explicit human gate, never fabricated); (C2) SUPERSEDED by D0105 (proposed): needs-first ordering becomes a DECLARED EdgeRule (architectural Decision/SystemRequirement -> #DerivedFrom/satisfy -> Need) evaluated by `keel check`, NOT a bespoke `keel guard ordering` — see D0105 + issue055 (do not add a per-defect guard); (C3) engine-triage + the planned UserPromptSubmit hook (issue020/sprint30) require recorded Needs before architecture elicitation + capture decisions at point-of-decision. This is a PROCESS CHANGE -> Decision + acceptance via the Change-Request path (Sec 3a) before implementation; C1/C2 now depend on D0105's declarative-controls direction. VERIFY: add-decision records a green-validating Decision+event; guard ordering flags an architecture-before-needs case + passes when traced; doc-sync; clippy + cargo test + keel validate + guard all green; D0047 permanent control."; }
        part needsFirstOrderingGuardDoDR1 : TestResult { :>> id = "0355bd02-7b31-4417-9970-f5362480dcea"; :>> outcome = VerdictKind::pass; :>> judgedAgainst = "f454ea5"; :>> judgedAt = "2026-07-03"; :>> judgedBy = "claudeOpus"; }

        action analysisChartersResearchSpike; // issue055: give upstream analysis/design a charter home (research spike) so it's tracked, not done in chat (PROCESS CHANGE -> CR path).
        verification analysisChartersResearchSpikeDoD : Test { :>> id = "a1c70160-0160-4160-9160-516273840160"; :>> method = VerificationMethod::inspect; :>> procedureText = "Resolves issue055: substantive analysis/design/research runs untracked in conversation. NOTE (verified in guards.rs/algo.rs): the charter guard checks only #CharteredBy EDGE EXISTENCE, not target type - so the guard ALREADY permits a research Story chartered to an Issue/proposed-Decision; the blocker is convention + missing triage routing, not guard code. FIX (convention-first): (1) D0068 wording blesses a WorkKind::research Story chartering to an Issue or a status=proposed Decision (DoR for a spike) - update the charter guard's MESSAGE string to match; (2) research-spike DoD = a design artifact (e.g. a proposal) + a recorded proposed Decision; (3) update the engine-triage skill (+ the planned UserPromptSubmit hook, issue020/sprint30) to ROUTE substantial design/analysis through a chartered research spike instead of ad-hoc chat; (4) DO NOT add a bespoke charter-target-type guard - if target-type validation is wanted, express it as a declared EdgeRule under the issue054 declarative-controls direction. PROCESS CHANGE -> Decision + acceptance via the Change-Request path (Sec 3a) before implementation. VERIFY: a research Story charters green to an Issue/proposed-Decision (already passes); D0068 + guard message + engine-triage updated; doc-sync (CLAUDE.md Sec 3 triage + Sec 4); guard all green; D0047 control via the EdgeRule path."; }
        part analysisChartersResearchSpikeDoDR1 : TestResult { :>> id = "a1c70160-0160-4160-9160-51627384016f"; :>> outcome = VerdictKind::pass; :>> judgedAgainst = "85e68b8"; :>> judgedAt = "2026-07-03"; :>> judgedBy = "claudeOpus"; }

        action downstreamClaudeMdTemplate; // issue057 (field defect): keel init must ship a DOWNSTREAM CLAUDE.md ('tracked BY keel'), not the self-build's.
        verification downstreamClaudeMdTemplateDoD : Test { :>> id = "a1c70166-0166-4166-9166-516273840166"; :>> method = VerificationMethod::test; :>> procedureText = "Resolves issue057. Author a DOWNSTREAM CLAUDE.md template (a new embedded asset, e.g. keel-cli/assets/claude-md-template.md) framing the new project as TRACKED BY keel — how to work here (text is truth; the AI parses input + drives the CLI, the human supervises; triage-first; substantive work through a sprint), pointing at .engine/reference/ for engine architecture, WITHOUT self-build specifics (no 'this repo IS the engine'; no self-build backlog/decisions/kernel paths). cmd_init writes the TEMPLATE (main.rs:1238), not include_str!(../../CLAUDE.md); the self-build repo keeps its own CLAUDE.md un-shipped. VERIFY: 'keel init' in a temp dir yields a CLAUDE.md that frames the project as tracked BY keel (not 'is keel'); a fresh init project validates; clippy + cargo test + keel validate + guard green; doc-sync (D0093 spin-up). Aligns with D0106 (strict process-boundedness) once accepted."; }
        part downstreamClaudeMdTemplateDoDR1 : TestResult { :>> id = "a1c70166-0166-4166-9166-51627384016c"; :>> outcome = VerdictKind::pass; :>> judgedAgainst = "c8cf7d3"; :>> judgedAt = "2026-07-02"; :>> judgedBy = "claudeOpus"; }

        action oneSourceDecisionAuthoring; // issue058: define one-source-of-truth decision-authoring (no prose restatement of computed/verdict facts) + a detecting rule (D0105 ElementRule).
        verification oneSourceDecisionAuthoringDoD : Test { :>> id = "a1c70168-0168-4168-9168-516273840168"; :>> method = VerificationMethod::inspect; :>> procedureText = "Resolves issue058 (ad-hoc authoring -> dual-truth). (1) Define a decision-authoring discipline (a process + deploying skill): each fact has ONE canonical home; acceptance/verdict/critique-state/status are structured (a TestResult) or COMPUTED, NEVER restated as prose; a decision's prose fields (context/decision/rationale/consequences) describe only its own what/why/impact. (2) A DETECTING rule under D0105 (an ElementRule): a Decision must not carry acceptance-verdict prose (e.g. an '(ACCEPTED <date> by <who>)' header/field) when its AcceptR1 TestResult exists. (3) 'status computed from the acceptance event' folds into guardsToRulesMigration (acceptance-events -> EdgeRule; status -> computed #View; the superseded state stays explicit, so status is a guarded cross-check, not pure redundancy). PROCESS CHANGE -> Decision + acceptance via the CR path (Sec 3a); the detecting rule ships with the declarative evaluator. VERIFY: the discipline is a deployed process/skill; no decision restates its acceptance verdict as prose; keel validate + guard green. Immediate cleanup (D0105/D0106 headers + D0105 consequences) already committed."; }
        part oneSourceDecisionAuthoringDoDR1 : TestResult { :>> id = "a1c70168-0168-4168-9168-51627384016f"; :>> outcome = VerdictKind::pass; :>> judgedAgainst = "551db09"; :>> judgedAt = "2026-07-04"; :>> judgedBy = "wweatherholtz"; }
        // R1's 'close as covered' (2026-07-04) was REVISED by the human 2026-07-05: enforceable = a defined
        // process that is CARRIED OUT. R2 supersedes it — the DoD's part (1) (a process + deploying skill) is
        // now genuinely delivered: .engine/processes/decision-authoring.sysml + the decision-authoring skill
        // (non-inert per D0059/process-skill), backstopped by decisionNoVerdictProseRule + guard:confirmation-authenticity.
        part oneSourceDecisionAuthoringDoDR2 : TestResult { :>> id = "a1c70168-0168-4168-9168-51627384016e"; :>> outcome = VerdictKind::pass; :>> judgedAgainst = "551db09"; :>> judgedAt = "2026-07-05"; :>> judgedBy = "claudeOpus"; }

        action strictProcessOperationalization; // D0106 (proposed): operationalize strict process-boundedness in CLAUDE.md Sec 3 + engine-triage (BLOCKED on D0106 sign-off).
        verification strictProcessOperationalizationDoD : Test { :>> id = "a1c70167-0167-4167-9167-516273840167"; :>> method = VerificationMethod::inspect; :>> procedureText = "Per D0106 (proposed; HELD until human sign-off). Operationalize strict process-boundedness: (1) CLAUDE.md Sec 3 — the AI PARSES every input into a VISIBLE enumerated decomposition (each part labelled TRIVIAL/CHANGE/EXECUTE/RECORD/VIEW/ORIENT), routes each non-trivial part to a defined process, DEFINES a process when none fits, executes (parallel where the dependency DAG allows); the trivial fast-path is retained but LABELLED, never silent. (2) engine-triage skill — emit the 'Parsed:' block every turn; sign-off is an explicit method=confirmation gate step (D0016/D0066), never inferred from a general instruction. (3) doc-sync. VERIFY: CLAUDE.md Sec 3 + engine-triage updated; the parsed-output format is the standard opening of every response; keel validate + guard green. HELD until D0106 is accepted via its explicit sign-off gate."; }
        part strictProcessOperationalizationDoDR1 : TestResult { :>> id = "a1c70167-0167-4167-9167-51627384016b"; :>> outcome = VerdictKind::pass; :>> judgedAgainst = "4873cd3"; :>> judgedAt = "2026-07-02"; :>> judgedBy = "claudeOpus"; }

        action declarativeControlsEvaluator; // D0105: generic model-driven evaluator + declared Rule schema (EdgeRule/ElementRule) + `keel check` + closed RMWX verb axis (PROPOSED — schema/core sign-off).
        verification declarativeControlsEvaluatorDoD : Test { :>> id = "a1c70161-0161-4161-9161-516273840161"; :>> method = VerificationMethod::inspect; :>> procedureText = "Per D0105 (proposed) + docs/proposals/2026-06-30-declarative-controls-issue054.md. Build the declarative-controls core: (1) schema/core adds `EdgeRule` (subject type/marker + requiredEdge + object type + cardinality + scope + severity + onViolation) and `ElementRule` (subject type + predicate composed from a CLOSED vocabulary: nonBlank/minLength/matchesPattern/inRegistry/distinct/referentExists/resolvesToCommand/countCompare), each carrying a justifiedBy edge to its Decision — FROZEN-CORE, needs HUMAN SIGN-OFF; (2) a generic `keel check` evaluator runs EdgeRules (graph queries), ElementRules (predicate vocabulary), and ORDERING from the existing workflow succession at instance level; (3) the closed RMWX verb axis (read/record/modify/execute) generic over the model, triage = (verb x targetType)->process. EXTENDS D0088 (constraint layer). VERIFY: `keel check` evaluates declared rules; ordering derived from business.sysml succession; a sample EdgeRule + ElementRule round-trip; clippy + cargo test + keel validate + check all green; doc-sync CLAUDE.md Sec 3 + Sec 5."; }
        part declarativeControlsEvaluatorDoDR1 : TestResult { :>> id = "a1c70161-0161-4161-9161-51627384016f"; :>> outcome = VerdictKind::pass; :>> judgedAgainst = "85e68b8"; :>> judgedAt = "2026-07-03"; :>> judgedBy = "claudeOpus"; }

        action guardsToRulesMigration; // D0105: migrate the 14 bespoke guards -> declared EdgeRule/ElementRule with a PARITY gate; reconcile the TOML contracts; reframes D0047 (D0067 expand/migrate/contract).
        verification guardsToRulesMigrationDoD : Test { :>> id = "a1c70162-0162-4162-9162-516273840162"; :>> method = VerificationMethod::inspect; :>> procedureText = "Per D0105 (proposed). Migrate via D0067 (expand/migrate/contract): express the ~8 conformance guards (ceremony/sprint-coverage/requirement-rootedness/issues/process-skill/charter/process-change/decision-requirement-link) as declared EdgeRules and the ~5 structural guards (actors/decision-rationale/critic-independence/manifest-coverage/viewpoint-renderer) as declared ElementRules; RECONCILE critique-policy.toml + reverify.toml into the model (governance->Rule; execution params referenced by a Rule) per fork #1. PARITY GATE (the safety mechanism): `keel check` output MUST equal the 14 guards' output on the current repo before any Rust predicate is retired (precedent: the retired python/rust parity check). REFRAMES D0047 (corrections become declared rules, not new code). VERIFY: parity proven (check == guards) on the live repo + a synthetic violation each; guards retired only after parity holds; clippy + cargo test + keel validate green; doc-sync."; }
        part guardsToRulesMigrationDoDR1 : TestResult { :>> id = "a1c70162-0162-4162-9162-51627384016f"; :>> outcome = VerdictKind::pass; :>> judgedAgainst = "85e68b8"; :>> judgedAt = "2026-07-03"; :>> judgedBy = "claudeOpus"; }

        action businessArchSkillAndWorkflowGuard; // D0105 / issue054-F1 root: author the missing Business/Architecture deploying skill (D0059) + extend process-skill coverage to .engine/workflows/.
        verification businessArchSkillAndWorkflowGuardDoD : Test { :>> id = "a1c70163-0163-4163-9163-516273840163"; :>> method = VerificationMethod::inspect; :>> procedureText = "Per D0105 (proposed); the REAL root of issue054 F1. The Business + Architecture workflows are inert (defined, no deploying skill, contra D0059), and the process-skill guard scans only .engine/processes/, not .engine/workflows/ — so a keel-blind external brainstorming skill filled the vacuum (prose + uncaptured decisions in the wrong order). FIX: (1) author a keel-native design/business skill that DEPLOYS the Business+Architecture workflows — runs the scoping dialogue recording each decision as a (proposed) Decision at point-of-decision, Needs before architecture Decisions; (2) extend the process-skill check (as a declared EdgeRule under D0105, or the existing guard) to require a deploying skill for every .engine/workflows/*.sysml, closing the blind spot. SCOPE (D0105 now accepted): Part 1 (the deploying skill) is delivered here; Part 2 (workflow-coverage ENFORCEMENT) is now a declared EdgeRule folded into guardsToRulesMigration — NOT a bespoke Rust guard (D0105). VERIFY: the business-architecture skill exists (.engine/skills/business-architecture/SKILL.md) + is registered (skills-registry businessArchitectureSkill), names the two workflows it deploys; kernel validate_instances PASS (registry); keel validate + guard all green; doc-sync. The workflow-coverage EdgeRule is tracked in guardsToRulesMigration."; }
        part businessArchSkillAndWorkflowGuardDoDR1 : TestResult { :>> id = "a1c70163-0163-4163-9163-51627384016d"; :>> outcome = VerdictKind::pass; :>> judgedAgainst = "e96b36f"; :>> judgedAt = "2026-07-02"; :>> judgedBy = "claudeOpus"; }

        action serveBusinessNeedsView; // D0105 / serve gap: add the Business/Needs browser to `keel serve` (the console has no Brief/Need/UseCase view).
        verification serveBusinessNeedsViewDoD : Test { :>> id = "a1c70164-0164-4164-9164-516273840164"; :>> method = VerificationMethod::test; :>> procedureText = "Per D0105 (proposed). `keel serve` renders orient/decisions/dispositions/processes/reports/recent/history + generic item/section, but has NO Business/Needs view — the Brief/Need/UseCase layer is invisible in the console (the gap the human hit: 'serve isn't showing me the business sysml data'). FIX: add a Business/Needs browser (api route + console tab) rendering the Brief, Needs (with satisfy/derive/verify trace), and UseCases as a computed #View. VERIFY: `keel serve` shows the Business layer for a project with authored Needs; renders the Need->requirement->verification trace; clippy + cargo test + keel validate + guard all green; doc-sync."; }
        part serveBusinessNeedsViewDoDR1 : TestResult { :>> id = "a1c70164-0164-4164-9164-51627384016e"; :>> outcome = VerdictKind::pass; :>> judgedAgainst = "51fa537"; :>> judgedAt = "2026-07-03"; :>> judgedBy = "claudeOpus"; }

        action d0105CritiqueResiduals; // issue056: residual D0105-critique findings needing a HUMAN — C11 (acceptance/procedural soundness) + C12 (two-thread coordination protocol).
        verification d0105CritiqueResidualsDoD : Test { :>> id = "a1c70165-0165-4165-9165-516273840165"; :>> method = VerificationMethod::confirmation; :>> procedureText = "Resolves issue056 (residual findings from the independent D0105 critique that an AI cannot self-resolve). C11: the HUMAN explicitly accepts or rejects D0105 (method=confirmation, the frozen-core sign-off) — is an AI-authored proposed decision reframing D0047/D0088 procedurally acceptable, and is the reworked D0105 sound? Per the confirmation rule a general 'continue' is NOT this sign-off. C12: record a two-thread coordination protocol (which thread owns the engine model; what the implementing thread may change without re-authorization; how divergence is adjudicated). VERIFY: a recorded human acceptance/rejection of D0105 (disposition of C11) + a recorded coordination protocol (C12); guard all green."; }
        part d0105CritiqueResidualsDoDR1 : TestResult { :>> id = "a1c70165-0165-4165-9165-51627384016f"; :>> outcome = VerdictKind::pass; :>> judgedAgainst = "50a98a9"; :>> judgedAt = "2026-07-03"; :>> judgedBy = "wweatherholtz"; }

        // ── Retrospective-finding resolvers (2026-07-04) — tracked, not yet done. ──
        action strictProcessGate; // issue059: make D0106 a real control (not vigilance/reminder-only).
        verification strictProcessGateDoD : Test { :>> id = "a1c70169-0169-4169-9169-516273840169"; :>> method = VerificationMethod::test; :>> procedureText = "Resolves issue059. Make D0106 (strict process-boundedness) an ENFORCED control, not a reminder: a commit-time check that substantive work carries process linkage (a covering sprint/charter, or a recorded route) and that any method=confirmation result carries a real attestation — so an ad-hoc edit / uncaptured decision / fabricated confirmation is BLOCKED, not merely discouraged. Builds on the planned UserPromptSubmit hook (issue020/sprint30). PROCESS CHANGE -> Decision + acceptance (Sec 3a). VERIFY: the gate flags a synthetic ad-hoc/unlinked change + passes a properly-routed one; clippy + cargo test + keel validate + guard green; D0047 permanent control. RESOLVED at human-adjudicated scope (2026-07-04): the ATTESTATION-AUTHENTICITY half is a live HARD gate (confirmation-authenticity, sprint191 — an accepted Decision's acceptance must be human-judged, never AI-fabricated). The human ADJUDICATED (explicit choice 'Accept current + close') that this gate + the existing process-linkage guards (sprint-coverage/charter/process-change) are SUFFICIENT for the commit-gatable surface, and that the conversational parse-first part is ACCEPTED as reminder-only (inherently un-gatable at commit). Not overclaimed — the residual is a recorded accepted-limitation, not a hidden gap."; }
        part strictProcessGateDoDR1 : TestResult { :>> id = "a1c70169-0169-4169-9169-51627384016f"; :>> outcome = VerdictKind::pass; :>> judgedAgainst = "551db09"; :>> judgedAt = "2026-07-04"; :>> judgedBy = "wweatherholtz"; } // issue060: prove the migration ROI (delete guard code) OR rescope (remove unused OrderingRule, free keel check).
        // The `action` line was missing while its DoD and a PASSING TestResult (3309949, 2026-07-04)
        // sat right below it, so `#Resolves ... from declarativeControlsRoiOrRescope to issue060`
        // pointed at nothing and issue060 read as triaged by a resolver that did not exist.
        // Restored rather than reconstructed: the DoD and result are committed records of what this
        // was and that it was done (issue109).
        action declarativeControlsRoiOrRescope;
        verification declarativeControlsRoiOrRescopeDoD : Test { :>> id = "a1c7016a-016a-416a-916a-51627384016a"; :>> method = VerificationMethod::inspect; :>> procedureText = "Resolves issue060. Decide the declarative-controls end-state honestly: EITHER prove ROI — migrate enough further guards that Rust guard code is actually DELETED (net code down) + free the `keel check` name for the evaluator + extend the RMWX record axis beyond one verb; OR rescope — remove the unused OrderingRule kind from schema/core (dead schema), keep the mechanism explicitly as 'downstream-declarable, minimal engine use', and correct D0105's 'code stays flat' claim. Either way: no dead schema, no unproven headline. PROCESS CHANGE. VERIFY: OrderingRule either used or removed; net-code direction stated with evidence; keel validate + guard + kernel green; doc-sync CLAUDE.md Sec 5."; }
        part declarativeControlsRoiOrRescopeDoDR1 : TestResult { :>> id = "a1c7016a-016a-416a-916a-51627384016f"; :>> outcome = VerdictKind::pass; :>> judgedAgainst = "3309949"; :>> judgedAt = "2026-07-04"; :>> judgedBy = "claudeOpus"; }

        action proveProcessDeployment; // issue061: exercise the business-architecture skill on a real design + route analysis via the issue059 gate.
        verification proveProcessDeploymentDoD : Test { :>> id = "a1c7016b-016b-416b-916b-51627384016b"; :>> method = VerificationMethod::inspect; :>> procedureText = "Resolves issue061. Prove the new deployments are real, not inert: (1) run the business-architecture skill END-TO-END on the next genuine design/scoping request (Brief->Needs->accepted->architecture Decisions, all authored, needs-before-architecture) and record that it produced tracked facts not chat; (2) tie research-spike routing (issue055) to the issue059 strict-process gate so substantial analysis is routed by a control. VERIFY: a real design session ran through the skill (evidence: the authored Business/Architecture items + point-of-decision Decisions); analysis-routing enforced not vigilance; guard green. Depends on strictProcessGate (issue059)."; }
        part proveProcessDeploymentDoDR1 : TestResult { :>> id = "1baae692-afe2-4b55-890e-a3d4ce28bd0b"; :>> outcome = VerdictKind::pass; :>> judgedAgainst = "5f82eec"; :>> judgedAt = "2026-07-14"; :>> judgedBy = "claudeOpus"; }

        action hardenVerdictProseRule; // issue062: positive test + broaden + decide gating for the dual-truth detecting rule.
        verification hardenVerdictProseRuleDoD : Test { :>> id = "a1c7016c-016c-416c-916c-51627384016c"; :>> method = VerificationMethod::test; :>> procedureText = "Resolves issue062. Harden decisionNoVerdictProseRule: (1) add a POSITIVE test fixture (a synthetic decision that restates its acceptance verdict as prose, which the rule MUST flag) so the catch path is proven, not just the 0-hit clean path; (2) broaden the pattern beyond the single 'ACCEPTED 202' substring to catch other verdict-prose forms; (3) decide whether to PROMOTE it to a blocking rule/guard once low-noise (the D0102 warning->hard precedent). VERIFY: the rule flags the positive fixture + still 0 on the live repo; clippy + cargo test green; keel validate + guard green."; }
        part hardenVerdictProseRuleDoDR1 : TestResult { :>> id = "a1c7016c-016c-416c-916c-51627384016f"; :>> outcome = VerdictKind::pass; :>> judgedAgainst = "3309949"; :>> judgedAt = "2026-07-04"; :>> judgedBy = "claudeOpus"; }

        // ── Field/retro-finding resolvers (2026-07-14, keel-serve dogfood + retro audit) — tracked, not yet done. ──
        action fixServeOrientPerf; // issue063: cut orient's git-subprocess storm (criterion-drift) that spikes serve first-load to 16-23s.
        verification fixServeOrientPerfDoD : Test { :>> id = "a1c70170-0170-4170-9170-516273840170"; :>> method = VerificationMethod::test; :>> procedureText = "Resolves issue063 (field-discovered via keel serve). ROOT (measured, corrected from 'hundreds'): orient spawns 19 git processes — batched cat-file (2) + a per-task fallback (git_criterion_at: git ls-tree + N git show) firing for ~5 done tasks whose dep DoD moved files; the fallback = ~15 avoidable spawns whose Windows CreateProcess/Defender tail amplifies to the intermittent 16-23s spike. FIX (perf-only, orient output UNCHANGED = not a view-meaning change, so EXECUTE not CHANGE): (a) git_criterion_at now does ONE `git grep -h -F` for the DoD's single-line declaration at the commit instead of ls-tree + N shows (extraction identical -> byte-identical orient); (b) the serve `cached` compute runs via tokio::task::block_in_place so a slow cold compute never STARVES the multi-thread runtime's worker. VERIFIED: orient JSON byte-identical before/after (diff clean); git spawns 19->9; A/B n=40 each (CLI cold): median 1211->847ms, p95 1769->1077ms, max 1820->1145ms (whole distribution down ~35%); NEW n=100: median 841, p99 1154, MAX 1154ms, 0 spikes >3s; live serve concurrency: a /api/item returned 0.29s WHILE orient computed 1.03s (no worker starvation). HONEST LIMIT: the 16-23s spikes are too rare (~1/50, external) to A/B statistically — the win is the measured distribution shift + halved spawn count (fewer spike opportunities), not a proof the spike rate dropped. clippy + cargo test (80) + keel validate + guard green."; }
        part fixServeOrientPerfDoDR1 : TestResult { :>> id = "58c60839-4adc-4460-ac1f-4213945a6ca4"; :>> outcome = VerdictKind::pass; :>> judgedAgainst = "50238fc"; :>> judgedAt = "2026-07-14"; :>> judgedBy = "claudeOpus"; }

        action surfaceDodDescription; // issue064: the console shows action/ready items as empty (+ a NextWork contains-edge), hiding the DoD procedureText.
        verification surfaceDodDescriptionDoD : Test { :>> id = "a1c70171-0171-4171-9171-516273840171"; :>> method = VerificationMethod::test; :>> procedureText = "Resolves issue064 (field-discovered via keel serve). An action task (e.g. proveProcessDeployment) genuinely has no authored attrs — correct — but its description lives in the verify-linked <task>DoD Test's procedureText, which the element view never surfaces; it shows the low-value structural `contains` edge from the NextWork action-def container instead, so a well-specified task LOOKS empty. FIX: the element/console view resolves <task>DoD (the verify-linked Test) and presents its procedureText (+ method) as the task's description. VERIFY: viewing a ready action in the console/element view shows its DoD criterion text; clippy + cargo test + keel validate + guard green."; }
        part surfaceDodDescriptionDoDR1 : TestResult { :>> id = "2aed59e5-19f2-42b9-96e3-a1e18fd8908f"; :>> outcome = VerdictKind::pass; :>> judgedAgainst = "f4ae61b"; :>> judgedAt = "2026-07-14"; :>> judgedBy = "claudeOpus"; }

        action osAdaptiveCommandGuidance; // issue065: AI shell guidance is Windows-hardcoded + the downstream keel-init template ships NO OS guidance.
        verification osAdaptiveCommandGuidanceDoD : Test { :>> id = "a1c70172-0172-4172-9172-516273840172"; :>> method = VerificationMethod::inspect; :>> procedureText = "Resolves issue065 (retro finding; generalizes issue013). CLAUDE.md Sec 6 is hardcoded to Windows/PowerShell/miniforge, and the shipped downstream template (keel-cli/assets/claude-md-template.md) has NO OS/env section — so future AI (here when a shell tool glitches; downstream on macOS/Linux) makes avoidable shell-mismatch mistakes. FIX: state the PRINCIPLE (detect + adapt to the host OS/shell; use OS-appropriate command forms; verify the shell before assuming syntax) in the operating guidance, keeping the Windows specifics as this repo's concrete instance; add a short OS/shell section to the downstream template so init'd projects on any OS inherit it. Record a lightweight convention Decision if it rises to one. VERIFY: CLAUDE.md Sec 6 states the OS-adaptive principle; the template carries an OS/shell section; doc-sync; keel validate + guard green."; }
        part osAdaptiveCommandGuidanceDoDR1 : TestResult { :>> id = "e05ee89c-3d01-41a8-a39b-3633b118d320"; :>> outcome = VerdictKind::pass; :>> judgedAgainst = "b794280"; :>> judgedAt = "2026-07-14"; :>> judgedBy = "claudeOpus"; }

        action jvmRetirementSpike; // issue066: RESEARCH SPIKE — scope whether the Rust validator can cover .engine SysML semantics to retire the JVM kernel entirely.
        verification jvmRetirementSpikeDoD : Test { :>> id = "a1c70173-0173-4173-9173-516273840173"; :>> method = VerificationMethod::inspect; :>> procedureText = "Resolves issue066 (architecture opportunity from the D0048 review). D0048 kept the JVM kernel as the .engine schema/workflow/instance SysML oracle (deep semantics the Rust validator does not cover); so engine commits still need conda + a ~20s JVM start and inherit an environment-fragile dependency. This is a WorkKind::research SPIKE (chartered to issue066 or a proposed Decision, per researchSpikeCharterRule/D0111): enumerate EXACTLY which checks the kernel validators (validate_schema/workflows/instances) perform that Rust does not, assess the cost/feasibility of replicating them in Rust, and produce a design artifact + a PROPOSED Decision on whether to retire the kernel entirely (with a migration path if yes). Implementation is a follow-on program gated on human acceptance. VERIFY: a design artifact enumerating the semantic gap + a recorded proposed Decision; keel validate + guard green."; }
        part jvmRetirementSpikeDoDR1 : TestResult { :>> id = "3707ab4f-b629-4b18-b651-a5f243fda37c"; :>> outcome = VerdictKind::pass; :>> judgedAgainst = "f0c081f"; :>> judgedAt = "2026-07-14"; :>> judgedBy = "claudeOpus"; }

        action engineRefResolver; // issue067 + D0112 phase 2: a Rust .engine reference resolver = the kernel-free backstop SKIP_VALIDATE + Rust-only CI currently lack.
        verification engineRefResolverDoD : Test { :>> id = "a1c70174-0174-4174-9174-516273840174"; :>> method = VerificationMethod::test; :>> procedureText = "Resolves issue067 + delivers D0112 phase 2. DELIVERED: `keel check-engine` (lib::validate_engine_instances) registers ALL .engine packages then runs the SAME PackageRegistry::validate used for .tracking against the .engine INSTANCE files (decisions/processes/views + skills-registry + tracking-template; schema/workflow defs registered-not-validated) — KERNEL-FREE. Catches the `unresolved` class: unresolved type references + unknown import namespaces (the two the kernel's error-keyword set flags). Cross-file refs resolve (Rust registers all first — the advantage over the per-file kernel, issue021/024). WIRED as the SKIP_VALIDATE-proof backstop: added to ci.yml (Rust-only CI now runs keel validate + guard + check-engine, so a hook-skipped commit is still caught) AND to .githooks/pre-commit (local, kernel-free). SCOPE HONESTY: name/type EXISTENCE, NOT full type-conformance/specialization (that residual stays the kernel's, D0112 phase 3 — the kernel is not removed). VERIFIED: check-engine clean on the live repo (0 false positives); a synthetic broken probe flagged BOTH `unknown import namespace` + `unresolved type reference`; is_engine_instance_file unit test; clippy --workspace --all-targets + cargo test (82) + keel validate + guard green; doc-sync CLAUDE.md §5. Governed by D0112 (#ProspectiveChange)."; }
        part engineRefResolverDoDR1 : TestResult { :>> id = "a66be8dd-6fdf-4516-b919-d0ba8668ce26"; :>> outcome = VerdictKind::pass; :>> judgedAgainst = "0c9985a"; :>> judgedAt = "2026-07-14"; :>> judgedBy = "claudeOpus"; }

        // ── keel-viewer implementation backlog (D0114 shape B; keel-SIDE deliverables — the viewer app is a SEPARATE project consuming these). Not yet done. ──
        action viewerKeelApi; // srViewerKeelApi (N-6): the versioned keel read/query/graph/temporal API — the enabling first increment for shape B.
        verification viewerKeelApiDoD : Test { :>> id = "a1c70180-0180-4180-9180-516273840180"; :>> method = VerificationMethod::test; :>> procedureText = "Satisfies srViewerKeelApi (N-6, D0114 shape B). Promote keel serve's /api/* into a STABLE, VERSIONED read/query/graph/temporal API: an explicit version string; documented request/response contracts; endpoints for run-a-viewpoint (select/traverse/project), element+neighbours, seed-expand-to-depth, and temporal state. Breaking changes bump the version. This is the enabling first increment — the separate viewer app consumes it. VERIFY: versioned endpoints documented + tested; a client can drive a viewpoint end-to-end; clippy + cargo test + keel validate + guard green. #Verify srViewerKeelApi."; }
        part viewerKeelApiDoDR1 : TestResult { :>> id = "559de651-7d06-4617-bb4c-fca9e01482a5"; :>> outcome = VerdictKind::pass; :>> judgedAgainst = "a0371ac"; :>> judgedAt = "2026-07-15"; :>> judgedBy = "claudeOpus"; }

        // (viewerTemporalState removed — D0116: no due/overdue state; temporal = time-as-query-filter via viewerDatePredicates/N-5.)

        action viewerGraphExpand; // srViewerGraphExpand (N-2): seed+expand, incremental, stable-layout graph.
        verification viewerGraphExpandDoD : Test { :>> id = "a1c70182-0182-4182-9182-516273840182"; :>> method = VerificationMethod::demo; :>> procedureText = "Satisfies srViewerGraphExpand (N-2). Seed-and-expand graph: load neighbours on demand, drill-into-detail, STABLE layout that doesn't re-shuffle on expand; incremental loading so it stays interactive past the ~2,500-node freeze point. VERIFY (demo): expand from a seed on a >2500-node model without a freeze; layout stability shown. #Verify srViewerGraphExpand."; }
        part viewerGraphExpandDoDR1 : TestResult { :>> id = "d8b04bab-9df7-4d23-bb4c-fca9ea772595"; :>> outcome = VerdictKind::pass; :>> judgedAgainst = "a0371ac"; :>> judgedAt = "2026-07-15"; :>> judgedBy = "claudeOpus"; }

        action viewerVisualViewpoint; // srViewerVisualViewpoint (N-1): declarable visual form + audience.
        verification viewerVisualViewpointDoD : Test { :>> id = "a1c70183-0183-4183-9183-516273840183"; :>> method = VerificationMethod::test; :>> procedureText = "Satisfies srViewerVisualViewpoint (N-1). A viewpoint declares a chosen VISUAL form (layout/grouping/styling) for its named audience, rendered accordingly — beyond the 3 fixed modes; unknown directives fail loud. RESOLVE open question Q4 first (authoring surface: extend .view.toml / new artifact / presentation layer). VERIFY: a declared visual viewpoint renders per its form + audience; unknown directive fails loud; clippy + cargo test + keel validate + guard green. #Verify srViewerVisualViewpoint."; }
        part viewerVisualViewpointDoDR1 : TestResult { :>> id = "cb97b922-9d5d-460f-bb4c-fca9f3b1295d"; :>> outcome = VerdictKind::pass; :>> judgedAgainst = "a0371ac"; :>> judgedAt = "2026-07-15"; :>> judgedBy = "claudeOpus"; }

        action viewerConfigurableSlice; // srViewerConfigurableSlice (N-4): configurable-depth, edge-selectable slice from a seed.
        verification viewerConfigurableSliceDoD : Test { :>> id = "a1c70184-0184-4184-9184-516273840184"; :>> method = VerificationMethod::test; :>> procedureText = "Satisfies srViewerConfigurableSlice (N-4). From any seed, produce a slice over CONFIGURABLE depth + a SELECTABLE typed-edge set, returning only the connected subgraph — generalizing the fixed 1-hop element_neighbourhood / Need-only need_slice. VERIFY: a seed slice at depth N over chosen edges returns exactly the connected subgraph; clippy + cargo test + keel validate + guard green. #Verify srViewerConfigurableSlice."; }
        part viewerConfigurableSliceDoDR1 : TestResult { :>> id = "753dba14-d06f-429a-a94a-55e420ac4afe"; :>> outcome = VerdictKind::pass; :>> judgedAgainst = "109fa45"; :>> judgedAt = "2026-07-14"; :>> judgedBy = "claudeOpus"; }

        action viewerDatePredicates; // srViewerDatePredicates (N-5): bounded date/range (+ likely OR) query predicates.
        verification viewerDatePredicatesDoD : Test { :>> id = "a1c70185-0185-4185-9185-516273840185"; :>> method = VerificationMethod::test; :>> procedureText = "Satisfies srViewerDatePredicates (N-5). Add date/range predicates (and likely OR) to the view query vocabulary — enough for temporal (N-3) + stakeholder filtering — while remaining a BOUNDED fixed vocabulary. RESOLVE open question Q3 first (the bound). VERIFY: a date-range viewpoint predicate selects correctly; the vocabulary stays fixed (no arbitrary expression); clippy + cargo test + keel validate + guard green. #Verify srViewerDatePredicates."; }
        part viewerDatePredicatesDoDR1 : TestResult { :>> id = "c8f11456-7a08-41ae-8983-e54558818ea6"; :>> outcome = VerdictKind::pass; :>> judgedAgainst = "4d9e10b"; :>> judgedAt = "2026-07-15"; :>> judgedBy = "claudeOpus"; }

        // ── keel-viewer expansion backlog (SRs from accepted Needs N-10, N-12, N-13; rest superseded by D0115). Not yet done. ──
        action viewerChangeImpact; // srViewerChangeImpact (N-10): downstream dependents of a seed (inverse slice).
        verification viewerChangeImpactDoD : Test { :>> id = "a1c70187-0187-4187-9187-516273840187"; :>> method = VerificationMethod::test; :>> procedureText = "Satisfies srViewerChangeImpact (N-10). From a seed, compute downstream dependents over configurable typed edges, grouped by distance, cycles shown once. VERIFY: a seed with dependents lists them by distance; a cycle terminates; a leaf reads 'nothing depends on this'; clippy + cargo test + keel validate + guard green. #Verify srViewerChangeImpact."; }
        part viewerChangeImpactDoDR1 : TestResult { :>> id = "8e2c9035-7c3c-483e-ac4f-6dd7e240af7a"; :>> outcome = VerdictKind::pass; :>> judgedAgainst = "dbb5287"; :>> judgedAt = "2026-07-15"; :>> judgedBy = "claudeOpus"; }
        action viewerExportShare; // srViewerExportShare (N-12): export a reproducible viewpoint snapshot.
        verification viewerExportShareDoD : Test { :>> id = "a1c70189-0189-4189-9189-516273840189"; :>> method = VerificationMethod::demo; :>> procedureText = "Satisfies srViewerExportShare (N-12). Export a viewpoint as a snapshot (link/file) stamped with as-of date + scope + source commit; oversized -> scoped subset with a note. VERIFY (demo): a snapshot round-trips to the same view from its as-of commit; clippy + cargo test + keel validate + guard green. #Verify srViewerExportShare."; }
        part viewerExportShareDoDR1 : TestResult { :>> id = "a863b201-4802-4041-8aba-e07bc66482ab"; :>> outcome = VerdictKind::pass; :>> judgedAgainst = "041978f"; :>> judgedAt = "2026-07-15"; :>> judgedBy = "claudeOpus"; }
        action viewerBaselineCompare; // srViewerBaselineCompare (N-13): diff a viewpoint across two times/baselines.
        verification viewerBaselineCompareDoD : Test { :>> id = "a1c7018a-018a-418a-918a-51627384018a"; :>> method = VerificationMethod::test; :>> procedureText = "Satisfies srViewerBaselineCompare (N-13). Diff a viewpoint between two points (dates/baselines) using git history; highlight added/removed/changed/re-verified; predating element -> 'added since'. VERIFY: a known change between two commits is classified correctly; no-change reads 'no drift'; clippy + cargo test + keel validate + guard green. #Verify srViewerBaselineCompare."; }
        part viewerBaselineCompareDoDR1 : TestResult { :>> id = "4086af91-5739-4937-8ff1-f4f94ef82f9d"; :>> outcome = VerdictKind::pass; :>> judgedAgainst = "e995440"; :>> judgedAt = "2026-07-15"; :>> judgedBy = "claudeOpus"; }

        // ── keel-viewer CRITIQUE backlog (accepted Needs N-15, N-16; the human's core goal). Not yet done. ──
        action viewerIterativeCritique; // srViewerIterativeCritique (N-15): axis-iterated AI critique over a query.
        verification viewerIterativeCritiqueDoD : Test { :>> id = "a1c7018c-018c-418c-918c-51627384018c"; :>> method = VerificationMethod::test; :>> procedureText = "Satisfies srViewerIterativeCritique (N-15). Run AI critique iteratively over a constrained query result, iterating over one axis (per element), a chosen lens, one tracked critique per element via apply-review (independent-critic + provenance). Support the process+downstream (best-practice) and requirement+downstream (semantic-sufficiency) flows. Reuse element-critique + the serve agent bridge. VERIFY: iterating a 3-element query yields 3 recorded critiques with correct lens/provenance; a requirement-comprehensiveness run reports a semantic gap; clippy + cargo test + keel validate + guard green. #Verify srViewerIterativeCritique."; }
        part viewerIterativeCritiqueDoDR1 : TestResult { :>> id = "32b347ec-764b-4edd-ae15-5abdd1c15967"; :>> outcome = VerdictKind::pass; :>> judgedAgainst = "bb92640"; :>> judgedAt = "2026-07-15"; :>> judgedBy = "claudeOpus"; }
        action viewerInProgramEdit; // srViewerInProgramEdit (N-16): modify facts via keel PROCESSES (decision/supersede/apply-review) in-program + re-critique.
        verification viewerInProgramEditDoD : Test { :>> id = "a1c7018d-018d-418d-918d-51627384018d"; :>> method = VerificationMethod::test; :>> procedureText = "Satisfies srViewerInProgramEdit (N-16, human-clarified: modify via keel PROCESSES, not rogue edits). Surface keel's disciplined write operations in-program: record a Decision, supersede a Need (change-a-fact = a superseding Decision, §2.4), apply-review, append-result, add-task — through the guarded write API; then re-critique on the same surface. A guard-rejected write is refused inline; a concurrent change flags a conflict (D0108). Reuse the existing write API (write.rs) + apply-review; NO raw field mutation, no second store. VERIFY: a disciplined change (e.g. a superseding Decision) persists via the write API + re-critique reflects it; a guard-violating write is rejected inline (no bad write lands); clippy + cargo test + keel validate + guard green. #Verify srViewerInProgramEdit."; }
        part viewerInProgramEditDoDR1 : TestResult { :>> id = "7b614128-3868-4d7a-9f75-f96f84ca670e"; :>> outcome = VerdictKind::pass; :>> judgedAgainst = "ee0fc87"; :>> judgedAt = "2026-07-16"; :>> judgedBy = "claudeOpus"; }

        // ── keel-viewer GENERATIVE-UI backlog (accepted N-17; D0117). keel exposes the model; the viewer generates. ──
        action viewerSchemaApi; // srViewerSchemaApi (N-17): expose declared types + attributes via /api/schema (the generativity substrate).
        verification viewerSchemaApiDoD : Test { :>> id = "a1c7018e-018e-418e-918e-51627384018e"; :>> method = VerificationMethod::test; :>> procedureText = "Satisfies srViewerSchemaApi (N-17/D0117). Expose keel's DECLARED model machine-readably via GET /api/schema: each item TYPE (part/requirement/use-case/... def in schema/core) with its ATTRIBUTE fields (name + type; enum members for enum defs). Parser skips type-def bodies, so text-scan schema/core (like build_dod_files). New types/attributes appear automatically (no hardcoded list). Add to the committed KEEL_API contract; bump version. VERIFY: /api/schema lists Need/Decision/etc. with their attributes (e.g. Need has statement/source/priority); a synthetic new attribute in a def appears; clippy + cargo test + keel validate + guard green. #Verify srViewerSchemaApi."; }
        part viewerSchemaApiDoDR1 : TestResult { :>> id = "affce34c-70a1-411e-8e65-56f73e5afb1e"; :>> outcome = VerdictKind::pass; :>> judgedAgainst = "01f80d7"; :>> judgedAt = "2026-07-15"; :>> judgedBy = "claudeOpus"; }
        action viewerGenerativeUi; // srViewerGenerativeUi (N-17): the viewer app GENERATES its UI from /api/schema + /api/launchables + write API (shape B, ongoing).
        verification viewerGenerativeUiDoD : Test { :>> id = "a1c7018f-018f-418f-918f-51627384018f"; :>> method = VerificationMethod::demo; :>> procedureText = "Satisfies srViewerGenerativeUi (N-17/D0117). The viewer app generates its display + manipulation UI from the declared model: /api/schema (types+attributes -> forms/fields), /api/launchables (processes/skills -> actions), the guarded write API + keel processes (N-16 -> changes); NOTHING hardcoded per type/process/field. VERIFY (demo): adding a process (or attribute) to the model makes it appear/manipulable in the UI with NO viewer code change. LARGELY THE VIEWER APP (shape B, separate project) — a substantial ongoing effort; keel's part is viewerSchemaApi + the existing launchables/write API. #Verify srViewerGenerativeUi."; }
        part viewerGenerativeUiDoDR1 : TestResult { :>> id = "b0d91d81-5c82-43b3-bb4c-fca9fc1fe1c9"; :>> outcome = VerdictKind::pass; :>> judgedAgainst = "a0371ac"; :>> judgedAt = "2026-07-15"; :>> judgedBy = "claudeOpus"; }

        // ── process-integrity fix (issue068): the review queue must respect governing-version, not grandfather ──
        action reviewQueueGoverningVersion; // resolves issue068 — obligation-views reflect CURRENT-process obligations, honoring creation-time governing-version (no retroactive flagging).
        verification reviewQueueGoverningVersionDoD : Test { :>> id = "a1c70190-0190-4190-9190-516273840190"; :>> method = VerificationMethod::inspect; :>> procedureText = "Resolves issue068. The review-queue view (D0121) must surface only CURRENT human obligations and MUST NOT resurrect historical items governed by a superseded process version, nor flag them deficient (govern.rs governing-version + forward-only retroactivity, D0068/D0069/D0070/D0034 already provide the resolution — the new view must USE it). IMMEDIATE: declare `retro` as a Delivery workflow phase so the existing model-driven ceremony filter (is_ceremony_gate) recognizes + drops retro gates (ceremony = autonomous, D0049) from the actionable set — WITHOUT rewriting the legacy gates' creation-time method. BROADER (design rule): every new computed obligation-view/guard consults governing-version so items are judged by the process in force at their charter (exceptions — safety-related / high-level Needs — may be deliberately re-governed). NO retroactive migration; any new guard is forward-only. Needs a governing Decision (CHANGE, §3a) + human acceptance before applying. VERIFY: retro gates no longer in the actionable review queue; legacy gate method unchanged; guard/validate green. #Verify (process-integrity)."; }
        part reviewQueueGoverningVersionDoDR1 : TestResult { :>> id = "35c00175-0327-4bc0-87d2-49e02b9d10dc"; :>> outcome = VerdictKind::pass; :>> judgedAgainst = "3d36c57"; :>> judgedAt = "2026-07-15"; :>> judgedBy = "claudeOpus"; }
        action viewerAuthoringEndpoints;
        verification viewerAuthoringEndpointsDoD : Test { :>> id = "94b02f4b-832c-4fcd-af96-31f774e74287"; :>> method = VerificationMethod::demo; :>> procedureText = "CREATE half of the Architect Sure authoring surface (srViewerAuthoringSurface, D0126): POST /api/item — create an item of any declared type through the guarded write path (write::create_item), generative from schema attrs (String + enum), keyword derived from meta-kind, provenance stamped, into .tracking/authored.sysml; inline /api/check feedback; never auto-commits. Viewer wires a generative New-item dialog (type picker + per-type fields) on the ＋ in Find. (Connect/critique/disposition already have endpoints — /api/edge, /api/agent, /api/disposition.) The EDIT path (attribute change via superseding Decision / guarded write) is split to viewerEditItem. VERIFY: create an Issue + Need end-to-end; validates clean; untriaged Issue flagged by /api/check. Delivered Sprint 242 (keel@cea5150, viewer@8738af4)."; }
        part viewerAuthoringEndpointsDoDR1 : TestResult { :>> id = "8d239944-5ca4-4e38-82cb-612705a7c50c"; :>> outcome = VerdictKind::pass; :>> judgedAgainst = "cea5150"; :>> judgedAt = "2026-07-16"; :>> judgedBy = "claudeOpus"; }
        action viewerEditItem;
        verification viewerEditItemDoD : Test { :>> id = "c568da6c-0d3a-4768-82cb-61270f79ac08"; :>> method = VerificationMethod::demo; :>> procedureText = "EDIT half of srViewerAuthoringSurface (D0126): change an existing item's attributes through the disciplined path — a superseding Decision for governed/owned items (Decision/Need/SR), a guarded in-place attribute write where permitted (D0108 owner-of-record). keel: an attribute-set write endpoint (single-line attrs; refuse Decision -> route to supersede; handle enum/string/bool literals); viewer: an Edit action on the detail sheet + context menu, with inline /api/check feedback + D0108 conflict detection. Never auto-commits."; }
        part viewerEditItemDoDR1 : TestResult { :>> id = "a40498cb-4cef-4bbd-bd42-9bafd970144f"; :>> outcome = VerdictKind::pass; :>> judgedAgainst = "fc62b2f"; :>> judgedAt = "2026-07-17"; :>> judgedBy = "claudeOpus"; }
        action viewerSystemBoundViews;
        verification viewerSystemBoundViewsDoD : Test { :>> id = "71e8db70-cee1-438f-9a38-0a9a629e50ed"; :>> method = VerificationMethod::demo; :>> procedureText = "srViewerSystemBoundViews (D0126): sibling/children/ancestry dynamic views with a shifting focus. keel: compute, from a focus, SIBLINGS (same type sharing a parent via a shared incoming edge), CHILDREN (downstream closure), ANCESTRY (upstream trace) — reuse the slice/traversal engine (directional, typed). Expose as slice modes or a /api/relations endpoint. viewer: context-menu Siblings/Children/Ancestry re-anchor the graph + a working set; VMC (view/modify/critique) over the set. Pure computed views, no stored state."; }
        part viewerSystemBoundViewsDoDR1 : TestResult { :>> id = "ce65bfc1-96d0-45dc-803c-390f013b2594"; :>> outcome = VerdictKind::pass; :>> judgedAgainst = "d21ee73"; :>> judgedAt = "2026-07-17"; :>> judgedBy = "claudeOpus"; }
        action viewerCreateLinkage;
        verification viewerCreateLinkageDoD : Test { :>> id = "bc9eae8c-81f0-44fb-9a38-0a9a6a1d91d5"; :>> method = VerificationMethod::demo; :>> procedureText = "srViewerCreateLinkage (D0126): create authors traceability edges, not orphans. viewer: the New-item flow (+ a connect action on existing items) offers upstream/downstream 'connect to' targets with the valid edge kinds for the pair (closed algebra); on create, author the item (/api/item) + edges (/api/edge) in one flow; inline /api/check. Depends partly on srViewerRelationshipGrammar for which edge kinds are valid per pair (until then, offer the full algebra + let guards/check validate)."; }
        part viewerCreateLinkageDoDR1 : TestResult { :>> id = "b516d19e-4c0c-4a21-ae4c-e92b1d4c89c3"; :>> outcome = VerdictKind::pass; :>> judgedAgainst = "1e7f524"; :>> judgedAt = "2026-07-17"; :>> judgedBy = "claudeOpus"; }
        action keelProcessPortability;
        verification keelProcessPortabilityDoD : Test { :>> id = "e61843aa-b7d2-46ad-9f61-4a3c3cae2ff7"; :>> method = VerificationMethod::demo; :>> procedureText = "Modular process portability (nProcessPortability, D0128): make a process a self-contained unit (definition + deploying skill + DECLARED rules/guards + metadata); a per-project ACTIVATION manifest so guards/orient enforce only active processes; keel process list/search/import/export/activate/disable + a curated palette; BYO + AI-assisted selection; opt-in popularity. Leans on the D0105/D0107 declarative-rules migration so activate/disable toggles enforcement."; }
        part keelProcessPortabilityDoDR1 : TestResult { :>> id = "0d80024e-0814-624e-9b3e-00000030024e"; :>> outcome = VerdictKind::pass; :>> judgedAgainst = "76635b4"; :>> judgedAt = "2026-08-15"; :>> judgedBy = "claudeOpus5"; }
        // ── extensibility: project-declared types (raised from the fcn-arch STPA project, 2026-08-07) ──
        action userDefinedTypedefs;
        verification userDefinedTypedefsDoD : Test { :>> id = "2716f8e8-19fb-493b-b80b-3853bc0f1269"; :>> method = VerificationMethod::test; :>> procedureText = "Let PROJECTS declare their own domain types in .tracking/ and have keel resolve them everywhere (validate/guard/render/query), so a project can extend the model WITHOUT editing the read-only .engine/ schema. TODAY a user-authored `part def` in .tracking fails semantic validation with `unresolved type reference` — type resolution only scans .engine/schema. MOTIVATING CASE (fcn-arch STPA control structure): the engine provides EngineSafety::ProcessModel (a controller's BELIEFS) but no type for a controller's CONTROL ALGORITHM (its decision logic); Leveson/Thomas treat these as distinct. Modeling both cleanly needs a project-local `part def ControlAlgorithm :> Element { attribute logic : String; ref heldBy : Controller; }`, which cannot be added to the frozen engine schema and does not resolve from .tracking. DESIGN: resolve type defs authored under .tracking (subtyping Element / engine defs), same as schema/core — likely extend the schema text-scan (cf. build_dod_files / viewerSchemaApi /api/schema) to include .tracking type defs; decide precedence + collision rules vs engine types; ensure /api/schema, guards, and renderers pick them up automatically. Consider whether this should be gated (a project may WANT the engine schema to be the sole authority — make it opt-in per project). VERIFY: a project `part def Foo :> Element { attribute bar : String; }` in .tracking + instances `part x : Foo { :>> bar = \"y\"; }` validate clean and guard green; /api/schema lists Foo with attribute bar; a renderer/query can select Foo instances; clippy + cargo test + keel validate + guard green."; }
        part userDefinedTypedefsDoDR1 : TestResult { :>> id = "0d80025e-0814-625e-9b3e-00000030025e"; :>> outcome = VerdictKind::pass; :>> judgedAgainst = "eeebc13"; :>> judgedAt = "2026-08-15"; :>> judgedBy = "claudeOpus5"; }
        action keelReleaseProcess;
        verification keelReleaseProcessDoD : Test { :>> id = "4a71c549-2c70-420d-9f61-4a3c44ebb513"; :>> method = VerificationMethod::demo; :>> procedureText = "Disciplined release/deploy (nReleaseDiscipline, D0128): operationalise the Deploy workflow — a deploy PROCESS + deploying skill (D0059); semver reconciled across crate/API/engine; a CI job that builds + publishes a GitHub release on a vX.Y.Z tag; a recorded Release item (version + SHA + contents); cadence per-milestone. First real run cuts a fresh release (main is a month past v0.1.0)."; }
        part keelReleaseProcessDoDR1 : TestResult { :>> id = "3494ec32-f721-4bdc-9fb3-77a257bb6616"; :>> outcome = VerdictKind::pass; :>> judgedAgainst = "e2c812f"; :>> judgedAt = "2026-08-14"; :>> judgedBy = "claudeOpus5"; }
        // ── extensibility: project vocabulary as INGESTED data, not a side-channel file
        // (raised from the fcn-arch function dictionary, 2026-08-11; needs userDefinedTypedefs first) ──
        // ── distributed collaboration: async remote mostly-AI team (D0129, 2026-08-12) ──
        // DAY-ONE BLOCKERS (dcMergeOnly..dcPortableGate): without these a multi-machine team
        // corrupts the model in week one. Each closes a VERIFIED defect (see D0129 context).
        action dcMergeOnlyIntegration;
        verification dcMergeOnlyIntegrationDoD : Test { :>> id = "0d5e0001-0812-4e01-9b3e-00000000e001"; :>> method = VerificationMethod::demo; :>> procedureText = "srDcMergeOnlyIntegration (D0129). Closes the EXISTENTIAL defect: orient is machine-dependent because `done` needs judgedAgainst to RESOLVE (orient.rs:494-531/123) and squash/rebase mint new SHAs, so the rewriting machine reads green while every other clone reads invalidEvidence and re-lists finished work. DO: (a) remote — disable squash-merge + rebase-merge, protect main (no force-push, no deletion), require the CI check; (b) local — rewrite .githooks/post-commit so a rejected push FETCHES and MERGES (never rebases) and retries, reporting loudly on failure instead of printing a note; (c) add a pre-merge-commit hook so merge commits are gated like any other; (d) document merge-never-rebase in CLAUDE.md. VERIFY: `gh api` shows squash+rebase disabled and main protected; two clones push concurrently and the loser auto-merges + lands with every judgedAgainst still resolvable in BOTH clones; a deliberate rebase attempt on evidence-carrying commits is refused/flagged; orient output is byte-identical across the two clones. clippy + validate + guard + check-engine green."; }
        part dcMergeOnlyIntegrationDoDR1 : TestResult { :>> id = "9b23fa03-a52c-4aa9-acda-5e09293ef2e7"; :>> outcome = VerdictKind::pass; :>> judgedAgainst = "b518c23"; :>> judgedAt = "2026-08-12"; :>> judgedBy = "claudeOpus5"; }
        action dcDuplicateIdentityGuard;
        verification dcDuplicateIdentityGuardDoD : Test { :>> id = "0d5e0002-0812-4e02-9b3e-00000000e002"; :>> method = VerificationMethod::test; :>> procedureText = "srDcUniqueIdentityGuard (D0129). Closes SILENT corruption: two offline agents both mint the next decision number by directory scan (write.rs:929-942); different slugs => different filenames => NO git conflict => both land => duplicate `package DecisionNNNN` silently merged by registry.rs:52-53. No guard among the seventeen detects duplicate id or name. DO: add a hard-blocking `duplicate-identity` guard (new entry in GUARD_NAMES + guards.rs) that scans the whole model for repeated element `id`, repeated declared item name within a package, repeated package name across files, and repeated allocated sequence number (decision/issue/sprint). Prefer sourcing it as a DECLARED ElementRule (D0105/D0107) if it fits the generic evaluator; otherwise Rust with the rollback criterion recorded. VERIFY: unit tests for each of the four duplicate classes fail the guard and a clean model passes; a synthesized duplicate DecisionNNNN pair is caught (the registry-merge case); guard runs in the pre-commit hook + CI; clippy + cargo test + validate + guard green."; }
        part dcDuplicateIdentityGuardDoDR1 : TestResult { :>> id = "589dc901-ed7e-42ee-9bf0-c45122c9047f"; :>> outcome = VerdictKind::pass; :>> judgedAgainst = "b518c23"; :>> judgedAt = "2026-08-12"; :>> judgedBy = "claudeOpus5"; }
        action dcCollisionResistantIds;
        verification dcCollisionResistantIdsDoD : Test { :>> id = "0d5e0003-0812-4e03-9b3e-00000000e003"; :>> method = VerificationMethod::test; :>> procedureText = "srDcCollisionResistantIds (D0129). gen_uuid (write.rs:63-99) mixes only clock seconds + subsec nanos + PID + an in-process counter that is 0 for the first record of every invocation, self-documents as 'not cryptographically random', and has NO host component — so independent machines are not independent sources, and identity (CLAUDE.md §2.3) is what a collision corrupts. DO: replace with a cryptographically-seeded random UUIDv4 (os RNG / `uuid` crate with the `v4` feature), keeping the emitted format identical so existing ids and parsers are unaffected. VERIFY: generated ids are RFC-4122 v4 (version + variant nibbles correct); a large-volume generation test shows no collisions and no clock/PID correlation; ids differ across simulated same-instant same-PID generation; existing recorded ids untouched; clippy + cargo test + validate + guard green."; }
        part dcCollisionResistantIdsDoDR1 : TestResult { :>> id = "c8b18ea7-f596-471e-96b4-6799e9fe5eda"; :>> outcome = VerdictKind::pass; :>> judgedAgainst = "b518c23"; :>> judgedAt = "2026-08-12"; :>> judgedBy = "claudeOpus5"; }
        action dcActorIdentityBinding;
        verification dcActorIdentityBindingDoD : Test { :>> id = "0d5e0004-0812-4e04-9b3e-00000000e004"; :>> method = VerificationMethod::test; :>> procedureText = "srDcActorIdentityBinding + srDcActorKindClassification (D0129). Closes TWO independent confirmation-authenticity bypasses (D0106/issue059 exists to stop an AI fabricating HUMAN acceptance): (i) seven serve.rs sites default author/judged_by to the human 'wweatherholtz' (304,331,357,384,409,483,1313), record decision likewise (main.rs:967), and five paths default to the UNREGISTERED 'keel-cli' (main.rs:910,935,1121,1151) — so an AI-driven call that merely OMITS the field records a human attestation silently; (ii) capture_user.py registers every enrolled actor as `: Person` with no kind question, so an onboarding AI is registered as a human and thereafter satisfies the guard legitimately. DO: resolve the acting actor from an explicit per-machine binding (config file or env var) or an explicit argument; REFUSE the write when unstated; remove every default that names a human or an unregistered actor; make actor kind an explicit required input when registering, with no inference from git identity and no Person default. VERIFY: every write path refuses with a clear message when identity is unstated; no default in the codebase names a registered human or an unregistered actor (grep-asserted in a test); registering an AI produces `: Actor` with kind=ai and cannot produce Person; a fabricated-human-acceptance attempt by an AI actor is refused; confirmation-authenticity guard still green; clippy + cargo test + validate + guard green."; }
        part dcActorIdentityBindingDoDR1 : TestResult { :>> id = "b03308aa-ed75-40e1-b60c-cdd9fcb24ea7"; :>> outcome = VerdictKind::pass; :>> judgedAgainst = "b518c23"; :>> judgedAt = "2026-08-12"; :>> judgedBy = "claudeOpus5"; }
        action dcPortableGate;
        verification dcPortableGateDoD : Test { :>> id = "0d5e0005-0812-4e05-9b3e-00000000e005"; :>> method = VerificationMethod::demo; :>> procedureText = "srDcPortableGate (D0129). The local gate evaporates off this machine: .githooks/pre-commit:17-21 hardcodes an absolute conda path + a Windows binary name; elsewhere it prints 'guards skipped' (pre-commit:66-68) so the gate silently becomes nothing, or aborts .engine commits and teaches SKIP_VALIDATE=1; only pre-commit/post-commit are installed so `git merge` (pre-merge-commit) is UNGATED — the conflict-resolution commits this workflow generates are exactly the ones with no local check; .gitattributes normalizes only *.sh, leaving *.sysml at each machine's core.autocrlf, which turns every shared model file into a whole-file phantom diff for a differently-configured contributor. DO: probe for `keel`/`keel.exe` on PATH and in target/release; make the conda/kernel path configurable and OPTIONAL (skip the kernel layer with a clear notice, never abort); install pre-merge-commit; add `* text=auto` + `*.sysml text eol=lf` to .gitattributes; make an unrunnable check FAIL LOUDLY rather than pass silently. VERIFY: the hook runs clean on a POSIX machine with no conda and on Windows; a merge commit is gated; a missing binary yields a NON-ZERO honest failure, not a silent skip; `git ls-files --eol` shows *.sysml as lf after normalization with no content change; clippy + validate + guard + check-engine green."; }
        part dcPortableGateDoDR1 : TestResult { :>> id = "8a14bcac-2c49-4800-8de8-2b9748f7a30b"; :>> outcome = VerdictKind::pass; :>> judgedAgainst = "b518c23"; :>> judgedAt = "2026-08-12"; :>> judgedBy = "claudeOpus5"; }
        // FROZEN-SCHEMA sign-off required (CLAUDE.md §2.5) — deliberately NOT day-one.
        // FOLLOW-ONS (post-day-one; each its own sprint).
        action dcTwoPassRegistration;
        verification dcTwoPassRegistrationDoD : Test { :>> id = "0d5e000e-0812-4e0e-9b3e-00000000e00e"; :>> method = VerificationMethod::test; :>> procedureText = "Resolves issue079 (filed 2026-08-12 for a fix found + written in an EARLIER, uncommitted session and never recorded). Defect: validate_root registered and validated each .tracking package in ONE pass, so resolution depended on filesystem iteration order — a tracking file importing another package (requirements.sysml importing ProjectBusiness) failed when visited before that package was registered. It flaked on CI's Linux file order while PASSING on Windows: a machine-dependent validation verdict, the same class as issue071 with the filesystem rather than the git object store as the varying input. FIX (present in the working tree, uncommitted at time of filing): two-pass — parse and register ALL tracking packages first, THEN validate all (keel-cli/src/lib.rs validate_root; mirrored in keel-parser/tests/parse_engine_files.rs). VERIFY: validation verdict is identical under reversed/randomized file iteration order; a cross-package import resolves regardless of visit order; the CI-vs-Windows divergence no longer reproduces; clippy + cargo test + keel validate + guard green. NOTE the fix is another session's uncommitted work — its author should confirm + commit it; this entry exists so the defect is RECORDED rather than living only in a code comment."; }
        part dcTwoPassRegistrationDoDR1 : TestResult { :>> id = "774e5edd-8898-4da1-af7c-1cc5fa5ec898"; :>> outcome = VerdictKind::pass; :>> judgedAgainst = "b518c23"; :>> judgedAt = "2026-08-12"; :>> judgedBy = "claudeOpus5"; }
        action projectVocabularyIngestible;
        verification projectVocabularyIngestibleDoD : Test { :>> id = "bfc1758a-f24e-4eab-b09d-031c87cea5a5"; :>> method = VerificationMethod::test; :>> procedureText = "Let a project author its DOMAIN VOCABULARY as facts keel INGESTS, so the two-model boundary (CLAUDE.md section 1 - the deliverable's own vocabulary stays in the deliverable's model) stops pushing authored data OUT of keel. Builds on userDefinedTypedefs, but is not the same ask: type resolution makes project types PARSE; this makes their instances COUNT (identity, query, render, coverage, temporal). SECOND MOTIVATING CASE (fcn-arch, 2026-08-11, Decision d0012 - independent of the ControlAlgorithm case that raised userDefinedTypedefs): the project needed a FUNCTION DICTIONARY as the enforced vocabulary for its functional architecture - 7 function kinds each with a definition-of-done template, 59 sanctioned verbs each with its kind + definition + a real example, 25 retired verbs each with why it was retired and what to use instead, 4 node roles with their obligations, and 12 naming rules each with rationale and example (about 100 terms). Authoring it in .tracking needed 5 project part defs subtyping Element (FunctionKindDef, FunctionVerb, RetiredVerb, NodeRoleDef, NamingRule). `keel validate` returned 107 semantic diagnostics, every one `unresolved type reference`. FALLBACK TAKEN: the vocabulary moved to keel/views/function-dictionary.yaml - authored YAML OUTSIDE .tracking - plus a project-side generator and renderer. COST OF THE FALLBACK (this is the real problem): that vocabulary is NORMATIVE (adopted by Decision d0012) and is what the project's checker enforces against, yet it has no UUID identity in the model, cannot be reached by satisfy/verify/allocate edges, is invisible to orient, coverage, critique and suspicion, is absent from /api/schema, cannot be selected by a declared view (D0075 enriched-select), and cannot be asked as-of a commit via the git-temporal substrate (D0013). A retired verb is exactly the kind of fact that should go SUSPECT when the decision behind it changes - and it cannot. Every downstream project that needs a controlled vocabulary (glossary, taxonomy, unit set, verb dictionary, state alphabet) will hit this and will invent its own side-channel file, so the engine loses sight of the deliverable's own definitions. DESIGN NOTES: (a) resolution alone is insufficient - decide how project-typed instances flow into the enriched item-table (D0075) so views can select them, and whether they are exempt from work-item semantics so orient/burndown do not miscount a glossary term as work; (b) they should carry the standard Element attrs (id/title/createdAt/createdBy) and take part in edges, so a Decision can verify-link a vocabulary; (c) consider a declared 'reference data' class of project type - authored, versioned, edge-addressable, but NOT work - since that is what a dictionary, glossary or taxonomy actually is; (d) keep it opt-in per project (a project may want the engine schema as the sole authority). VERIFY: a project authors >= 2 domain types + >= 20 instances under .tracking; keel validate and guard are green; the instances appear in /api/schema and are selectable by a declared view; they carry UUID identity and createdAt/createdBy; a Decision can satisfy/verify-link them and they go suspect when it changes; as-of queries work at an older commit; orient/burndown do not count them as outstanding work; the fcn-arch function dictionary is migrated from views/*.yaml back into .tracking with no loss and its checker reads the model instead of the YAML; clippy + cargo test + keel validate + guard green."; }
        part projectVocabularyIngestibleDoDR1 : TestResult { :>> id = "0d80025f-0814-625f-9b3e-00000030025f"; :>> outcome = VerdictKind::pass; :>> judgedAgainst = "eeebc13"; :>> judgedAt = "2026-08-15"; :>> judgedBy = "claudeOpus5"; }
        action dcContractDedup;
        verification dcContractDedupDoD : Test { :>> id = "0d650002-0813-4502-9b3e-000000150002"; :>> method = VerificationMethod::inspect; :>> procedureText = "Resolves issue086 (raised by the sprint 249 retro under the new issue085 obligation — a retro finding must become a tracked item, not prose). D0130 makes the output style the CANONICAL home of the response contract and CLAUDE.md a REFERENCE, and a pointer was added at the head of section 3 — but the RESTATEMENT was not fully removed: section 3's 'Strict process-boundedness' paragraph still spells out the Parsed-block mandate, the label vocabulary and the trivial-exemption rule that `.claude/output-styles/keel.md` now owns. Two live copies of one rule is exactly the dual truth D0105 forbids, and the copy in the weaker layer is the one that will drift. DO: reduce section 3 to the ROUTES (the classification table + the recurring-or-one-time check) plus a pointer, deleting the restated contract text outright — no tombstones, state what IS. Then confirm no other doc surface restates it (grep the doc surface per the doc-sync skill). VERIFY: the Parsed-block format, label vocabulary and trivial-exemption appear in EXACTLY ONE place (the output style); CLAUDE.md section 3 still fully defines the routes; guard doc-sync passes; keel validate + guard green."; }
        part dcContractDedupDoDR1 : TestResult { :>> id = "b8e6a21f-f0c4-4356-ab29-e3f76d96aa00"; :>> outcome = VerdictKind::pass; :>> judgedAgainst = "e2c812f"; :>> judgedAt = "2026-08-14"; :>> judgedBy = "claudeOpus5"; }
        // ---- deprioritized: lowest-value ready work ----
        action keelArchViews;
        verification keelArchViewsDoD : Test { :>> id = "4152d90a-2a4d-4ccb-b0cf-aabcca5b6261"; :>> method = VerificationMethod::test; :>> procedureText = "Add the keel `arch` view command group so a downstream project's EngineCodeAudit CodeElement registry is COMPUTABLE (first consumer: SelfSync, its D0029 + docs/design-history/2026-07-18-architecture-audit-design.md). Prereq: promote the EngineCodeAudit schema module (CodeElement + RiskClass/InvariantSafety/StpaRole/DesignPattern + #Controls/#Feedback/#Restructure markers) into the engine's shipped schema so `keel init` gives every downstream the type (SelfSync authored a local copy at .engine/schema/codeaudit/ to prove the model; keel already parses the module-defined type generically). Commands (all COMPUTED views; keel never parses deliverable source — it reads authored CodeElement instances + the Needs graph + the in-code @audit-hash markers): arch elements [--kind --file] (list); arch criticality (risk-class tier bumped by high-severity Need-trace = the ranked audit frontier); arch coupling (Ca/Ce/instability/distance-from-main-sequence + dependency cycles over the #DependsOn graph); arch drift (each CodeElement.codeHash vs the live // @audit-hash, reusing the audit_hash brace-scan -> the re-audit frontier, unifying with D0028); arch stpa-inputs [--render] (the captured stpaRole/actions/#Controls/#Feedback control structure as the hand-off to a later STPA analysis process, NO analysis here); arch coverage (non-blocking: heuristic top-level-def enumeration flags un-catalogued elements). Register each as a declared viewpoint (viewpoint-registry). VERIFY: on SelfSync's authored registry, arch criticality ranks the DataLoss/security elements top; arch drift flags a function whose body changed since its codeHash; a coverage-floored test per command; clippy + cargo test + keel validate + guard green."; }
        part keelArchViewsDoDR1 : TestResult { :>> id = "4f960cbe-1400-494f-8170-f7b332a5a288"; :>> outcome = VerdictKind::pass; :>> judgedAgainst = "4bf8906"; :>> judgedAt = "2026-08-15"; :>> judgedBy = "claudeOpus5"; }
        action dcValidateNamesItsScope;
        verification dcValidateNamesItsScopeDoD : Test { :>> id = "412a74c6-6042-42ee-952b-0ba383bc8731"; :>> method = VerificationMethod::test; :>> procedureText = "DONE MEANS: a green `keel validate` cannot be read as covering a tree it did not judge. MEASURED 2026-09-09 (sprint 622): with `.engine/decisions/0001-*.sysml` carrying `DecisionStatus::superseded` after the member left the enum, `keel validate .` printed `708 tracking file(s) validated clean` and exit 0 - true, and read by two authors (D0398's consequences text and sprint 622's first DoD draft) as the schema gate refusing the value; `keel check-engine .` is the command that refuses under `.engine`, and it is a separate invocation the doc surface names in one place. DO: either (a) `validate` states its scope in its verdict line - `.tracking: 708 file(s) validated clean; .engine: not judged (run check-engine)` - or (b) `validate` runs the engine-instance check too and reports both counts, with `check-engine` kept as the narrower command. Pick by measuring what the pre-commit hook and CI already run (both run both); a verdict that names its scope is the smaller change and never reads as more than it is. VERIFY: a test constructs a scaffold whose `.engine` holds an unknown enum member and asserts that the `validate` output either names `.engine` as unjudged or fails naming the member - never a bare clean line; the doc surface (CLAUDE.md section 5, usage.md) states which command judges which tree in one sentence."; }
        action dcBriefFactsReadStandingFromTheEdge;
        verification dcBriefFactsReadStandingFromTheEdgeDoD : Test { :>> id = "d2d7ac2a-8da0-47d6-99aa-2d03025f8a04"; :>> method = VerificationMethod::test; :>> procedureText = "DONE MEANS: the decision brief's facts script reads a Decision's standing the way the engine does after D0398 - status MINUS the #Supersede edge - and cannot publish a pending count the engine disagrees with. MEASURED 2026-09-09 at 649b433: scripts/exec_brief/facts.py counted decisionsProposed = 3 (d0038 and d0353, both retired by a #Supersede edge, plus d0399) while keel orient pendingAcceptances read 1; its supersession census still carried the pre-D0398 'two representations disagree' facts (supersessionDisagreements = 5 over five Decisions the migration had just retired whole) and listed d0353 as a proposed Decision whose code already ships. The sprint 622 doc-sync grep covered the Rust readers and the doc surface and missed the one Python reader of the status field. DO: compute the retired set from non-comment #Supersede lines in facts.py and subtract it from accepted, proposed and the consent-scope census; replace the D0384 census facts with decisionsRetired, supersedeEdges and supersedeClauseEdges; and when the file-derived proposed count differs from orient's pendingAcceptances, emit decisionsProposed as null with a how that names both numbers - the brief then cannot carry either. VERIFY: facts.py on this tree reads decisionsProposed = 1 = pendingAcceptances, decisionsAccepted = 389 (the governance card's accepted count), decisionsRetired = 7 and supersedeClauseEdges = 7 (the seven clause reversals D0398 named), and scopeDecisionsOpen = 1; the cross-check refuses when the two disagree."; }
        // RAN: python scripts/exec_brief/facts.py at 649b433 after the patch: decisionsProposed 1 = pendingAcceptances 1 (was 3 vs 1), decisionsAccepted 389 = governance card, decisionsRetired 7 (d0003 d0014 d0038 d0069 d0071 d0310 d0353), supersedeClauseEdges 7 (d0114 d0115 d0129 d0175 d0178 d0205 d0351), scopeDecisionsOpen 1, pendingAlreadyShipped 0; the disagreement branch emits decisionsProposed null naming both counts
        part dcBriefFactsReadStandingFromTheEdgeDoDR1 : TestResult { :>> id = "f0db293a-a603-4a40-baa7-ce3bb43a8931"; :>> outcome = VerdictKind::pass; :>> judgedAgainst = "649b433"; :>> judgedAt = "2026-09-09"; :>> judgedBy = "claudeOpus5"; }
        action dcFieldReadersOutsideRustAreEnumerated;
        verification dcFieldReadersOutsideRustAreEnumeratedDoD : Test { :>> id = "b1c3996f-de06-4891-9744-afd8fc6b97cc"; :>> method = VerificationMethod::test; :>> procedureText = "DONE MEANS: every reader of a model field that lives OUTSIDE keel-cli/src is enumerated by a computed lens, so a change to what a field MEANS has a named sweep surface instead of a grep the author remembers. MEASURED 2026-09-09: sprint 622 changed the meaning of a Decision's status (D0398: standing = status minus the #Supersede edge), doc-synced the Rust readers and the doc surface, and missed scripts/exec_brief/facts.py, which regex-reads the same field and would have published decisionsProposed 3 against the engine's 1 (issue420). DO: add a `keel show field-readers` lens that lists, per model field name (status, verdict, method, severity, judgedAgainst, createdBy and the rest of the schema's attribute names), every file under scripts/, .engine/tools/ and .github/ whose text names that field, so the sweep for a meaning change is one command; and a guard `field-readers-swept` that WARNS (never blocks) when a commit touches a schema enum or attribute definition without touching, in the same commit, at least one file the lens lists for that field. VERIFY: the lens names scripts/exec_brief/facts.py under `status`; the guard, run against 649b433's parent range, warns on the D0398 commit and is silent on a commit that touches no schema definition."; }
        action dcControlDecisionNamesItsUca;
        verification dcControlDecisionNamesItsUcaDoD : Test { :>> id = "5a6bb71c-66d8-497b-90c1-0b544f47c758"; :>> method = VerificationMethod::test; :>> procedureText = "Verifies srControlDecisionNamesItsUca. A warning-level guard `control-ask-grounded` reads every proposed Decision carrying the process-change or safety-change marker whose text names a guard, hook rule, write-path check or commit-gate tier and reports the ones that neither name an UnsafeControlAction / ControllerConstraint id in their text nor carry a #DependsOn / #DerivedFrom edge to one, and the ones whose UCA has no Issue edge and do not say the UCA is code-read; the decision brief's facts.py emits the same set so an ungrounded ask reaches the human labelled. VERIFY: a unit test over a fixture tree with one grounded and one ungrounded control Decision names exactly the ungrounded one; the live check is the guard reporting zero on this tree once d0427 and d0428 carry their UCA edges."; }
        action dcSessionActorFollowsTheModel;
        verification dcSessionActorFollowsTheModelDoD : Test { :>> id = "e95da394-7787-4142-a7e7-1493125135da"; :>> method = VerificationMethod::test; :>> procedureText = "DONE when a record cannot name an actor that is not the model running the session. FOUND by stpa-self run 4 (UCA-RB1): the session binding .keel/sessions/<id>/actor was declared claudeOpus5 on 2026-09-08 and the harness switched the same session to Fable 5 between e1de7c7 and ceaabdd; ceaabdd (7 records) and 76b106e (8 records) carry createdBy/judgedBy claudeOpus5 under a commit trailer Co-Authored-By: Claude Fable 5 - verified by git show on the three fold commits. The binding is per session but the model is per turn, and nothing re-reads it. DO: the session binding carries the model name it was declared under, and every path that resolves an AI actor (actor.rs resolve) compares that name with what the harness reports for the current turn - the SessionStart / hook payload model field where the harness supplies one, else the launcher's declared model - and refuses the write naming both; an audit-history check holds every createdBy/judgedBy an AI introduced in a commit equal to the model the commit trailer names, so a landed mismatch is a red CI verdict and not a retro finding. VERIFY: a fixture with a binding declared under one model and a turn reporting another refuses with both names; the same model passes; the audit re-read of ceaabdd and 76b106e names both commits and nothing else since the actors were split (D0129); the landed records stay as written - history is not rewritten - and this task's DoD result carries the receipt. Resolves issue498."; }
        action dcChatStatementsAwaitTheirSpeaker;
        verification dcChatStatementsAwaitTheirSpeakerDoD : Test { :>> id = "19e13844-075d-4133-aba2-0bba058ec805"; :>> method = VerificationMethod::test; :>> procedureText = "DONE when a Statement an AI typed on a human's behalf is distinguishable, at read and in every lens, from one the speaker recorded. FOUND by stpa-self run 4 (UCA-RS1): keel record statement takes --said-by and --text from the same typing hand and defaults --channel to chat (main.rs cmd_record_statement); the record then reads as the human's verbatim words with the AI's paraphrase risk invisible - the UCA-H1 class (issue428) one layer down, since a Decision that DOES link its Statement is only as verbatim as the Statement. DO: a Statement whose recorder (createdBy) is an AI actor and whose saidBy is a Person lands in the attestation lens as testimony awaiting the speaker (the D0312 B shape) and keel judge-set or the serve intake surface lets the speaker confirm the words; a Statement the speaker records through a channel keel observed (serve, an authenticated intake) is a receipt and needs no confirmation; a Decision or Story deriving from an unconfirmed Statement shows it in decision-card and orient. VERIFY: a fixture Statement typed by an AI actor for a Person reads as testimony and flips to receipt on the speaker's confirmation; one recorded by the speaker reads as receipt from the start; the attestation lens over this tree counts the existing chat Statements and names them; no Statement text is changed. Resolves issue499."; }
        action dcReverifyStampsTheRunDate;
        verification dcReverifyStampsTheRunDateDoD : Test { :>> id = "beaf1ea0-85cc-4a43-bf86-c9acd3d0bdd0"; :>> method = VerificationMethod::test; :>> procedureText = "DONE when a result keel record reverify stamps says when it was judged. FOUND by stpa-self run 4 (cmdRecordReverify, wrongTimingOrder): reverify.rs run() takes judgedAt from git show -s --format=%cs HEAD - the commit date of the tree, not the date of the run - so a re-verification run days after HEAD landed records a judgment dated before it happened, and the impossible-evidence-date guard cannot see it because the date is not impossible, only wrong. DO: judgedAt is the run's own date (the same local date every other record sub-verb takes from --judged-at or the clock), the evidence string keeps naming the HEAD it ran against, and the working-tree state at the run is named in the evidence when dirty (binding_note's fact, made part of the record). VERIFY: a fixture with HEAD committed on one date and the run on a later date stamps the later date; the evidence names the short sha; a run on a dirty tree names the dirty path count in its evidence; keel suite touched set green. Resolves issue500."; }
        action dcSubVerbEffectIsDeclared;
        verification dcSubVerbEffectIsDeclaredDoD : Test { :>> id = "194bdcc6-fac6-45b0-b889-702e3db9f315"; :>> method = VerificationMethod::test; :>> procedureText = "DONE when the computed control structure labels a sub-verb by its own effect, not its router's. FOUND by stpa-self run 4 (D0454 read-back): keel process is one CliCommand fact with effect writes, so its list, search, show and export sub-verbs appear in keel show control-structure as write actions cmdProcessList, cmdProcessSearch, cmdProcessShow, cmdProcessExport, and the stpa-currency guard asks for a UCA analysis of four reads; keel record has the same shape in reverse - mint writes nothing and is a write action. DO: a routing command's sub-verbs carry their own declared effect - a per-segment effect in the fact's invocation grammar or one CliCommand fact per sub-verb under a routing parent, chosen by a Decision with the schema owner's sign-off since cli.sysml is engine schema - and control-structure emits a sub-verb action only for a sub-verb whose declared effect writes; the cli-surface-declared guard holds the per-sub-verb declaration equal to dispatch. VERIFY: after the change keel show control-structure names no cmdProcessList/Search/Show/Export and no cmdRecordMint; the record, process and library write sub-verbs are unchanged in name; stpa-currency's open set shrinks by exactly the five; the_record_sub_verbs_match_the_fact and the routing test in control_structure.rs read the declared effects. ALSO (issue506): the sub-verb list is DECLARED with the effect, not derived from the invocation grammar by cli_facts.rs sub_verb_segments - that reader is deleted with its ordering rule (the router-own bare alternative had to trail; a grammar opening with a placeholder hid `render report`), the router tests read the declaration, and `render` joins the routers the test holds. ALSO (D0453 fold, sprint 683): keel github is one fact with effect both, so its decider, gesture and decision-id sub-verbs - two reads that the pre-fold structure computed as the feedbacks readGithubDecider and readGithubGesture, and one tooling verb that writes nothing - appear as the write actions cmdGithubDecider, cmdGithubGesture and cmdGithubDecisionId (control structure 66 actions at the fold, 63 before), and the per-sub-verb stability is lost the same way: the three deprecated verbs (D0289) and the two stable ones read as one stable fact. VERIFY adds: after the change none of those three is a write action, cmdGithubPull and cmdGithubIngest are unchanged in name, the two reads return as feedbacks, and stpa-currency's open set shrinks by those three as well. Resolves issue501, issue506."; }
        action dcAnEditCannotNestAnItemByAccident;
        verification dcAnEditCannotNestAnItemByAccidentDoD : Test { :>> id = "fb7201cd-78f9-4238-8d21-aada8f54b93b"; :>> method = VerificationMethod::test; :>> procedureText = "DONE when an edit cannot nest one item inside another by accident, at either end of the act. FOUND twice in sprint 681 (issue502): a textpatch insert-after anchored on a PREFIX of a one-line `part X : TestResult { ... }` split the line, and the whole run-4 block - five UCAs, five constraints, the run record - landed inside that part's body; validate passed, the text-based stpa-currency reader saw the names, the item-based census answered 16 of 21. DO, two controls: (1) scripts/textpatch.py refuses an insert-after whose anchor ends mid-line and an insert-before whose anchor starts mid-line, naming the rest of the line the insert would split - the act cannot split a line; its probe carries the D0388 pair (prefix anchor refused and the file untouched; the same anchor as a whole line patched) and CI runs the probe (dcScriptProbesRunInCi). (2) keel validate flags a `part` declared inside the body of a leaf item - TestResult, Issue, UnsafeControlAction, ControllerConstraint, Decision - naming the enclosing part and the nested one, so a nesting that reaches the tree by any editor is a red gate and not a census discrepancy someone happens to count. VERIFY: (1) textpatch --probe reports the new pair passing; (2) a fixture with a UCA nested in a TestResult is red with both names, the same UCA at package level is green, and engine-ucas.sysml at HEAD is green. Resolves issue502."; }
        action dcAuthorityQueueListsConfirmationGates;
        verification dcAuthorityQueueListsConfirmationGatesDoD : Test { :>> id = "46e05cad-9107-456c-8e60-5e055d4479f8"; :>> method = VerificationMethod::test; :>> procedureText = "Resolves issue561. A CHANGE to the meaning of a view (D0129 srDcHumanAuthorityQueue), so the working sprint carries its own Decision marked process-change and the item is worked under that acceptance. TODAY keel show authority-queue enumerates two kinds, decisionAcceptance and findingDisposition (keel-cli/src/view/mod.rs OBLIGATION_FROM and collect_decision_and_finding_obligations); a method=confirmation Test with no TestResult - a Business gate such as ProjectBusinessModularMembers::modularMembersNeedsAccept, which exists only to hold a human's word - is not a row, so the decision page built from the lens (D0359) has to carry that ask by hand and the state test in the decision-surfacing skill cannot see it move. DO: a third kind, confirmationGate: every Test whose method is confirmation and whose id no TestResult's verifiedBy names, with shortName its title, origin its file, since its createdAt, in force from the working Decision's date through OBLIGATION_FROM so no earlier gate is retro-owed; the JSON row shape is the existing Awaiting; facts.py's pendingMembers stays Decisions and gains a sibling fact pendingConfirmations read from the same lens. Known-positive, chosen before the tree is read: a fixture tree with one confirmation Test and no result lists one confirmationGate row; known-negative: the same tree with a passing TestResult naming it lists none; the live tree lists modularMembersNeedsAccept until wweatherholtz's word is recorded and none after. Done means: the pair passes as a Rust test in view/mod.rs, keel show authority-queue . on this tree carries the row, and facts.py authorityQueueKinds reads listsConfirmationGates true"; }
        action dcBriefAskGlossesItsMetric;
        verification dcBriefAskGlossesItsMetricDoD : Test { :>> id = "71621cef-cf16-4ef3-b532-a39051d1b424"; :>> method = VerificationMethod::test; :>> procedureText = "DONE MEANS: every ask on the decision brief whose evidence is a measurement says, in one plain paragraph the reader can judge, WHAT the measured thing is (the instrument, what one case is), what each number means for THEM (a higher/lower value changes what they experience), and why the ask is theirs at all - before any table or sweep line. FOUND 2026-09-14 on the twenty-ninth publish: the d0466 panel (the recall rule read at 50 or 100 cases) carried both sweeps' verdict lines and three options and the human's words were 'The sample fork item is still confusing to me. What's the point? You don't say what the metric is actually doing sufficiently'; the explanation had to be given in chat (recall walks typed edges on every prompt; a case is a linked record's words with names stripped; hits, median position and top-3; the dominance bonus and what lowering it costs the ordinary search) before the letter came. The numbers were on the page; the meaning was not, and the brief contract (D0355, D0377) counts figures and words, not meaning. DO: the ask panel gains a data-metric-gloss element (one paragraph, counted in the tab's word budget) required wherever the panel carries a data-metric figure or a sweep table; the gloss names the instrument, the unit of one case, and the reader-facing meaning of the statistic's direction; scripts/check_templates.py --brief refuses a panel with a measurement exhibit and no gloss, and refuses a gloss that quotes a record id or a variable name (DOMINANCE, --cases) in place of a plain noun - the reader's vocabulary, not the code's; the asi-templates skill section 2 carries the clause. Known-positive, chosen before any page is read: a fixture panel with a sweep table and no gloss is refused; known-negative: the same panel with a gloss paragraph is clean; the twenty-ninth published page, re-checked, is refused on its d0466 panel. VERIFY: check_templates.py --self-test carries the pair; the next brief with a measured ask passes the check and is not questioned on what the metric does."; }
        action dcDeliveredClaimsAreReadBackFromSource;
        verification dcDeliveredClaimsAreReadBackFromSourceDoD : Test { :>> id = "32d534f1-9990-4ce5-9dd5-fceee37b7c12"; :>> method = VerificationMethod::test; :>> procedureText = "Resolves issue533. A Story DoD's DELIVERED: text is read back from the source before its result is written: the VERIFIER brief in delegated-ceremony SKILL.md gains a step that takes every clause naming a source relation (X beside Y, X calls Y, X shares Y, X gains Y, a file:line) and writes a CLAIMS: block in the receipt - one line per clause with the grep or sed that read it and the line it found, or HELD: naming the clause the source does not show - and a checker beside check_report.py (references/check_receipt.py) refuses a receipt whose CLAIMS: block is missing while the DoD carries a DELIVERED: clause, or carries a HELD: line, so the RECORDER cannot write a pass on a sentence no one read. D0388 pair: a receipt for sprint 703's DoD at aba396e with the shared-walk clause HELD is refused naming the clause; the same receipt with the clause read at the D0472 tree passes. .claude is regenerated by sync-claude. A #ProspectiveChange Decision governs the brief and checker change."; }
        action dcEveryRegisteredRefusalLedgersAFire;
        verification dcEveryRegisteredRefusalLedgersAFireDoD : Test { :>> id = "1f464f01-05f2-418d-b5d8-e86bb67b20d5"; :>> method = VerificationMethod::test; :>> procedureText = "issue527 is resolved - an integration test drives every entry of write::WRITE_PATH_REFUSALS through its verb against a fixture project (an AI actor bound, each refusal's triggering input authored: a receiptless AI method=test result, injected tool-output prose in a decision and an issue, an unquoted --by note, a gesture word, a --by with no delegation) and reads .keel/metrics/hooks.jsonl back, asserting one event=refused line whose control equals verb:check for each entry and no unregistered: line; an entry with no ledger line fails naming it. VERIFY (probe pair, D0388): with the record:tool-output-prose match arm in cmd_record_issue removed the test fails naming record:tool-output-prose (known positive); on the real tree every entry produces its line (known negative); clippy clean."; }
        action dcVerdictCommandsAreReadBackIntoTheAuthorityLists;
        verification dcVerdictCommandsAreReadBackIntoTheAuthorityListsDoD : Test { :>> id = "96147c3a-14fb-489a-ad3e-fd873825b2e3"; :>> method = VerificationMethod::test; :>> procedureText = "issue529 is resolved - a test in keel-cli (beside human_authority_commands_refuse_an_ai_actor) reads the CliCommand facts in .engine/cli/commands.sysml and holds the two Rust lists to them in the direction the existing test lacks: every CliCommand whose declared facts say it records a human's verdict (today: a synopsis opening 'record a human's'; if the sprint prefers a declared fact it adds one to the CliCommand schema under a CR) is a member of HUMAN_AUTHORITY_COMMANDS and of HUMAN_ONLY_WRITE_COMMANDS, and every member of either list is such a CliCommand, so the test names any command in one place and not the other. VERIFY (probe pair, D0388): known positive - 'reject' removed from HUMAN_AUTHORITY_COMMANDS, the test fails naming reject; known negative - the real tree passes, as do accept_decision_refuses_ai_and_unregistered_judges and reject_decision_refuses_ai_and_unregistered_judges; clippy clean."; }
        action dcTouchedReceiptStatesItsOwnAttribution;
        verification dcTouchedReceiptStatesItsOwnAttributionDoD : Test { :>> id = "ccdc48dc-0de9-47de-b07f-89d7ea555b41"; :>> method = VerificationMethod::test; :>> procedureText = "issue530 is resolved - the touched receipt (.keel/metrics/touched-receipt.toml, written by keel suite --touched) states its own attribution: a `changed` array of every path the run attributed (keel-cli/src and .engine, tracked plus untracked) and an `attribution` table mapping each changed path to the stem it contributed (or to unattributed), so a reader checks stems against the receipt's own rows rather than re-deriving the rule; the test-verify skill's receipt-honesty row for `stems` (SKILL.md:126) is rewritten to compare `stems` to the receipt's `attribution` values and to name `init` as the stem every changed .engine path contributes, and the receipt line the verifier writes reads MATCH or MISMATCH from that comparison; sync-claude regenerates .claude/skills. VERIFY (probe pair, D0388): known positive - a receipt whose `attribution` names a stem absent from `stems` is reported MISMATCH by the skill's comparison, and a unit test in touched.rs fails when a changed .engine path is missing from `changed`; known negative - the real tree's receipt over a diff touching keel-cli/src and .engine/rules reads MATCH with init present; clippy clean."; }
        action dcScriptCallersOfTheCliAreHeldToTheSurface;
        verification dcScriptCallersOfTheCliAreHeldToTheSurfaceDoD : Test { :>> id = "47773a56-81ce-46b8-89dd-2458ecb20c9e"; :>> method = VerificationMethod::test; :>> procedureText = "DONE when a script that invokes a keel command by a spelling the CLI surface does not declare is a red gate at the commit that renames the command, not a null fact two commits later. FOUND (issue503): the D0450 fold moved orient, status and enforcement-report under show; scripts/exec_brief/facts.py kept the old spellings at four sites and emitted null facts until a brief build refused. DO: a guard (cli-callers-declared) scans scripts/**/*.py, .engine/tools/**/*.py, .claude/hooks and .githooks for keel invocations - the `[KEEL, 'a', 'b', ...]` argv form and the `keel a b` form in a command string - resolves each to a family/command/lens against .engine/cli/commands.sysml (the facts cli-surface-declared already holds), and fails on any spelling the surface does not declare, naming file:line and the nearest declared spelling; a `# not-keel:` marker exempts a line that names a command as prose. The guard is a Rust guard, so it carries its D0209 co-committed Decision and its D0388 pair (a fixture calling `keel orient` is red naming `show orient`; the same fixture calling `keel show orient` is green). VERIFY: the guard is green at HEAD after this commit's four fixes; reverting one fix makes it red at that file:line; the catalogue .engine/docs/guards.md carries the row and `keel version` counts it. ALSO (issue505): the same guard scans the document surface - README.md, CLAUDE.md, .engine/docs/**/*.md and .engine/skills/**/*.md - for a backticked `keel <verb> [<sub-verb>]` and for a bare backticked verb inside a table row or list that names commands, and fails on a spelling the surface does not declare; VERIFY adds a fixture README whose table names `orient` bare (red, naming `show orient`) and the same table naming `show orient` (green). Resolves issue503, issue505."; }
        action dcAuditHistoryLabelsTheBinarysSkew;
        verification dcAuditHistoryLabelsTheBinarysSkewDoD : Test { :>> id = "766506cc-c1db-430b-8738-40da9685e154"; :>> method = VerificationMethod::test; :>> procedureText = "DONE when `keel audit history` does not report a pre-fold commit as failing a guard that compares the running binary to a source tree the binary was not built from. FOUND in sprint 682's three-tree comparison: `keel audit history --max 3` with the post-fold binary judged all three pre-fold commits FAIL, where the pre-fold binary judged them PASS; the only red guard was cli-surface-declared, which holds the binary's Rust fact mirror (cli_facts.rs) equal to .engine/cli/commands.sysml - at a historical tree that comparison is between two different commits' surfaces and cannot pass after any fold. CI survives only because its --since range starts at the pushed commit; the `--max 20` fallback would go red on every fold. DO: audit history knows which guards are binary-bound (cli-surface-declared, and any guard whose input is the binary's own build: keel version, hardening floors) and, for a commit whose source files those guards read differ from the binary's build commit, reports them as SKEW with the file that differs, neither PASS nor FAIL; a commit whose only non-passing guards are SKEW is counted separately from the failing commits in the summary line ('N of M do not pass; K judged by a binary built from another tree'). VERIFY: the D0388 pair - a fixture range spanning a fact-surface change with the current binary reports SKEW on the older commit and PASS on the newer; the same range with a tree-only change (a .tracking edit) reports PASS/PASS; a genuinely red historical commit (an unresolved import in .tracking) still reports FAIL. The pre-fold comparison of the next fold (D0453, sprint 683) is re-run and the audit-history row is SAME or differs only in the SKEW label. Resolves issue504."; }
        action dcCliReferencesAreAListableLens;
        verification dcCliReferencesAreAListableLensDoD : Test { :>> id = "96905c77-d113-4898-82f0-949e263db6ed"; :>> method = VerificationMethod::test; :>> procedureText = "issue531 is resolved - a lens `keel show cli-references [ROOT]` (a CliCommand in .engine/cli/commands.sysml, family lens, stability experimental) renders every command reference guard cli-reference examines on the living doc surface, one row each: file:line, the token as written, the verb, the next token, the context (code or prose), and the verdict (dispatched, or the guard's defect text), with `--json`; the guard's `scanned` count and the lens's row count are computed by one function (cli_references over living_doc_files) and a unit test holds them equal on a fixture tree, so a survey of the surface is this lens and never a scratchpad script, and an Issue that names a site count cites the lens run that produced it. VERIFY (probe pair, D0388): known positive - a fixture doc line `keel guard .` appears in the lens as one row with verdict naming `keel gate guard`, and a prose sentence `for keel itself.` appears in no row; known negative - the real tree's lens rows all read dispatched and their count equals the guard's scanned; clippy clean; cli-surface-declared green with the new lens."; }
        action dcServedWhatsNextIsTheCliFrontier;
        verification dcServedWhatsNextIsTheCliFrontierDoD : Test { :>> id = "c71b21e7-90f5-4f54-aa6f-959bb2b17cdd"; :>> method = VerificationMethod::test; :>> procedureText = "Resolves issue535. The served whats-next view (serve.rs computed_binding 'whats-next') returns the same list, in the same order, as keel show whats-next: it calls orient::ready and nothing else, and lib.rs compute_orient_state / whats_next_root / orient_root either delegate to orient::ready or are removed with their one test caller (keel-cli/tests/cli_bdd.rs) re-pointed. VERIFY: a test in serve.rs or orient.rs builds a fixture with two action defs where the alphabetically-first ready action is declared second and asserts the served JSON's ready array equals the CLI frontier (declaration order); D0388 pair: that fixture (positive) and a single-def fixture where the two orders coincide (negative, would pass under the old code too and so is the guard that the test measures order, not presence). cargo test --release --lib for the touched modules passes; clippy -D warnings clean."; }
        action dcBriefExitFactsReadTheReturnCode;
        verification dcBriefExitFactsReadTheReturnCodeDoD : Test { :>> id = "30aeb06b-49a2-4699-acab-9498e998705a"; :>> method = VerificationMethod::test; :>> procedureText = "DONE MEANS: no fact the decision brief publishes under a name that asserts a process outcome (exit0, probeExit0) can derive from run()'s ok flag, which answers True for any command that printed. Resolves issue553. DO: facts.py carries run_rc (returncode, stdout) and every exit0 fact reads rc == 0; at start facts.py runs the D0388 pair on its own sensor - known-positive, a python -c that prints and exits 1 reads rc 1; known-negative, one that prints and exits 0 reads rc 0 - and refuses to emit any fact when either fails; a source scan refuses a key named exit0 or probeExit0 assigned from an ok flag. VERIFY: facts.py emits complete=true on the tree; recorderCheckerLive.perFixture reads exit0 false for each positive-* fixture and true for each negative-*; check_report.py run by hand on a positive fixture exits 1; the twenty-sixth builder no longer refuses at the D0473 block."; }
        // RAN: // RAN: python scripts/exec_brief/facts.py (repo root, 130675d) -> exit 0, complete=true, 200 facts; recorderCheckerLive.perFixture exit0: positive-undeclared-marker false, positive-sprint703-textpatch-write false, positive-sprint703-retro-recorded-twice false, negative-sprint647-receipt-driven true, negative-sprint703-record-only true; python check_report.py <positive-sprint703-textpatch-write> --root . -> exit 1 by hand; source-scan pair probed before the tree was read: the four old shapes ('exit0': _ok / bool(_fok) / bool(ok), 'probeExit0': bool(ok)) each caught, the four new shapes (_rc == 0 ...) each clean, live source 0 matches; runtime pair: python -c print+exit 1 -> rc 1, print+exit 0 -> rc 0 (facts.py refuses to emit otherwise); build_2026_09_14_facts_in_force_layering_build_skill.py -> wrote decision-brief.html, check_templates --brief clean
        part dcBriefExitFactsReadTheReturnCodeDoDR1 : TestResult { :>> id = "20b876b1-ee95-4876-92ec-85271b7e9669"; :>> outcome = VerdictKind::pass; :>> judgedAgainst = "130675d"; :>> judgedAt = "2026-09-14"; :>> judgedBy = "claudeFable5"; }
        action dcEveryEdgeKindHasAReader;
        verification dcEveryEdgeKindHasAReaderDoD : Test { :>> id = "94fb2f5c-7b9d-4c3c-a519-c597a17c53d9"; :>> method = VerificationMethod::test; :>> procedureText = "DONE MEANS: an edge kind that is authored anywhere under .tracking or .engine and read by no view is a guard violation, so a stored fact nothing consumes cannot sit silent (resolves issue554). DO: a guard edge-kind-readers computes the set of edge kinds the Model would store (every #Marker on a dependency plus the bare dependency, succession, satisfy, allocate, supersede, resultof, contains, flow, as edge_kind_from_marker and Model::build produce them) and the set of kinds some Rust source under keel-cli/src or members/ compares an edge's kind against; every stored kind has at least one reader or the guard names the kind, one file that authors it, and says no reader consumes it. Known-positive, chosen before the tree is read: a fixture marker #NobodyReadsThis on a dependency is named with its file; known-negative: the real tree at the adding commit passes, or every kind it names is either given a reader or retired by a Decision in the same commit. VERIFY: the pair is carried as --probe on the ladder; keel version's guard count rises by one and .engine/docs/guards.md carries the row; keel gate guard --no-receipt . passes."; }
        action dcSessionActorDoesNotInheritSilently;
        verification dcSessionActorDoesNotInheritSilentlyDoD : Test { :>> id = "36630bc7-9182-4022-bfa8-04d0c5d9f553"; :>> method = VerificationMethod::test; :>> procedureText = "Resolves issue620. A KEEL_ACTOR set for a single invocation no longer silently governs every later write in the session. Whichever shape is chosen -- do not persist a session actor that came from the environment; or persist it and say so on first use; or refuse when a session binding contradicts an explicit .keel/actor binding -- the D0388 probe pair is: positive, a session whose .keel/actor reads A and which ran one command under KEEL_ACTOR=B does not go on attributing later writes to B without saying so; negative, a session that ran `keel actor set B` deliberately still writes as B with no warning. Done when `keel actor` and .keel/actor can no longer disagree in silence."; }
        action dcConfirmationFlipChecksItsDelegation;
        verification dcConfirmationFlipChecksItsDelegationDoD : Test { :>> id = "901a57bb-7b31-4c51-8a93-858b7aed4ef9"; :>> method = VerificationMethod::test; :>> procedureText = "Resolves issue621. `keel record result` and `keel record gate-result` consult the confirmationRecord delegation before writing a method=confirmation result whose judgedBy is a Person, exactly as `keel accept` consults decisionAcceptance. D0388 probe pair: positive, a project with delegatedRecording commented out refuses an agent-session flip naming a human judge, with the same message shape `keel accept` gives; negative, a project that declares the delegation still records it, and a flip whose judge is the acting AI itself is untouched because it claims no human judgment. Done when the two write paths agree about whether this project granted the delegation."; }
        action dcAllocatedNameIsOneNamespaceAcrossPackages;
        verification dcAllocatedNameIsOneNamespaceAcrossPackagesDoD : Test { :>> id = "45a3f5ea-626b-44b4-8b72-f497b41da3fe"; :>> method = VerificationMethod::test; :>> procedureText = "Resolves issue624 (two clones each minted issue620 and issue621 on 2026-09-18 - claudeFable5 in issues-claudeFable5.sysml, claudeOpus5 in issues-claudeOpus5.sysml - and the merge landed the guard set GREEN: duplicate-identity's class 2 is per-package and the per-actor files are separate packages, while every lens resolves the bare name, so `keel show open-issues` showed ONE issue621 carrying both resolvers and hid the other's open issue620 behind this one's pass). DONE MEANS: (1) guard duplicate-identity gains class 5: a name the write API allocates by a whole-tree number scan - issueNNN, stNNN, usNNN (prefix + digits only; issue620Disp1 is not one) - declared in two places anywhere under .tracking is a VIOLATION naming both locations, whatever package each sits in. (2) The colliding pair in this tree is renumbered on the later-landing side (claudeFable5's issue620/issue621 -> issue622/issue623, D0108: owner edits own items) and every reference in that owner's files follows. (3) `keel land`'s merged-tree gate therefore refuses the next collision before the push, which is where this one should have been caught. KNOWN-POSITIVE (chosen before the tree was read): two files, two packages, each `part issue620 : Issue` with distinct ids -> exactly one violation naming issues-a.sysml:2 and issues-b.sysml:2; and the guard run over HEAD's two issue files as they were -> FAIL 2 violation(s), issue620 and issue621. KNOWN-NEGATIVE: the same two files at issue620 and issue621 -> clean; a `issue620Disp1` beside its Issue is not an allocated name; the renumbered tree -> duplicate-identity PASS."; }
        // RAN: cargo test --release -p keel-guards --lib allocated_name -> 1 passed (an_allocated_name_is_one_namespace_across_packages: KNOWN-POSITIVE two packages each part issue620 : Issue -> exactly one violation naming issues-a.sysml:2 and issues-b.sysml:2; KNOWN-NEGATIVE issue620 + issue621 across the two -> clean; is_allocated_name true for issue620/st167/us102, false for issue620Disp1/issue/story12/status); cargo test --release -p keel-guards --lib duplicate -> 2 passed (the four earlier classes unchanged) keel gate guard duplicate-identity --no-receipt over a scratch tree holding HEAD 5170199e two issue files as they were -> FAIL 2 violation(s): issues-claudeOpus5.sysml:2331 allocated name issue620 also declared at issues-claudeFable5.sysml:2209; :2342 issue621 also at :2220 renumbered tree (claudeFable5 issue620/621 -> issue622/623 in 10 files, 18 sites): keel gate guard duplicate-identity --no-receipt . -> PASS 1497 scanned 0 violation(s); keel gate validate . -> 863 clean
        part dcAllocatedNameIsOneNamespaceAcrossPackagesDoDR1 : TestResult { :>> id = "e5c53fea-e42d-496b-9414-d4920be29376"; :>> outcome = VerdictKind::pass; :>> judgedAgainst = "5170199e"; :>> judgedAt = "2026-09-18"; :>> judgedBy = "claudeFable5"; }
        action dcLandMergedGateReadsTheTreeTheMergeWrote;
        verification dcLandMergedGateReadsTheTreeTheMergeWroteDoD : Test { :>> id = "24a68bf8-1ab4-4d33-82af-e9a61d2e291f"; :>> method = VerificationMethod::test; :>> procedureText = "Resolves issue625 (keel land's merged-tree gate, run inside the post-commit hook at 1809e70f -> merge 5170199e, reported 2 edge-endpoints VIOLATIONS naming `dcSessionActorDoesNotInheritSilently` and `dcConfirmationFlipChecksItsDelegation` as declared nowhere, while both were declared in .tracking/backlog.sysml:2884/2886 of that merged tree and `keel gate validate .` + `keel gate guard .` run by hand on the same tree read 863 clean / ALL PASS; the merge had to be committed by hand). DONE MEANS: the cause is established by reproduction, not reasoning - a fixture with two clones where one adds a declaration in a shared file and a #Resolves edge from it in its own per-actor file and lands first, the other lands from inside a post-commit hook (GIT_INDEX_FILE and KEEL_HOOK set as the hook inherits them) - and the merged-tree gate reads the tree the merge WROTE: the corpus every guard resolves endpoints in is the merged working tree, never the pre-merge index a hook inherited, or the run says which read it made in its refusal line. KNOWN-POSITIVE: the reproduction fails today with the same two lines; KNOWN-NEGATIVE: the same two clones landed from a terminal (no hook environment) pass. If the reproduction does NOT fail, the DoD records that with the exact environment tried and the Issue closes as not reproduced with the observed refusal text kept."; }
        action dcEngineEmbedRerunsOnEngineChange;
        verification dcEngineEmbedRerunsOnEngineChangeDoD : Test { :>> id = "7fed6974-6a8b-471e-8133-3dd85af1ca57"; :>> method = VerificationMethod::test; :>> procedureText = "Resolves issue626 (members/keel-schema/src/embedded.rs:13 embeds .engine with one include_dir! and the crate has no build.rs, so an incremental cargo build after a .engine/ edit ships the PREVIOUS tree inside the binary unless embedded.rs is touched by hand; sprint 544's retro called it a build habit and CLAUDE.md sec 4 carries the `touch` as a reminder - D0047 says a reminder is not a control, and this session's D0524 guard-class work rebuilt twice before the touch was remembered). DONE MEANS: members/keel-schema gains a build.rs that emits `cargo:rerun-if-changed=<manifest>/../../.engine` (cargo scans a named directory recursively), so any changed, added or removed file under .engine/ recompiles keel-schema and every dependent, and the `touch members/keel-schema/src/embedded.rs` line leaves CLAUDE.md and the build skill because the build does it. KNOWN-POSITIVE (chosen before the change): add one file under .engine/docs/, run cargo build --release, `keel init` into a scratch dir - today the file is ABSENT from the scaffold; after: present. KNOWN-NEGATIVE: a second cargo build with nothing changed under .engine/ recompiles nothing (Finished with no Compiling line). Touched receipt: a changed .engine/ path already contributes stem `init` (issue530); this item does not change that."; }
        action dcAReleasePurposeNamesOnlyResolvedIssues;
        verification dcAReleasePurposeNamesOnlyResolvedIssuesDoD : Test { :>> id = "ead133e1-39f1-4253-8698-315f615494fc"; :>> method = VerificationMethod::test; :>> procedureText = "Resolves issue627 (release051's purpose and the cut commit 5f89df77 named issue623 as fixed in v0.5.1 while its resolver had no result and the Issue was open at the tagged tree; nothing read the claim against the model). DONE MEANS: guard release-recorded (or a sibling in the deploy unit) reads every `issueNNN` a Release's purpose names and FAILS when that Issue is computed OPEN at the Release's `commit` - resolution computed as open-issues computes it, by the resolver's passing result at or before that commit - naming the Release, the Issue and the resolver that has no pass; a Release naming no Issue scans clean; an Issue resolved after the tag but before HEAD is still a violation (the binary the tag ships does not carry it). The CHANGELOG is out of scope: it is prose the release skill's doc-sync pass reads. KNOWN-POSITIVE (chosen before the change): a fixture Release at commit C whose purpose names an Issue whose resolver's only pass is judged at a commit after C -> one violation naming all three; release051 as authored at 5f89df77 (purpose naming issue623) -> one violation. KNOWN-NEGATIVE: release051 as corrected (issue615-617, issue622, issue624 - each resolved at 5f89df77) -> clean; a Release with no issue reference -> clean."; }
        action dcGitHubAnswerRendersFromTheModel;
        verification dcGitHubAnswerRendersFromTheModelDoD : Test { :>> id = "a62e92e0-da67-44c2-b8c9-dcdac2592ae2"; :>> method = VerificationMethod::test; :>> procedureText = "Resolves issue628 (GH#88's v0.5.1 answer named issue612's resolver by a name the tree does not hold; every fact in a github-intake step-4 comment is computed and was typed). DONE MEANS: `keel github answer --issue N [--release <tag>] [--dry-run]` renders the comment for GitHub issue N from the model - the Statement whose sourceUrl is that issue, its story, the Issue(s) the story #Implicates, each Issue's #Resolves resolver and whether it is computed resolved (open-issues' rule), and the Release whose `commit` is an ancestor of HEAD containing the resolver's passing result when --release names a tag - and posts it through `gh issue comment --body-file` from a file the render wrote, never from a shell argument (D0224); --dry-run prints the file and posts nothing; an Issue still computed OPEN renders as 'tracked, not yet resolved' and the command refuses --close for it. The command is a CliCommand fact in .engine/cli/commands.sysml (D0271) and the github-intake skill's step 4 names it in place of 'comment the tracked id'. KNOWN-POSITIVE (chosen before the change): a fixture Statement for GH#88 with issue612 -> the render names dcSourceReferenceReadsTheAdoptersOwnClaims and no other resolver; KNOWN-NEGATIVE: a GitHub issue no Statement cites -> refused naming `keel github ingest`."; }
        action dcGuardReaderSkipsStringLiterals;
        verification dcGuardReaderSkipsStringLiteralsDoD : Test { :>> id = "e67d0836-aaee-4434-ac9a-c2ee61c0290d"; :>> method = VerificationMethod::test; :>> procedureText = "Resolves issue629. The guard reader members/keel-guards/src/sprints.rs declared_tests reads a Test's block as raw text to the first close brace and decides confirmation by the substring VerificationMethod::confirmation anywhere in it, and reads title by the same raw search, so a string literal inside the block is read as if it were a field: a procedureText that quotes the confirmation literal, or a title that says sitting review, changes the verdict, and a close brace inside a string ends the block early. DONE MEANS: the reader skips string literals when it looks for the method, the title and the block's end, so only fields outside quotes count; the pre-existing four tests still pass and two new ones hold the D0388 pair written before the fix - known-positive a Test with method = VerificationMethod::analysis whose procedureText quotes VerificationMethod::confirmation is not read as confirmation; known-negative a Test with method = VerificationMethod::confirmation on its own line after a procedureText containing a close brace is still read as confirmation with the right name. keel gate guard sitting-review-method reports the same scanned count on this tree before and after. clippy -D warnings clean; the sprints unit tests pass."; }
        // RAN: // RAN: ./target/release/keel-serve.exe verify . --probe-from C:/Users/WilliamWeatherholtz/AppData/Local/Temp/claude/C--Users-WilliamWeatherholtz-claude-code-sysmlv2-ai-toolkit/b43aa4fc-84f7-4c3d-bc35-61eccafbbda8/scratchpad/pair747.txt -> outcome=pass stopped_at=none seconds=969 at=1789810795 (1789810795>1789809822: ok) // RAN: outcome=pass passed=943 failed=0 seconds=850 at=1789810795 launch=1789809822 (1789810795>1789809822: ok)
        part dcGuardReaderSkipsStringLiteralsDoDR1 : TestResult { :>> id = "0fcf2a4d-be3e-4f26-aa15-3693ffc606dd"; :>> outcome = VerdictKind::pass; :>> judgedAgainst = "abe64e84"; :>> judgedAt = "2026-09-19"; :>> judgedBy = "claudeFable5"; }
        action dcScratchCloneProbeAssertsItsPlant;
        verification dcScratchCloneProbeAssertsItsPlantDoD : Test { :>> id = "a54a1d29-62f2-4e7b-9d91-57c8004e1f1d"; :>> method = VerificationMethod::test; :>> procedureText = "DONE MEANS: a scratch-clone probe helper, scripts/probes/scratch_clone.py, is the one way a known-negative is planted in a clone of this repository (D0388): it clones with core.longpaths=true to the directory it is given, refuses to continue while git status --short in the clone lists anything (a failed checkout leaves every path staged as deleted, and a commit -a there records the whole tree's deletion), applies the planted edit as a single staged path, commits with hooks off, and prints the diff stat of the probe commit - refusing when that stat names more than the one planted path - before it runs the command under test and reports that command's exit code and output. Carries a `# ci-probe: --probe` line: its known-positive is a clone where the planted edit is one path and the stat shows one file; its known-negative is a clone whose checkout it is made to leave dirty (a path longer than the host limit under a deliberately deep target), which it refuses before committing anything. Resolves issue630. The evidence: sprint 748's first known-negative for keel audit adherence was run in a clone at the scratchpad path whose checkout had failed with Filename too long; commit -a there recorded 2122 deletions and the audit named every guard absent - a refusal that looked like the negative case passing and was not. The second attempt, with core.longpaths=true and one staged path, named guard:ceremony alone."; }
        action dcVerifierTreeWrittenSeesEveryPath;
        verification dcVerifierTreeWrittenSeesEveryPathDoD : Test { :>> id = "0f4fbecf-6b28-4305-9dd0-b3497f59f11b"; :>> method = VerificationMethod::test; :>> procedureText = "DONE MEANS: the SubagentStop hook's verifier baseline and its stop-time reading cover every path git would report - hook_subagent_stop (members/keel-hooks/src/lib.rs) folds the fingerprint of .tracking and .engine together with git status --porcelain --untracked-files=all over the project root, so a verifier that leaves a new file at the repo root, under scripts/, or under a member crate is routed VerifierTreeWritten and ledgered verifier:tree-written like one that edits a .sysml file. Resolves issue631. A unit test under keel-hooks plants an untracked file at a root outside .tracking/.engine between the baseline and the stop reading and asserts the route is VerifierTreeWritten; its known-negative plants nothing and asserts Silent (D0388). The evidence: sprint 748's verifier redirected keel verify --wait into verify-wait-output.txt at the repo root; the hook fired Silent and the ledger's last verifier:tree-written line predates the run, because fingerprint.rs folds only .tracking and .engine."; }
        action dcVerdictChannelIsOneSurface;
        verification dcVerdictChannelIsOneSurfaceDoD : Test { :>> id = "3774029e-86bd-4308-90c9-b344f1a4dc4c"; :>> method = VerificationMethod::demo; :>> procedureText = "Resolves issue632. DONE MEANS: the project's human can drive every decision the loop hands them -- accept, reject, dispose a finding, sign a confirmation -- from wherever they are, with nothing to copy and nothing to type twice. Concretely: (1) one surface, reachable from a phone or a browser away from the machine that runs keel, lists every pending gesture with the same substance the CLI computes: the Decision's context, the clauses it reverses, the critique recorded against it, and what the frontier does when it is accepted or rejected; (2) a tap or a sentence on that surface IS the gesture: the verdict and the human's words are captured by the surface itself and written through the write API with the D0192/D0198 substance (a quoted span or a cited gesture), the human never restating them in a terminal, a chat, or a file; (3) the same surface works when the machine is local and when the session is remote, and its verdicts arrive in the tree as receipts an agent session can act on without a human present; (4) a delegation grant is itself a gesture on that surface, so a fresh project's policy file is not a hand-edit; (5) `keel serve` local-only, the deprecated GitHub gesture, the retired Smartsheet inbox and quoted chat words are each measured against these clauses and either retired or named as the transport. Demo: a fresh project, a proposed Decision, a phone, an acceptance recorded with the human's words and the frontier re-ranked -- zero terminal, zero paste."; }
        action dcGithubPullWalksEveryPage;
        verification dcGithubPullWalksEveryPageDoD : Test { :>> id = "a263401b-5b5b-47d1-8beb-937afb57d4ae"; :>> method = VerificationMethod::test; :>> procedureText = "Resolves issue633. keel github pull walks every page of the open-issue list: github_ingest.rs follows the GitHub API page sequence (per_page=100, page=N until a page comes back short) instead of one request at the --limit, and --limit, when given, caps the total ingested rather than the page size; the pull report states pages fetched, issues seen and Statements written so a short read is visible in the receipt. keel currency passes no limit and therefore gets the whole list (currency.rs pull_args). Known-positive, chosen before the tree is read: a repository with more open issues than one page - this one, 44 open on 2026-09-19 - pulled with no --limit yields a Statement for every open issue no Statement cites (before the change, 30 at most: GH#9, #29, #31, #32 among the fourteen never reached). Known-negative: a repository whose open list fits one page pulls exactly once and the report says 1 page. The fetch is behind a function that the unit test drives with a fake page sequence, so the test needs no network."; }
        action dcInitAppendsToGitignore;
        verification dcInitAppendsToGitignoreDoD : Test { :>> id = "4be1ddca-fe41-45ec-8c89-30a884d34e5b"; :>> method = VerificationMethod::test; :>> procedureText = "Resolves issue634. keel init on a directory that already holds a .gitignore appends the keel entries it does not find and leaves every existing line in place, in order, instead of replacing the file. Known-positive: a .gitignore with three project lines gains the keel entries below them. Known-negative: a file already carrying every keel entry is left byte-identical. Covered by a unit test over a fake directory. GH#83 (st158)."; }
        action dcAcceptFindsTheExistingEvent;
        verification dcAcceptFindsTheExistingEventDoD : Test { :>> id = "10b79ef4-da46-41c5-9100-85c5552ff536"; :>> method = VerificationMethod::test; :>> procedureText = "Resolves issue635. keel accept on a Decision whose file already declares its <id>Accept verification (a hand-authored Decision in the documented shape) records the human's result against that existing event instead of appending a second one, so the file validates after the accept. Known-positive: a Decision authored with its Accept event accepts cleanly and validate stays green. Known-negative: a Decision with no event still gains one. Covered by a unit test over accept_decision_locked. GH#71 (st121, st138)."; }
        action dcValidateReadsANamedDependency;
        verification dcValidateReadsANamedDependencyDoD : Test { :>> id = "44af8b29-8fa6-4959-9bdb-5430eb01c9b7"; :>> method = VerificationMethod::test; :>> procedureText = "Resolves issue636. keel validate accepts a SysML v2 dependency that carries a name before its from clause (`dependency name from A to B;`), as the kernel grammar does, and the parser test suite holds a named and an anonymous dependency side by side. Known-positive: a named dependency validates. Known-negative: a dependency with no from clause is still refused with the same message as today. GH#72 (st125, st137)."; }
        action dcLandRefusesAnUnknownArgument;
        verification dcLandRefusesAnUnknownArgumentDoD : Test { :>> id = "20cf55b3-440a-41ef-b0e6-61a94f1a6f3e"; :>> method = VerificationMethod::test; :>> procedureText = "Resolves issue637. keel land takes only the arguments its CliCommand fact declares; `--help` prints usage and exits 0 without landing, and any other unknown flag is refused with exit 2 before a single git command runs. Known-positive: `keel land --help` prints usage, pushes nothing. Known-negative: `keel land .` still lands. Covered by a unit test over the argument parse. GH#73 (st124, st136)."; }
        action dcAClaimCommitCarriesOnlyTheClaim;
        verification dcAClaimCommitCarriesOnlyTheClaimDoD : Test { :>> id = "3cb89e51-598d-4f96-80c8-f6aafd86e6b2"; :>> method = VerificationMethod::test; :>> procedureText = "Resolves issue638. keel claim commits the claim file alone in its own commit, and keel land refuses a commit whose diff touches a claim file together with any other path, naming both. Known-positive: a claim followed by land produces a commit containing only the claim. Known-negative: a staged edit beside the claim is refused by land with the two paths named. Covered by a unit test over the ride-along check. GH#74 (st123, st135)."; }
        action dcRecordDecisionNamesEveryMissingFlagAtOnce;
        verification dcRecordDecisionNamesEveryMissingFlagAtOnceDoD : Test { :>> id = "69ba4111-cae5-4b73-b3f6-c04a64513b0e"; :>> method = VerificationMethod::test; :>> procedureText = "Resolves issue639. keel record decision with missing required inputs reports every missing flag in one message, and `keel record decision --help` prints the usage instead of the refusal. Known-positive: an invocation missing two flags names both. Known-negative: a complete invocation is unchanged. GH#75 (st134)."; }
        action dcActivateWritesTheCharter;
        verification dcActivateWritesTheCharterDoD : Test { :>> id = "4b438109-fbcd-4d49-ad39-4154872e5c67"; :>> method = VerificationMethod::test; :>> procedureText = "Resolves issue640. keel activate and keel deactivate accept --charter dNNNN and write charteredBy under [processes] in .engine/contracts/activation.toml, and keel onboard step 5 names that flag instead of a hand edit. Known-positive: `keel activate agile-workflow --charter d0001` yields a manifest keel onboard reads as CHARTERED. Known-negative: an unknown Decision id is refused. Covered by a unit test over the manifest writer. GH#77 (st132)."; }
        action dcPreBashSeesABacktickInsideARecordArgument;
        verification dcPreBashSeesABacktickInsideARecordArgumentDoD : Test { :>> id = "5d7f07af-cb6f-42da-92f1-effeb754bd89"; :>> method = VerificationMethod::test; :>> procedureText = "Resolves issue641. The pre-bash hook's classifier recognises a keel record invocation whose double-quoted argument contains a backtick and denies it naming the argument, before the shell runs it. Known-positive: a record issue call whose quoted --description names a command in backticks is denied. Known-negative: the same text read from a file with --description-from passes. Covered by a unit test over bash_classify. GH#79 (st130)."; }
        action dcHookIntegrityExpandsTheProjectDir;
        verification dcHookIntegrityExpandsTheProjectDirDoD : Test { :>> id = "309a8586-67aa-4f24-9775-a89090358f43"; :>> method = VerificationMethod::test; :>> procedureText = "Resolves issue642. guard hook-config-integrity expands $CLAUDE_PROJECT_DIR (and ${CLAUDE_PROJECT_DIR}) in a hook command before comparing it to the expected binary path, so a settings file written the way Claude Code documents passes. Known-positive: a command using the variable passes. Known-negative: a command naming a different binary still warns. GH#80 (st129)."; }
        action dcBuildStampsAFixedWidthCommit;
        verification dcBuildStampsAFixedWidthCommitDoD : Test { :>> id = "ed584732-99f1-4713-b146-dbaaab401e80"; :>> method = VerificationMethod::test; :>> procedureText = "Resolves issue643. build/provenance.rs (keel-cli/build.rs until sprint 757; provenance.rs:32 today) stamps the build commit with `git rev-parse --short=8`, so two machines building one commit report one stamp. Known-positive: two builds of one commit agree. Known-negative: a dirty tree still says so. GH#81 (st128)."; }
        action dcParserKeepsEveryMarkerInAnActionDef;
        verification dcParserKeepsEveryMarkerInAnActionDefDoD : Test { :>> id = "709b6c35-0695-46c5-bf0a-09f21484cb19"; :>> method = VerificationMethod::test; :>> procedureText = "Resolves issue644. The parser records every `#Marker dependency from A to B;` declared inside an action def body, not only succession markers, so a #Covers edge authored beside its sitting review is indexed and traced. Known-positive: 74 #Covers edges inside a delivery def all appear in trace. Known-negative: a marker outside any def is unchanged. Covered by a parser unit test. GH#60 (st108, st149)."; }
        action dcMigrateBlocksOnAProjectExtendedEngineFile;
        verification dcMigrateBlocksOnAProjectExtendedEngineFileDoD : Test { :>> id = "91a00a71-e9eb-4c64-a1a0-55ffe8915a91"; :>> method = VerificationMethod::test; :>> procedureText = "Resolves issue645. keel migrate treats an engine-shipped file the project has extended (a schema file with project metadata defs, a process file with a project step) as a Blocker naming the file and the project's additions, instead of staging the engine's version over it. Known-positive: a relationships.sysml with 25 project metadata defs blocks with those names listed. Known-negative: an unmodified engine file migrates as today. GH#61 (st107, st148)."; }
        action dcDispositionNeedsItsResult;
        verification dcDispositionNeedsItsResultDoD : Test { :>> id = "5d23070d-c394-4cdc-98a4-48026328ac25"; :>> method = VerificationMethod::test; :>> procedureText = "Resolves issue646. issue_disposition reads a disposition only from a Test that has a TestResult judged by a human; a confirmation Test carrying acceptRisk with no result leaves the Issue open. Known-positive: a dispositioned Test with a passing human result closes the Issue. Known-negative: the same Test with no result leaves it open in open-issues. Covered by a unit test. GH#62 (st106, st147)."; }
        action dcMigrateTracksTheOverlayHook;
        verification dcMigrateTracksTheOverlayHookDoD : Test { :>> id = "5016027f-eb82-48f1-b37c-9a6123d47b71"; :>> method = VerificationMethod::test; :>> procedureText = "Resolves issue647. keel migrate runs a project's declared post-migrate overlay (tools/after_migrate.py or the path named in .engine/contracts/migration.toml) between apply and gate, so the gate judges the repaired tree and a project pin survives a verified migration. Known-positive: a project whose overlay restores two cutoffs migrates green. Known-negative: a project with no overlay is unchanged. GH#68 second defect (st114, st141)."; }
        action dcRecordResultFindsAStandaloneTest;
        verification dcRecordResultFindsAStandaloneTestDoD : Test { :>> id = "e748fad6-16c8-4c07-b223-ed8ddd3ef287"; :>> method = VerificationMethod::test; :>> procedureText = "Resolves issue648. keel record result addresses a `verification x : Test` declared at package level (not inside an action def) and appends the TestResult beside it. Known-positive: a standalone Test gains a result. Known-negative: an unknown name is still refused. Covered by a unit test over the block lookup. GH#69 (st113, st140)."; }
        action dcLandReadsPorcelainBeforeLanded;
        verification dcLandReadsPorcelainBeforeLandedDoD : Test { :>> id = "31900169-138b-4646-b381-54d9660b6d7c"; :>> method = VerificationMethod::test; :>> procedureText = "Resolves issue649. keel land reads `git status --porcelain` after its commit and before printing landed, and refuses with the dirty paths named when anything is left unstaged or uncommitted. Known-positive: a clean landing prints landed. Known-negative: a session that authored a file it never staged is refused with the path. GH#9 (st059, st180)."; }
        action dcProtectedPathsBindToThePath;
        verification dcProtectedPathsBindToThePathDoD : Test { :>> id = "82aaae88-b0d4-4638-a46e-0ff8d8d81396"; :>> method = VerificationMethod::test; :>> procedureText = "Resolves issue650. The pre-bash and pre-write hooks protect a fact surface by its path, whatever tool writes it: .engine/decisions is a tracking target, and an rm, mv or shell redirect aimed at a protected path is classified and denied like an Edit. Known-positive: `rm .engine/decisions/0001-x.sysml` is denied. Known-negative: rm of a scratch file passes. Covered by a unit test over tracking_target. GH#32 (st054, st177)."; }
        action dcScaffoldPlaceholderSeesTheStarterActors;
        verification dcScaffoldPlaceholderSeesTheStarterActorsDoD : Test { :>> id = "a1bcd810-4728-4c1c-916d-b7ffe2b5ec48"; :>> method = VerificationMethod::test; :>> procedureText = "Resolves issue651. guard scaffold-placeholder fails on any actor keel init wrote as a placeholder (the STARTER_ACTORS names, `Your Name` included) that is still declared and still unrenamed when the project has its first non-scaffold item. Known-positive: a fresh strict project with `Your Name` still declared and one recorded task fails. Known-negative: the same project after actor enrollment passes. GH#33 (st053, st157)."; }
        action dcTraceWalksMarkerEdges;
        verification dcTraceWalksMarkerEdgesDoD : Test { :>> id = "53b8faa8-1cc5-4c4f-90a7-9f65709566bc"; :>> method = VerificationMethod::test; :>> procedureText = "Resolves issue652. keel trace reports every typed edge reaching an item in both directions, marker-form dependencies included, matching its own help text; the indexer records every `#Marker dependency` as an edge of that marker's kind. Known-positive: an item with one #DerivedFrom edge shows it upstream. Known-negative: an unknown name still exits non-zero. GH#34 (st046, st156)."; }
        action dcCompoundGuardExemptsASupersededDecision;
        verification dcCompoundGuardExemptsASupersededDecisionDoD : Test { :>> id = "80ee4c31-aa59-476a-afc5-c904a996cfa0"; :>> method = VerificationMethod::test; :>> procedureText = "Resolves issue653. guard decision-scaffolding does not report a compound Decision that a #Supersede edge has retired, whatever its date, and says how many it exempted for that reason. Known-positive: a post-cutoff compound Decision with a Supersede edge aimed at it passes. Known-negative: the same Decision with no Supersede edge is reported. Covered by a unit test beside compound_decisions. GH#94 (st170)."; }
        action dcRecordDecisionRefusesACompoundClause;
        verification dcRecordDecisionRefusesACompoundClauseDoD : Test { :>> id = "e3b4923c-5516-477f-97b3-7f8aabf88b0a"; :>> method = VerificationMethod::test; :>> procedureText = "Resolves issue654. keel record decision runs clause_count over the decision text before writing and refuses a text enumerating two or more clauses, naming the count and D0303, so a compound Decision is never recorded and then auto-accepted. Known-positive: a `(1) ... (2) ...` text is refused. Known-negative: a one-clause text is written. GH#93 (st171)."; }
        action dcReviewRoundTripRefusesAnAgentVerdict;
        verification dcReviewRoundTripRefusesAnAgentVerdictDoD : Test { :>> id = "aa7361ac-80d7-4c53-bfb1-861b2d6bafaf"; :>> method = VerificationMethod::test; :>> procedureText = "Resolves issue655. keel record review applies the same verdict_channel_refusal as keel accept, keel reject and keel judge-set: a human verdict carried in a review file is refused from an agent environment unless a delegation grant names the recorder. Known-positive: a review file carrying a human pass under an agent session is refused. Known-negative: the same file under a TTY passes. GH#92 (st172)."; }
        action dcMigrateSeesARemovedEnumMember;
        verification dcMigrateSeesARemovedEnumMemberDoD : Test { :>> id = "66017af6-e04e-4af6-aaf9-dff78df3bc53"; :>> method = VerificationMethod::test; :>> procedureText = "Resolves issue656. keel migrate enumerates the items affected when the engine removes an enum MEMBER (as it does for a removed type), naming each `Enum::member` use, and refuses until they are migrated. Known-positive: a tree using a member the new engine dropped is refused with the paths. Known-negative: a tree using only surviving members migrates. GH#91 (st173)."; }
        action dcIntakeShowsANeedStoryWithoutANeed;
        verification dcIntakeShowsANeedStoryWithoutANeedDoD : Test { :>> id = "58c52d30-a3d4-440b-a641-3395f33ce275"; :>> method = VerificationMethod::test; :>> procedureText = "Resolves issue657. keel show intake lists every UserStory with implication need that no Need cites through #DerivedFrom, under needStoriesWithoutNeed, so a need that was translated and never elevated is visible. Known-positive: a need story with no Need appears. Known-negative: one a Need cites does not. GH#95 (st176)."; }
        action dcResolverLookupCoversEveryDef;
        verification dcResolverLookupCoversEveryDefDoD : Test { :>> id = "2ff9a06d-5e37-4eae-a2b7-2895796dcd55"; :>> method = VerificationMethod::test; :>> procedureText = "Resolves issue658. record issue --resolver accepts an action declared inside any project action def under .tracking (not only backlog.sysml and delivery/), and its refusal message names the file set searched in grammatical English. Known-positive: an action in .tracking/architecture/x.sysml resolves. Known-negative: an undeclared name is refused. GH#41 (st050, st150)."; }
        action dcBriefDraftKeyIsThePublishedSet;
        verification dcBriefDraftKeyIsThePublishedSetDoD : Test { :>> id = "9caa7079-1136-40c0-9e4a-b04434ddaa61"; :>> method = VerificationMethod::test; :>> procedureText = "DONE MEANS: Resolves issue659. The brief page's draft store (chosen courses and the note the reader types before Record) is keyed on the published decision set and tree, never on a value that is the same across briefs; a page with no declared set restores nothing. check_templates --brief refuses a page whose draft-store key is document.title, naming the mechanism, with a self-test pair (title-keyed refused, set-keyed passes). The six-held builder carries the live verdict block forward on a republish (--carry FILE) so a fix to the page never drops a recorded verdict, and the digest footer reads as a sentence. Verified: the self-test passes; the standing brief is republished with the six records intact and the note empty."; }
        // RAN: // RAN: python scripts/check_templates.py --self-test -> exit 0; 'ok title-keyed draft store refused', 'ok set-keyed draft store passes', 'ok a JSON data block is not reader prose', 'ok the same words in a paragraph are refused'; last line 'check_templates --self-test: pass' // RAN: python scripts/check_templates.py --brief previous_0919b.html (the page as it was live) -> 1 violation: 'the draft store is keyed on document.title' (known positive) // RAN: python scripts/exec_brief/build_2026_09_19_six_held.py facts.json previous_0919b.html decision-brief-six.html --carry verdicts_live.json -> exit 0; python scripts/check_templates.py --brief decision-brief-six.html -> 'brief contract: clean', exit 0; node --check on the page's tail script -> ok // RAN: Artifact publish to https://claude.ai/code/artifact/634dee77-bdfb-49e1-925e-929f4a3c2bf4 (label six-held-draftkey-fix), then Artifact read of the live page: keel-verdicts block holds 6 records d0525,d0527,d0528,d0529,d0530,d0531 seq 1-6; 'keel-brief:'+document.title' absent; '.page[data-set]' key present with two if(!key)return guards; data-set='d0525,d0527,d0528,d0529,d0530,d0531@59ebd752'; footer ends '132 open. Source repository.'
        part dcBriefDraftKeyIsThePublishedSetDoDR1 : TestResult { :>> id = "f45444e5-cf5c-4245-9633-2b2c6c86da2c"; :>> outcome = VerdictKind::pass; :>> judgedAgainst = "59ebd752"; :>> judgedAt = "2026-09-19"; :>> judgedBy = "claudeFable5"; }
        action dcBriefTailIsAnAuthoredSource;
        verification dcBriefTailIsAnAuthoredSourceDoD : Test { :>> id = "17416bb9-11bb-4b8f-9bd2-dc81237e54bb"; :>> method = VerificationMethod::test; :>> procedureText = "DONE MEANS: the brief page's tail script (tabs, copy digest, draft store, verdict capture) is one authored source under scripts/exec_brief/ that every builder reads, never a byte-for-byte copy of the previous published page's tail; a builder that still slices its tail from a previous page is refused by check_templates --self-test or a guard naming the builder; the authored source carries its own node --check and the D0388 pair (a tail with a title-keyed draft store refused, the authored tail passes). Verified: the standing brief rebuilt from the authored tail is byte-identical in behaviour - same keel-verdicts block, same data-set key, brief contract clean."; }
        action dcCodeRegistryRowsFollowTheCode;
        verification dcCodeRegistryRowsFollowTheCodeDoD : Test { :>> id = "00af7d65-fe85-43bd-b532-f6d2435a41d6"; :>> method = VerificationMethod::test; :>> procedureText = "Sprint 750 retro finding. The code registry (.tracking/architecture/code-registry.sysml) is authored fact about where risk-classed code lives: ceHookDispatch said filePath keel-cli/src/main.rs and titled itself main.rs cmd_hook from sprint 739 (when cmd_hook moved to members/keel-hooks/src/lib.rs, D0511) until sprint 750 noticed it by hand, because no guard reads filePath and the file it named still existed. Every D0479 extraction moves code and none of them is asked whether a registry row followed. DONE MEANS: a guard (family: architecture) reads every CodeElement's filePath and holds that the path exists in the tree and, for kind = function, that a fn whose name the title contains is defined in that file; a module row holds when the path exists. A row that fails names the element, the path and what was not found, and the fix is a registry edit (or a #Supersede if the code is gone), never a guard exception. Known-positive, chosen before the registry is read: a fixture CodeElement of kind function whose title names cmd_hook with filePath keel-cli/src/main.rs FAILS naming the element and the file. Known-negative: the registry at the commit that lands this guard passes with every row named. The guard is enforcement surface and lands with its marked Decision."; }
        action dcAgentHarnessLandscapeIsRecorded;
        verification dcAgentHarnessLandscapeIsRecordedDoD : Test { :>> id = "140065f6-2897-4b09-9c4e-f62312590649"; :>> method = VerificationMethod::analyze; :>> procedureText = "The human's ask of 2026-09-20 (st184): research alternative harnesses - Bazel and GitHub Actions, sandbox container setups for AI agents, anyone strongly considering custom processes and verification workflows, other strengths to integrate - fifty tools, noting what has gained a following recently. DONE MEANS docs/reviews/agent-harness-landscape-2026-09-20.md exists carrying the human's words verbatim, the answer first in the order they asked, at least fifty tools in dated URL-cited table rows across five lenses (sandboxes; task-owning harnesses; workflow and durable-execution engines; hermetic build and CI; verification, spec and attestation), a ranked table of mechanisms to integrate each naming the tool it runs in, a following-recently table with numbers and dates, the cross-lens convergences, the adversarial case against the tool-owns-the-task design with a disposition per critique, the check date and epistemic status stated in the header, and the five lens reports appended verbatim with their sources; the knowledge record .tracking/knowledge/agent-harness-landscape-2026-09-20.sysml holds the D0196 replication text with a passing result at HEAD; D0540 charters the spike as saved with no tool adopted and no backlog item raised against the unapproved design. VERIFY: grep the review for each required section heading and count its numbered table rows (>= 50); keel gate validate .; keel gate guard --no-receipt; every lens claim about keel's own code re-checked against source before it is used, the check named beside it in the synthesis."; }
        // RAN: grep -c '^| *[0-9]* *|' docs/reviews/agent-harness-landscape-2026-09-20.md -> 110 (>= 50); grep -n '^# Appendix' -> 0, A, B, C, D, E once each; grep -n 'Check date/|pistemic status' -> header lines present; keel gate validate . -> 878 tracking file(s) validated clean; keel gate guard --no-receipt -> ALL PASS; lens claims about keel's own code re-checked: D0054 at CLAUDE.md section 4, keel accept --words D0192/D0289 at CLAUDE.md section 4, both named beside their use in the synthesis.
        part dcAgentHarnessLandscapeIsRecordedDoDR1 : TestResult { :>> id = "1889af25-36d9-4f82-9654-4282980f5ac4"; :>> outcome = VerdictKind::proposed; :>> judgedAgainst = "68fb803bc14646ab17f5cb8f0106f9fcbd04223f"; :>> judgedAt = "2026-09-20"; :>> judgedBy = "claudeFable5"; }
        action dcRunnerDaemonLandscapeIsRecorded;
        verification dcRunnerDaemonLandscapeIsRecordedDoD : Test { :>> id = "4cf2f26a-6e58-41bf-aeca-879bb8270b52"; :>> method = VerificationMethod::analyze; :>> procedureText = "The human's ask of 2026-09-21 (st187): what a runner daemon actually is - research best practices in existing frameworks, look up complaints from fifty forum threads to see user-identified weaknesses of their approach, and set ourselves apart. DONE MEANS docs/reviews/runner-daemon-landscape-2026-09-21.md exists carrying the human's words verbatim, the answer first: the runner-daemon practice table across CI runners, workflow and queue workers, agent-harness runners and the runner-facing protocols as specified, each row dated and URL-cited; at least fifty numbered forum threads in dated URL-cited rows each quoting the user's complaint verbatim and each dispositioned against our design as ADDRESSED, VULNERABLE or N/A with a clause why; the complaint themes ranked by recurrence with the thread numbers behind them; the set-apart section listing, per recurring user-identified weakness, the design mechanism that answers it or the honest statement that the design is vulnerable; the check date and epistemic status stated in the header; the five lens reports appended verbatim with their sources. The knowledge record .tracking/knowledge/runner-daemon-landscape-2026-09-21.sysml holds the D0196 replication text with a passing result at HEAD; the charter Decision saves the spike with no tool adopted and no backlog item raised against the unapproved design. VERIFY: grep the review for each required section heading; count its numbered thread rows (>= 50); keel gate validate .; keel gate guard --no-receipt; every lens claim about keel's own code re-checked against source before it is used, the check named beside it in the synthesis."; }
        // RAN: grep -n of section headings in docs/reviews/runner-daemon-landscape-2026-09-21.md finds the practice table, the thread tally, the ranked themes, the set-apart table, the epistemic header and Appendices 0 and A-E; grep -c of numbered thread rows -> 224 (122 complaint threads, above fifty); keel gate validate . -> 881 tracking file(s) validated clean; keel gate guard --no-receipt -> ALL PASS; every lens claim about keel's own code re-checked against source with the check named beside it in the synthesis (five kept, one count corrected to 98 lines); knowledge record holds the D0196 text with a passing result; D0541 saves the spike with no tool adopted and no item against the unapproved design.
        part dcRunnerDaemonLandscapeIsRecordedDoDR1 : TestResult { :>> id = "1df43d50-ede8-4e5f-ae36-e9322c57f51d"; :>> outcome = VerdictKind::proposed; :>> judgedAgainst = "0bef913f6be26971b81c752aacd7dbd1785df30f"; :>> judgedAt = "2026-09-21"; :>> judgedBy = "claudeFable5"; }
        action dcRunnerDirectionPanelIsRecorded;
        verification dcRunnerDirectionPanelIsRecordedDoD : Test { :>> id = "ded3827d-0c8c-46bb-8752-3d7d7f513d24"; :>> method = VerificationMethod::analyze; :>> procedureText = "The human's ask of 2026-09-22 (st190): critique the tool-owns-the-task runner-protocol direction with a panel, make an artifact, and make the case that it is the right direction. DONE MEANS docs/reviews/runner-direction-panel-2026-09-22.md exists carrying the human's words verbatim, the direction artifact as attacked (every revision, with its finding-to-resolution map), every panelist's report per round verbatim with its numbered findings, severities, evidence and verdict, the round-by-round verdict table, the irreducible disagreements handed to the human if convergence stopped, and the independence honesty note verbatim: same-model subagent panelists are a rigor framing whose critiques record critiquedBy = aiModel - the record claims convergence, never critic independence. An executive brief page built from a facts file computed over the panel reports and the repository (never a typed number) passes python scripts/check_templates.py --brief and is published as an artifact whose URL the review names; the brief carries the verdict first, one tab per ask the human owns, two logic exhibits per tab, a do-nothing course per ask and a falsifier per ask. The knowledge record .tracking/knowledge/runner-direction-panel-2026-09-22.sysml holds the D0196 replication text with per-round results at HEAD; surviving findings that demand work are Issues or tasks; the direction outcome is a proposed Decision the human accepts or declines. VERIFY: grep the review for each panelist heading per round; python scripts/check_templates.py --brief on the page; keel gate validate .; keel gate guard --no-receipt; the brief's numbers reconcile with the panel facts file by a script run."; }
        // RAN: grep -c of '### .* round' headings in docs/reviews/runner-direction-panel-2026-09-22.md -> 27 panelist reports; python scripts/check_templates.py --brief -> clean; keel gate validate . -> 884 clean; keel gate guard --no-receipt -> ALL PASS; brief_facts.py recomputed and the page rebuilt from it so every number reconciles with the panel facts files by construction; the review names the published URL; the knowledge record holds the D0196 text with a result per round; the two recurring findings are Issues with resolvers; the direction outcome is seven held Decisions the human accepts or declines.
        part dcRunnerDirectionPanelIsRecordedDoDR1 : TestResult { :>> id = "64e771bc-56f1-4a86-83bc-dcc75060dcf1"; :>> outcome = VerdictKind::proposed; :>> judgedAgainst = "f365cb7a21cf0147a06d4c3c6b70e94e8007eacb"; :>> judgedAt = "2026-09-22"; :>> judgedBy = "claudeFable5"; }
        action dcPanelistsAreDispatchedIntoAnIsolatedTree;
        verification dcPanelistsAreDispatchedIntoAnIsolatedTreeDoD : Test { :>> id = "91b7c7fd-59d6-419f-8da5-f0a5e5cdbc95"; :>> method = VerificationMethod::inspect; :>> procedureText = "Resolves issue671. The adversarial-panel-review process (D0187) dispatches every panelist into an isolated working copy of the repository at the reviewed commit - the Agent tool's worktree isolation or an equivalent detached clone - never into the real tree, and the dispatch step's actionText says so; a panelist's report that names a write under the real tree is a REFUSED finding in the record. DONE MEANS .engine/processes/adversarial-panel-review.sysml's dispatch step carries the isolation requirement with a co-committed marked Decision (D0209 clause 2), the skill's convene section carries the dispatch shape, and the next panel run's knowledge record names the isolation used per panelist. VERIFY: grep the process file for the isolation clause; keel gate check-engine .; the next panel's knowledge record."; }
        action dcPanelTallyReadsAMachineTrailer;
        verification dcPanelTallyReadsAMachineTrailerDoD : Test { :>> id = "23b85e88-3eb1-4ba1-9f5b-c2651d8d5370"; :>> method = VerificationMethod::test; :>> procedureText = "Resolves issue672. A panel round's verdict and severity counts are computed by a committed script under scripts/ from a machine-readable trailer each panelist report must end with - one line per finding as SEVERITY<TAB>number and one VERDICT line - and the script refuses a report with no trailer or with a trailer that disagrees with the report's own numbered findings; the adversarial-panel-review skill's output contract names the trailer. DONE MEANS the script exists with its D0388 probe pair (a report whose trailer matches, one whose trailer is missing), the skill's output contract carries the trailer, and the next panel's knowledge record cites the script's output for every round. VERIFY: python scripts/<script> --probe; grep the skill for the trailer; the next panel record."; }
        action dcBriefNoteIsPerAsk;
        verification dcBriefNoteIsPerAskDoD : Test { :>> id = "0e0cc7e9-c48a-4f8e-8ce5-46995fa50a8a"; :>> method = VerificationMethod::test; :>> procedureText = "The human's correction of 2026-09-22 (st192): the brief's comment field must be unique per tab so feedback attaches to one ask. DONE MEANS scripts/check_templates.py --brief refuses a page whose note-field count differs from its tab-panel count or whose note sits outside a panel, naming the counts, with two self-test cases (a shared note below two tabs refused; one note inside each of two tabs passes) under --self-test; the asi-templates skill's section table carries the Notes row naming that check, in .engine/skills and its .claude mirror; the runner-direction brief (D0542) is rebuilt with one note per ask keyed to the ask, its digest emits each note beneath its own answer, it passes the checker, and it is republished at its existing URL. VERIFY: python scripts/check_templates.py --self-test; python scripts/check_templates.py --brief on the rebuilt page and on the previous standing page (which must now fail the clause); keel sync-claude --check; keel gate validate .; keel gate guard --no-receipt."; }
        // RAN: python scripts/check_templates.py --self-test -> pass with the two new cases; python scripts/check_templates.py --brief runner_direction_verdict.html -> clean and on brief58.html -> notes and asks disagree; grep -c 'Notes' .engine/skills/asi-templates/SKILL.md and .claude/skills/asi-templates/SKILL.md -> the row present in both; keel sync-claude --check -> clean; the republished page's digest emits Recorded with this answer under each ask.
        part dcBriefNoteIsPerAskDoDR1 : TestResult { :>> id = "c8d3a47d-09bc-42eb-9f77-5da5c742cfef"; :>> outcome = VerdictKind::pass; :>> judgedAgainst = "b65a13e4894742f65340660584e599deb5404a73"; :>> judgedAt = "2026-09-22"; :>> judgedBy = "claudeFable5"; }
        action dcBriefStatesTheDelineatingFacts;
        verification dcBriefStatesTheDelineatingFactsDoD : Test { :>> id = "94c0c550-632b-4310-9814-607d7baade02"; :>> method = VerificationMethod::inspect; :>> procedureText = "The human's correction of 2026-09-22 (st195): the brief narrated the choosing instead of informing it. DONE MEANS the asi-templates skill's executive-brief section carries the human's words and the shape - per ask, three to five verified facts that separate the options, an option table of what each gives and costs, one line on what would change it, no scaffolding prose, no placeholders or asides, answered asks removed, recommendation optional - in .engine/skills and its .claude mirror with keel sync-claude --check clean; the runner-direction brief is rebuilt to that shape with the three open asks and the four answered listed once, passes python scripts/check_templates.py --brief, and is republished at its URL. VERIFY: grep the skill for the 2026-09-22 paragraph; keel sync-claude --check; python scripts/check_templates.py --brief on the page; keel gate validate .; keel gate guard --no-receipt."; }
        // RAN: grep of the skill paragraph in source and mirror -> present; keel sync-claude --check -> clean; python scripts/check_templates.py --brief runner_direction_verdict.html -> clean; keel gate validate . -> clean; keel gate guard --no-receipt -> ALL PASS; the page republished at its URL with three tabs of facts and the four answered listed once.
        part dcBriefStatesTheDelineatingFactsDoDR1 : TestResult { :>> id = "1230ab52-0049-446f-a41f-9e76caf51738"; :>> outcome = VerdictKind::proposed; :>> judgedAgainst = "9675a3a56e5142598d7736f75725f318033e340d"; :>> judgedAt = "2026-09-22"; :>> judgedBy = "claudeFable5"; }
        action dcKeelNextHandoffIsRecorded;
        verification dcKeelNextHandoffIsRecordedDoD : Test { :>> id = "35f7b388-12b8-4242-944e-3eec03c8e5a6"; :>> method = VerificationMethod::analyze; :>> procedureText = "The human's ask of 2026-09-22 (st196): a hard split into a separate project for the next keel, a panel to harvest the critical knowledge, the harvest and probably keel itself as the seed, decouplable, and a clean need, use case, requirement and code-architecture scaffold. DONE MEANS docs/reviews/keel-next-handoff-2026-09-22.md exists carrying the human's words verbatim, a synthesis in their order (directions worth carrying, processes worth carrying, lessons from mistakes as day-one rules, research and insights as design inputs, the next-build feature candidates, the scaffold tree, the decoupling plan), every item self-contained with its substance and its source, and the six lens reports appended verbatim; the new repository exists as a sibling directory seeded with the engine by its adoption path, carrying the scaffold as SysML text under its own .tracking (Needs derived from quoted Statements, UseCases, SystemRequirements with satisfy and verify, an architecture allocation) and a HANDOFF.md that names what came from keel and how to remove it; the knowledge record .tracking/knowledge/keel-next-handoff-2026-09-22.sysml holds the D0196 replication text with a passing result at HEAD; the charter Decision saves the harvest and names the split as the human's accepted choice (D0549). VERIFY: grep the review for the section headings; count its appended lens headings (six); the new repository's keel gate validate . is clean; keel gate validate . and keel gate guard --no-receipt here."; }
        // RAN: Task DoD (method analyze, lands proposed per D0312). // RAN: grep -n of the nine '### N.' synthesis headings in docs/reviews/keel-next-handoff-2026-09-22.md -> nine sections in the human's order; grep -c '^## Appendix [A-F] ' -> 6 appended lens headings // RAN: keel-serve.exe gate validate . in keel-next -> 6 tracking file(s) validated clean // RAN: keel-serve.exe gate validate . and gate guard --no-receipt . here -> recorded in the sprint's implement gate and the commit's pre-commit hook // RAN: .tracking/knowledge/keel-next-handoff-2026-09-22.sysml holds the replication text with kKeelNextHandoffR1 pass at bfc654d5; D0553 accepted and names D0549 option B as the human's choice
        part dcKeelNextHandoffIsRecordedDoDR1 : TestResult { :>> id = "88deaebc-4401-4d67-83bb-036ba6c3a5d2"; :>> outcome = VerdictKind::proposed; :>> judgedAgainst = "bfc654d5ed2e0e6fcd132db1b90adb43aa741c27"; :>> judgedAt = "2026-09-22"; :>> judgedBy = "claudeFable5"; }
        action dcIdGuardChargesOnlyAuthoredSurfaces;
        verification dcIdGuardChargesOnlyAuthoredSurfacesDoD : Test { :>> id = "71015c65-5349-4da8-9d8b-61a9c3e2c416"; :>> method = VerificationMethod::test; :>> procedureText = "Resolves issue673. The id-is-a-uuid guard charges a non-v4 id only to a surface the project authors - .tracking and .engine/decisions - and never to a file byte-identical to the engine tree the binary embeds, so a fresh adoption's first commit is not refused for the engine's own ids. DONE MEANS the guard passes on a scaffold produced by keel init in a repository with no HEAD, the init smoke test runs the guard in exactly that state and fails without the fix, the D0388 probe pair is a fresh scaffold with no HEAD (negative before the fix, positive after) and a project-authored non-v4 id under .tracking (still refused), and the guard catalogue row says which surfaces it reads. VERIFY: cargo nextest run -p keel-cli init_smoke; keel gate guard --no-receipt in a fresh keel init tree before any commit."; }
        action dcRetroGuardReadsTheTreesItemNames;
        verification dcRetroGuardReadsTheTreesItemNamesDoD : Test { :>> id = "02ac8e7b-7b22-4e5d-99eb-ea667320c187"; :>> method = VerificationMethod::test; :>> procedureText = "Resolves issue674. The retro-backlog guard recognises a named item by matching the retro text against the item names the tree declares - every `action` inside a project action def, every `part issueNNN`, every Decision part - rather than against the dc, issue and d0 prefixes, so a downstream project's own task names satisfy it. DONE MEANS the guard passes a retro that names a task declared as an action under .tracking with a non-dc name added in the same commit, still refuses a retro naming a token no declaration carries, the D0388 probe pair is those two fixtures, and the keel-next sprint 1 retro would have passed as first written. VERIFY: cargo nextest run -p keel-guards retro_backlog; a fixture tree with an action named nxSomething in its backlog."; }
        action dcMigrateScannerSkipsLineComments;
        verification dcMigrateScannerSkipsLineCommentsDoD : Test { :>> id = "ca406773-788b-410f-a82d-90942c3b693d"; :>> method = VerificationMethod::test; :>> procedureText = "Resolves issue675. The removed-types step of keel migrate scans each authored line with its string literals blanked AND its trailing // line comment dropped, so a removed type named in a comment, such as the '// RAN: Task DoD' evidence line the write API emits, is not a blocker, while a real ': Agent' annotation before a trailing comment still is. Done when the unit test a_removed_type_named_inside_a_line_comment_is_prose_not_schema in members/keel-process/src/migrate.rs passes beside its string-literal sibling, and keel migrate . --dry-run over keel-next at 692c62c plans the 0.5.x resync with 0 blockers where the 0.5.2 binary reported 4."; }
        // RAN: cargo test -p keel-process --lib migrate -> 15 passed, 0 failed, including a_removed_type_named_inside_a_line_comment_is_prose_not_schema beside a_removed_type_named_inside_a_string_literal_is_prose_not_schema; the new test failed before the fix at migrate.rs:1779 (the comment arm blocked). keel migrate . --dry-run over keel-next at 692c62c: the published 0.5.2 binary (build bb1882d) reported 4 blockers, .tracking/backlog.sysml:11, 15, 19, 23; the binary built at this tree reports totals 21 file(s), 21 edit(s), 0 blocker(s). cargo clippy --workspace --all-targets -D warnings clean. keel land at 36057f44: touched tests 767 passed.
        part dcMigrateScannerSkipsLineCommentsDoDR1 : TestResult { :>> id = "2065c400-b317-4d7f-831b-2abb2d10938c"; :>> outcome = VerdictKind::pass; :>> judgedAgainst = "36057f44"; :>> judgedAt = "2026-09-23"; :>> judgedBy = "claudeFable5"; }
        action dcHooksResolveThePinnedBinaryVerified;
        verification dcHooksResolveThePinnedBinaryVerifiedDoD : Test { :>> id = "9e1e3cc7-f6b6-4ddd-866c-d0c0e84a4394"; :>> method = VerificationMethod::test; :>> procedureText = "Resolves issue676. Outside keel's own self-build tree, the generated hooks and the rendered pre-commit resolve the binary pinned-first: KEEL_BIN when set, else .keel/bin/<pin>/ verified against keel-wrapper.toml exactly as keelw verifies a cache hit, and a loose .keel/bin/keel(.exe) is used only in the self-build tree (D0391). Known-positive: an adopter tree with a mismatched binary at the loose slot and the verified release in .keel/bin/<pin>/ runs the release. Known-negative: a cached binary whose SHA-256 differs from the wrapper entry is refused loudly, never run."; }
        action dcRetroNamesAnyDeclaredItem;
        verification dcRetroNamesAnyDeclaredItemDoD : Test { :>> id = "0b9b7124-8d8d-4384-b5c1-d86b5e730a40"; :>> method = VerificationMethod::test; :>> procedureText = "Resolves issue677. The retro-backlog guard reads a retro's named items with named_items (members/keel-guards/src/sprints.rs), which recognizes issueNNN, d0NNN and a task only when its name begins with dc; added_items reads `action dcX;` the same way. A downstream project names its tasks by its own prefix (keel-next: nxSchemaMeasurementsRunOnADag), so a retro that names the item this commit adds is reported as naming no item at all, and passes only when it also names a Decision. Done when named_items and added_items recognize any declared action name in the tree's backlog action defs, not a prefix: a retro naming a task the commit adds passes on its own; a retro naming a task that does not exist is still a violation; the existing tests hold and two new ones cover an nx-prefixed task, positive and negative. VERIFY: cargo test -p keel-guards retro; keel gate guard retro-backlog on keel-next at 1538a4c with the d0004 mention removed from the sprint 8 retro passes."; }
        action dcDecisionIsOneProposalInParagraphs;
        verification dcDecisionIsOneProposalInParagraphsDoD : Test { :>> id = "ab31fd03-bc07-464e-af34-9a39ddcea99e"; :>> method = VerificationMethod::test; :>> procedureText = "Resolves issue678. A Decision presented to the human is one proposal the human can accept or reject, and its text reads as paragraphs. Done when (1) keel record decision refuses a decision field that lays out more than one option as the thing to accept (OPTION A ... OPTION B ..., or an 'or' chain of proposals) and says to write one proposal with the alternatives in context or rationale, with a probe pair; (2) the review pane renders a field's paragraph breaks and the decision-authoring skill says to write them, one idea per paragraph; (3) serve shows, beside accept and reject, the words box first, so a human who wants to answer in their own words sees how. VERIFY: cargo test on the record verb's probe pair; keel-next D0002 in its rewritten shape is accepted by the verb and its old shape refused; a decision drafted with blank lines reads as paragraphs in the pane."; }
        action dcOverrideConsumedOnAnyToolsWrite;
        verification dcOverrideConsumedOnAnyToolsWriteDoD : Test { :>> id = "6e398a6e-ee0a-43d3-ada9-6b288d56e3b4"; :>> method = VerificationMethod::test; :>> procedureText = "Resolves issue679. An armed override is consumed by the first allowed write to its path by any tool, and a Python or shell write to a locked fact surface is refused as sed is. Done when (1) the pre-write hook, on allowing a write to the armed path, records override-consumed in the ledger, removes the arming and writes the obligation, whatever tool made the write (the Edit tool and a Write tool among them); (2) the pre-bash hook refuses a shell command that writes a locked fact surface through python, perl, awk, tee or a redirection as it refuses sed, naming the path; (3) a test under remaining_controls_actually_fire.rs proves both: an armed path written by a non-sed tool leaves a consumption and an obligation, and a python write to a locked path is refused; (4) keel-next re-reads its issue009 against the fixed engine."; }
    }

    // issue106 established that `ref createdBy : Actor` cannot be built without inverting the D0093
    // engine/instance boundary, and sprint 278 recorded that dcProvenanceAsRefs "must not be executed
    // as written". That was recorded in PROSE inside a procedureText and nowhere else, so the item
    // stayed on the ready frontier — third-ranked, auto-followed (D0052), and pointing a successor at
    // work already found to be structurally impossible. The retirement is a typed edge or it is not
    // state (D0018 / issue100).
    #Supersede dependency from dcActorTraceView to dcProvenanceAsRefs;

    #Resolves dependency from dcSchemaSweepResidue to issue108;

    // dcWorkClaim cannot start until D0147 signs a `Claim` type into frozen core, and the frontier is
    // AUTO-FOLLOWED (D0052) — so without this edge the next contributor is pointed straight at work
    // that provably cannot be done. The edge is the authored fact; `ready` computes the rest, and the
    // item returns by itself when the Decision is accepted or rejected (issue112).
    #DependsOn dependency from dcWorkClaim to d0147;

    // keelArchViews cannot start until D0148 ships a `CodeElement` type for `keel arch` to read.
    // The frontier is AUTO-FOLLOWED (D0052), so without this edge the next contributor is pointed at
    // work whose own DoD opens with an unmeetable prerequisite (issue112's machinery, issue114).
    #DependsOn dependency from keelArchViews to d0148;

    // dcCorrectExclusionText changes PROCESS DEFINITION text (§3a), so it cannot start until D0149 is
    // signed off. The frontier is AUTO-FOLLOWED (D0052) — without this edge the next contributor is
    // pointed at a correction they are not authorised to apply (issue112's machinery).
    #DependsOn dependency from dcCorrectExclusionText to d0149;

    // dcVerifyBeforeAsserting changes the RESPONSE CONTRACT (§3a), which lives in the output style
    // per D0130, so it cannot start until D0151 is signed off. Without this edge the auto-followed
    // frontier would point a successor at a contract edit nobody authorised (issue112's machinery).
    #DependsOn dependency from dcVerifyBeforeAsserting to d0151;
        action dcGateEvidenceControl;
        verification dcGateEvidenceControlDoD : Test { :>> id = "bcb6f165-a75b-4377-a8e1-632838c05dbd"; :>> method = VerificationMethod::test; :>> procedureText = "Resolves issue116. A commit made with hooks bypassed is INDISTINGUISHABLE from a gated one afterwards, which I proved by making one: to build a two-clone fixture I committed with core.hooksPath set to the null device, and the only reason it was recovered is that I disclosed it in the same session. Disclosure is not a control (D0047). DO: a check that computes, over a commit range, which commits carry no evidence of having passed the gate, and reports them - so a bypass is VISIBLE in a computed view rather than depending on the bypasser to mention it. DESIGN CONSTRAINT, and the hard part: the evidence must be something a bypasser cannot trivially forge while still being derivable from the repo alone, so a self-asserted 'I ran the gate' marker in the commit message is NOT sufficient. Consider instead re-running the gate at each commit in the range and reporting which commits FAIL it - honest, forgery-proof, and expensive, so it belongs in CI or an on-demand audit rather than in the per-edit tier. VERIFY: the known-bypassed commit in this repo's history is detected by whatever rule is chosen, or the rule is documented as unable to detect it and says why; a clean range reports nothing; the check never blocks a commit (it is an audit, not a gate, per D0098 - completeness is a burndown, not a commit gate); clippy + cargo test + validate + guard green."; }
        part dcGateEvidenceControlDoDR1 : TestResult { :>> id = "68399d59-3a31-4c27-a741-adfea016481b"; :>> outcome = VerdictKind::pass; :>> judgedAgainst = "9bcab3b"; :>> judgedAt = "2026-08-15"; :>> judgedBy = "claudeOpus5"; }
        action dcCorrectExclusionText;
        verification dcCorrectExclusionTextDoD : Test { :>> id = "e3cb927f-e5ce-4822-9b6f-384d013fa8a4"; :>> method = VerificationMethod::inspect; :>> procedureText = "Resolves issue115. D0129 and the dcWorkClaim DoD both state that two contributors claiming one item are excluded because the remote accepts exactly one push (a ref update being a compare-and-swap). A two-clone race test DISPROVED this: claims are written to per-actor files under srDcPerActorWriteTargets, which deliberately removes the write contention, so the loser merges and retries and BOTH claims land. claim.rs now states the true mechanism and computes the holder, but the PROCESS TEXT still teaches the false one - dual truth in exactly the document a downstream project would build on. DO: correct D0129's exclusion clause and the dcWorkClaim DoD text, and check the distributed-collaboration skill and any doc making the same claim. The correction is not a footnote: it changes exclusion from a property of git to a property of a computed rule, and the two facts that fell out of it belong in the corrected text - that whoever-landed-first is NOT recoverable from merged history (parallel claims are siblings of equal ancestry depth and their commit timestamps tie within a second), and that expiry must remove a claim from contention rather than only from the top of the ranking. VERIFY: no surviving doc asserts the push provides exclusion; grep the doc surface for the compare-and-swap claim; validate + guard green; the correction rides one commit with its doc-sync."; }
        part dcCorrectExclusionTextDoDR1 : TestResult { :>> id = "93023c80-3565-4a4e-941e-eab56825d727"; :>> outcome = VerdictKind::pass; :>> judgedAgainst = "01fce65"; :>> judgedAt = "2026-08-15"; :>> judgedBy = "claudeOpus5"; }
        // Ranked ABOVE dcArchRegistryPortability deliberately (D0052: declaration order IS
        // priority, and reordering is how you reprioritize). The priority-inversion guard flagged
        // the original placement: this item resolves two HIGH findings, while
        // dcArchRegistryPortability is blocked on data no one in this repo can supply.
        action dcServeRequirementRework;
        verification dcServeRequirementReworkDoD : Test { :>> id = "4b413c5c-e8df-4585-bc1f-4bcf11ae11fc"; :>> method = VerificationMethod::inspect; :>> procedureText = "Resolves issue121-issue125, the five findings from the independent Core-3 critique of the serve-discipline SystemRequirement cluster (critic claudeOpus5, independent of author wweatherholtz). BLOCKED ON HUMAN DISPOSITION: every finding is >= Medium, so each needs a typed act/accept-risk/dismiss verdict (D0092) before any rework is authorised - and ACT on some findings may be declined in favour of accepting the risk, which would close them without a text change. DO, for whichever findings are dispositioned ACT: (C1, High) srServeModelDrivenRegistry requires computing each process's expected output schema from the declared model, and no schema type can hold one - producedArtifact is free-text prose, so this Tier-1 contract is half unbuildable and two Tier-2 requirements #DependsOn it; either add the schema representation (a frozen-core change needing its own Decision) or re-scope the requirement to the launchable set alone. (C3, High) srServeApproveGate never constrains the approving operator to a HUMAN, so an AI could approve its own routing and defeat the parent Need; bind it to the attestation-policy kinds=human machinery that D0146 and the attestation-authority guard now provide. (C2, Medium) srServeLauncherDefinedOnly states a universal negative no test can demonstrate; restate as a structural property a guard can enforce. (C4, Medium) srServeOutputSchemaValidate governs the result but not side effects already taken by a failed attempt; say what happens to work already performed. (C5, Medium) srServeScopedContext bounds only passed-in context while a launched agent reconstitutes context by READING, so the anti-drift property it claims is not delivered by input scoping alone. VERIFY: each dispositioned-ACT finding has a corrected requirement text; each accept-risk/dismiss finding is closed by its typed disposition rather than by an edit; re-critique at HEAD after any text change, since the existing critique goes suspect the moment its target moves; validate + guard green."; }
        part dcServeRequirementReworkDoDR1 : TestResult { :>> id = "49cbbf65-3cba-4664-b37d-504ac1e23516"; :>> outcome = VerdictKind::pass; :>> judgedAgainst = "b05548a"; :>> judgedAt = "2026-08-15"; :>> judgedBy = "claudeOpus5"; }
        action dcArchRegistryPortability;
        verification dcArchRegistryPortabilityDoD : Test { :>> id = "932a0ef5-409b-4487-8ab8-483708b360be"; :>> method = VerificationMethod::demo; :>> procedureText = "Resolves issue117. keelArchViewsDoD required verifying the six arch views on SelfSync's authored registry; this repo does not hold that data, so sprint 301 verified against a registry authored for keel's OWN source instead. That registry was authored by the same author as the views, so it cannot detect an assumption shared between them - which is precisely the portability claim keelArchViews was about. BLOCKED ON EXTERNAL DATA and recorded as such rather than quietly counted as done. DO: run the six views against a registry authored by a DIFFERENT project (SelfSync's, or a second project's), reached either by that project running keel arch itself or by importing its registry here for the test. VERIFY: each of the six views computes a defensible result on that project's data without a change to keel; any change keel DOES need is the finding, and is recorded as such; the schema module reaches the project through keel init rather than by hand-copying, since shipping it was D0148's entire point."; }
        part dcArchRegistryPortabilityDoDR1 : TestResult { :>> id = "57b67241-ab65-496a-9108-373a0fa77558"; :>> outcome = VerdictKind::pass; :>> judgedAgainst = "0deee4e"; :>> judgedAt = "2026-08-15"; :>> judgedBy = "claudeOpus5"; }
        action dcSchemaReconciliation;
        verification dcSchemaReconciliationDoD : Test { :>> id = "634748e9-04d7-401e-81e5-ccd5980d9a4d"; :>> method = VerificationMethod::test; :>> procedureText = "Resolves issue118, issue119, issue120. A holistic pass over every hook against the schema found that the engine checks MARKERS (D0133) and ENUM VALUES but not ATTRIBUTE NAMES, and that three hardcoded lists in the binary mirror schema vocabulary with nothing reconciling them. DO: (1) an attribute-vocabulary guard - every :>> name = on a typed element must be an attribute declared by that type or an ancestor - hard-blocking and FORWARD-ONLY grandfathered per issue068, since a new control must never retro-fail work that was correct when written; (2) a schema-reconciliation guard that fails when a hardcoded list in the binary disagrees with the schema it mirrors, covering at minimum KNOWN_EDGES vs the EdgeKind enum, ENGINE_MARKERS vs the declared metadata defs, and RISK_ORDER vs the RiskClass enum; (3) reconcile the KNOWN_EDGES drift itself so derivedFrom, covers, dispositions and specialize become traversable in declared views. VERIFY: a misspelled attribute is REJECTED with the type it was authored on and the nearest declared name; a correctly spelled one passes; every pre-existing file still validates green so the control is forward-only; a deliberately drifted hardcoded list FAILS the reconciliation guard; a view over derivedFrom resolves and returns the 97 edges that exist; clippy + cargo test + validate + guard green."; }
        part dcSchemaReconciliationDoDR1 : TestResult { :>> id = "b931f5e1-bd2e-4609-82dd-30ba6cde6c65"; :>> outcome = VerdictKind::pass; :>> judgedAgainst = "0f964ae"; :>> judgedAt = "2026-08-15"; :>> judgedBy = "claudeOpus5"; }
        action dcScratchPathControl;
        verification dcScratchPathControlDoD : Test { :>> id = "3829266e-b045-4746-a292-0c2621d34603"; :>> method = VerificationMethod::test; :>> procedureText = "Resolves issue126. The pre-bash hook (shellcheck.rs, issue094) advises on host/shell adaptation and is the natural home for a defect that has now recurred three times in one session: writing a heredoc to git-bash /tmp and then reading that path from Windows python, which cannot see it. Each occurrence cost a failed step and a retry, and the remedy was already recorded in a sprint 301 retro before recurring in sprint 305 - which is exactly the D0047 case where a reminder is not a control. DO: extend keel hook pre-bash to detect a command that writes to a /tmp path AND a later step in the same command reading it with a Windows interpreter, or more simply any /tmp path used in a command that also invokes python/conda on this platform, and emit the advisory naming the scratchpad alternative. ADVISORY ONLY, never blocking (issue094 established that this hook must not block, and a false positive that stops work would be worse than the defect). VERIFY: a command mixing a /tmp heredoc with a python read triggers the advisory; a pure-bash /tmp use does not; the hook stays silent when it has nothing to say; on a POSIX host the check does not fire at all since the defect is Windows-specific; clippy + cargo test + validate + guard green."; }
        part dcScratchPathControlDoDR1 : TestResult { :>> id = "2f367261-8b8b-4758-bb65-89c0576ffa46"; :>> outcome = VerdictKind::pass; :>> judgedAgainst = "c918626"; :>> judgedAt = "2026-08-15"; :>> judgedBy = "claudeOpus5"; }
        action dcCritiqueCoverageSupersede;
        verification dcCritiqueCoverageSupersedeDoD : Test { :>> id = "e47a4268-c5bc-4dbe-bb10-9d4aa53cf3af"; :>> method = VerificationMethod::test; :>> procedureText = "Resolves issue127. critique-coverage counts SUPERSEDED elements as governed, while compute_coverage and compute_tier_satisfaction both exclude them (view.rs builds a descoped set from supersede edges and filters targets by it). Proven by acting on the sprint 305 findings: srServeApproveGate and srServeModelDrivenRegistry are now superseded by corrected requirements and still report governed=true, so a retired requirement occupies a slot in the critique-coverage denominator permanently and its critique must be maintained forever. DO: exclude #Supersede-targeted elements from the critique-coverage governed set, matching the two sibling views and the engine's own doctrine that superseded means RETIRED. NOTE THIS CHANGES A COMPUTED VIEW'S NUMBERS and is therefore section 3a: it needs sign-off before it lands, and the pre-change and post-change counts must both be reported so the human sees exactly what moved. VERIFY: a superseded element drops out of governed; its critiques remain readable and #Verify-linked, since retiring an element must never delete the evidence about it; the three views agree on which elements are in scope; a non-superseded element is unaffected; clippy + cargo test + validate + guard green."; }
        part dcCritiqueCoverageSupersedeDoDR1 : TestResult { :>> id = "5836fa6a-94f1-476e-a51e-87b4685386e2"; :>> outcome = VerdictKind::pass; :>> judgedAgainst = "bc8097f"; :>> judgedAt = "2026-08-15"; :>> judgedBy = "claudeOpus5"; }
        action dcVerifyBeforeAsserting;
        verification dcVerifyBeforeAssertingDoD : Test { :>> id = "27c91919-3740-4491-b3b9-14976e6be343"; :>> method = VerificationMethod::inspect; :>> procedureText = "Resolves issue134. Applies D0151 once accepted: add the verify-before-asserting clause to the response contract in .claude/output-styles/keel.md, which is where the contract lives (D0130 — CLAUDE.md was demonstrably ignored, issue084/085). DO: state that an unverified suspicion is either silent or explicitly labelled as unverified, never asserted as a defect; and that a defect claim made to the human NAMES THE CHECK that established it, the same way a claim about code cites file:line. VERIFY: the clause is present in the output style; the existing contract sections are unchanged; a Decision records the acceptance; validate + guard green. HONEST LIMIT, to be stated in the clause itself rather than discovered later: no gate can read conversational output, so unlike every other item in the contract this one is unenforceable by the engine. It is a stated rule plus the human noticing, and the naming-the-check requirement exists precisely so the reader can audit a claim they cannot have machine-checked."; }
        part dcVerifyBeforeAssertingDoDR1 : TestResult { :>> id = "b7caf928-b6b8-46c6-ac75-1af9c93c8ac3"; :>> outcome = VerdictKind::pass; :>> judgedAgainst = "b82e777"; :>> judgedAt = "2026-08-15"; :>> judgedBy = "claudeOpus5"; }
        action dcSittingObligationScope;
        // Result recorded below the DoD it judges; the DoD's own text is unchanged (D0108: add, never overwrite).
        verification dcSittingObligationScopeDoD : Test { :>> id = "2a2e018e-6a62-4369-b1f3-0f359ee7ab05"; :>> method = VerificationMethod::inspect; :>> procedureText = "Resolves issue135. The obligation surface reports sitting-review-due as 311 of 315 sprints, because per-sitting review (D0049) post-dates almost all of this repo's history and nothing distinguishes a sitting that is actually AWAITING review from one that predates the convention. The number is true and useless as a queue: N-C1 says the surface shows every obligation requiring the human's judgment AND NOTHING ELSE, and 311 historical sittings do not require judgment now. It is currently reported WITH a caveat rather than filtered, because silently scoping it to 'recent' would invent an actionable definition nobody has agreed. DO: decide what makes a sitting review ACTIONABLE - candidates are sittings after the D0049 convention took effect, sittings within a bounded recency window, or sittings whose work is not yet superseded - and either scope the computed class accordingly or grandfather the pre-convention set explicitly the way issue068 grandfathers other forward-only controls. VERIFY: the obligation total reflects only actionable items; the grandfathered set is still visible somewhere rather than deleted; the caveat is removed once the definition is defensible; a sitting that genuinely awaits review still appears."; }
        part dcSittingObligationScopeDoDR1 : TestResult { :>> id = "6b1d84f0-2c73-4a95-8e61-df02a7c5b913"; :>> outcome = VerdictKind::pass; :>> judgedAgainst = "9d10ee1"; :>> judgedAt = "2026-08-17"; :>> judgedBy = "claudeOpus5"; }
        action dcResolverKindGuard;
        verification dcResolverKindGuardDoD : Test { :>> id = "9f2c0a71-4d85-4b16-9e03-7ca518d6b204"; :>> method = VerificationMethod::test; :>> procedureText = "Resolves issue136. DO: add a hard guard so a #Resolves edge whose resolver could not possibly resolve anything is a violation rather than a pass. A resolver must be a declared `action` (work that closes the Issue) or a `Decision` (which moots it, §1.4); a requirement, Need, Test or Story is not an act and can never compute as complete against the Issue. Repoint the two pasted edges onto real resolvers in the same change so the guard starts at zero. VERIFY: the guard is in the enforced set and reports 134 edges scanned with no violation; reintroducing a requirement-as-resolver fails it; `keel open-issues` no longer reports untriaged=false for an Issue nothing is on the hook for."; }
        part dcResolverKindGuardDoDR1 : TestResult { :>> id = "7d4b2e19-8c60-4a37-95f1-0eb3c85479da"; :>> outcome = VerdictKind::pass; :>> judgedAgainst = "5547107"; :>> judgedAt = "2026-08-17"; :>> judgedBy = "claudeOpus5"; }
        action dcRootArmSweep;
        verification dcRootArmSweepDoD : Test { :>> id = "3a6e91b8-72f4-4c0d-b5a9-1e8d04c37f65"; :>> method = VerificationMethod::test; :>> procedureText = "Resolves issue133's remaining half. The reverify parser was fixed when the issue was recorded; the issue also says the same catch-all-as-root arm exists in OTHER subcommand parsers, and that sweep was never done. DO: find every subcommand argument parser whose final arm treats an unrecognised token as ROOT, and make an unrecognised `--flag` an error naming the usage line instead of a path. This is the session's dominant defect shape — a wrong input producing a confident wrong answer downstream instead of an error at the point of the mistake. VERIFY: each fixed subcommand rejects an unknown flag with its usage line; a legitimate positional ROOT still works; the count of remaining catch-all arms is reported rather than claimed to be zero."; }
        part dcRootArmSweepDoDR1 : TestResult { :>> id = "b8e0f36c-51a2-4d78-8b04-2c9741ed6a5f"; :>> outcome = VerdictKind::pass; :>> judgedAgainst = "5547107"; :>> judgedAt = "2026-08-17"; :>> judgedBy = "claudeOpus5"; }
        action dcNeed8ScopeNarrowing;
        verification dcNeed8ScopeNarrowingDoD : Test { :>> id = "c1b70de4-5a29-4f83-8d61-2b940ae7c518"; :>> method = VerificationMethod::confirmation; :>> procedureText = "Resolves issue132, and BLOCKED BY DESIGN on d0156 (proposed) — nViewerPersistedViewpoints is owned by wweatherholtz and D0108 forbids a non-owner editing its fields, so this cannot be worked until its owner decides. The #DependsOn edge to a proposed Decision keeps it off the ready frontier (blocked-on-acceptance) rather than ranking work an AI is not permitted to do. DO, once d0156 is accepted: narrow N-8's statement to the surviving single-user half, or supersede N-8 with a Need that states it. VERIFY: N-8 no longer states scope D0115 removed; srViewerPersistedViewState still satisfies it; the human authored or explicitly authorized the edit."; }
        part dcNeed8ScopeNarrowingDoDR1 : TestResult { :>> id = "2c74e0b8-9f36-4a51-8d27-b60e3f1c9a84"; :>> outcome = VerdictKind::pass; :>> judgedAgainst = "7493b12"; :>> judgedAt = "2026-08-17"; :>> judgedBy = "claudeOpus5"; }
        action dcMachineScopeRestatement;
        verification dcMachineScopeRestatementDoD : Test { :>> id = "e93b1d57-4c82-40a6-b715-8f2e06da3947"; :>> method = VerificationMethod::inspect; :>> procedureText = "Resolves issue137. D0115 clause 1 says 'the viewer is single-user + unauthenticated', which is inconsistent with shipped behaviour: D0108/D0129 already give one BOUND ACTOR PER MACHINE with several machines collaborating through git. DO: author a Decision superseding that clause, restating the boundary as 'one bound actor per machine; collaboration by git; the console is local-only and unauthenticated', and sweep every claim derived from the old phrase - requirements, viewpoint concerns, docs - fixing each in the same commit. Human acceptance required: this is a scope statement in an accepted Decision, not a wording nit. VERIFY: no live artifact asserts single-user of the ENGINE; the console's local-only scope is stated where a reader meets it; the superseding Decision carries its acceptance."; }
        part dcMachineScopeRestatementDoDR1 : TestResult { :>> id = "c8f31a07-2b64-4d59-8e17-905ab2c73f48"; :>> outcome = VerdictKind::pass; :>> judgedAgainst = "32a0a31"; :>> judgedAt = "2026-08-17"; :>> judgedBy = "claudeOpus5"; }
        action dcSharedParsedModel;
        verification dcSharedParsedModelDoD : Test { :>> id = "c50fa127-9b46-4e83-8d71-63ae02b48f95"; :>> method = VerificationMethod::test; :>> procedureText = "Resolves issue142. A cold burst of the eight endpoints the console requests takes 5.2s and the same burst warm takes 0.5s, so roughly nine tenths of a cold load is recomputation over an already-parsed corpus. DO: instrument FIRST - per-phase timing inside Model::build and a per-view parse counter, because three separate wall-clock inferences were wrong before instrumentation was tried - then share one parsed model per content fingerprint across the 74 Model::build call sites, and consider whether composite views (assured, coverage) should reuse their component views results rather than recomputing them. VERIFY with repeated samples on a WARMED binary, never a single post-build run: the cold burst should approach the warm burst, and every view must return byte-identical JSON before and after."; }
        part dcSharedParsedModelDoDR1 : TestResult { :>> id = "cd35a587-9a63-4c72-ba5c-5a642d79f751"; :>> outcome = VerdictKind::pass; :>> judgedAgainst = "edd129a"; :>> judgedAt = "2026-08-20"; :>> judgedBy = "claudeOpus5"; }
        action dcObligationActionable;
        verification dcObligationActionableDoD : Test { :>> id = "8f36b0d4-71ca-4e29-95b8-04e7c218a6f3"; :>> method = VerificationMethod::demo; :>> procedureText = "Resolves issue141 and delivers srConsoleObligationActionable / UC-C7. DO: carry the viewpoint IDENTITY on every obligation class the surface reports; bind card clicks by that identity via one delegated handler rather than by DOM position; select the destination's SURFACE as well so the nav agrees with what is rendered; give only cards with a resolvable target the affordance; and serve any declared viewpoint's computed view generically so a card always lands on something real. VERIFY: the two act destinations that had no endpoint (authority-queue, sitting-coverage) return their computed views; an unbound command FAILS LOUD naming the CLI command rather than rendering blank; the positional binding is gone from the served console; the obligation counts are unchanged through the unified dispatch; and the human confirms a click lands where the work is."; }
        part dcObligationActionableDoDR1 : TestResult { :>> id = "2b7e4c90-6a31-4f85-9d02-c73e158ab604"; :>> outcome = VerdictKind::pass; :>> judgedAgainst = "844b4ca"; :>> judgedAt = "2026-08-17"; :>> judgedBy = "claudeOpus5"; }
        action dcConsoleBuildStamp;
        verification dcConsoleBuildStampDoD : Test { :>> id = "2f60d84b-9c17-4e53-8a26-71be05fc3d92"; :>> method = VerificationMethod::test; :>> procedureText = "Resolves issue153. The console build id is a hash of the page's own bytes, substituted into the HTML BY THE SERVER so `build <id>` renders with no JavaScript - verified live: `Technical smooth sailing - build 87f94652` is present in the raw response and the __KEEL_BUILD__ placeholder count is zero. Exposed as `consoleBuild` on /api/version, distinct from apiVersion because the API contract holds steady across page changes. The page compares its embedded id with the server's on every SSE hello and every 30s and reloads when they differ, so a tab open across a restart removes itself instead of running dead logic. STATED LIMIT: a page already stale when this shipped has no such check and needs one manual reload."; }
        part dcConsoleBuildStampDoDR1 : TestResult { :>> id = "8b41c9e0-5d72-4a38-b165-0e73fa2c6549"; :>> outcome = VerdictKind::pass; :>> judgedAgainst = "8ba97f9"; :>> judgedAt = "2026-08-19"; :>> judgedBy = "claudeOpus5"; }
        action dcDeckReviewIntake;
        verification dcDeckReviewIntakeDoD : Test { :>> id = "4a7e60c9-3b12-4d85-9f01-e6b25a7c3f14"; :>> method = VerificationMethod::test; :>> procedureText = "Intake of the human's first obligations-deck review, step 4 of the obligation-review skill. RECORDED AS THEIRS: 4 Decision acceptances via `keel accept` with their submission quoted; 19 finding dispositions with each per-item note VERBATIM and the deck-verdict-to-DispositionKind mapping STATED rather than assumed (Accept -> act, Needs work -> act because their note says the answer is insufficient, Reject -> dismiss); sitting05Review covering the 34 due sprints on their instruction `accept all sprints`, scoped to the live queue and NOT re-attesting what D0155 grandfathered. RECORDED AS MINE, under the delegation their third clause granted (D0165): dispositions for issue154-157, which accrued after the deck was generated and were never in front of them - judgedBy claudeOpus5, each citing D0165, so nothing claims a human judged them. Read back: pendingAcceptances 0, undispositioned 0 of 116, sittings due 0. ALSO FIXED, answering their issue150 note (`Root cause? How did the model miss? Be specific`): the oversight advisory I shipped in sprint 349 sat INSIDE the green branch of `hook stop`, so a red model MASKED it - the same single-channel blindness as the original defect. It now computes in both branches and appends to the blocking reason. Its test was rewritten to assert the PROPERTY (the advisory alone resolves to a systemMessage; a block stays gated on `problems`) rather than the layout it had been asserting. 191 tests, clippy clean, 36 guards ALL PASS."; }
        part dcDeckReviewIntakeDoDR1 : TestResult { :>> id = "d05f3e81-7a46-4b29-8c73-15be0f2a9c46"; :>> outcome = VerdictKind::pass; :>> judgedAgainst = "513a1a4"; :>> judgedAt = "2026-08-20"; :>> judgedBy = "claudeOpus5"; }
        action dcIdentityPresent;
        verification dcIdentityPresentDoD : Test { :>> id = "7e51c8a3-0d84-4b17-9f26-38ea5c1074bd"; :>> method = VerificationMethod::test; :>> procedureText = "Resolves issue166. Guard 37 `identity-present`, HARD: every id-bearing declaration in `.tracking` or `.engine` must carry an `:>> id`. Closes an invariant that was unguarded - `keel validate` passed with issue159 stripped of its id. A TEXT SCAN, not a model walk, because an item with no identity is what the model layer sees least clearly and this must run at commit speed: measured 172/246/254ms over 8738 declarations with `Model::build was never called`, confirming the design rather than assuming it. NO GRANDFATHER LINE: the corpus was measured BEFORE the guard was written (8738 declarations, 0 missing), so an exemption would have been ceremony over an empty set. The body of each declaration stops at the NEXT declaration, so a member can never borrow its sibling's id - the bug that would let a file pass with one item holding two ids and its neighbour none. VERIFIED BOTH WAYS ON A NEW TYPE AND AN OLD ONE: clean PASS; a Statement stripped of its id FAILS and is named with file and line; an Issue stripped of its id FAILS. Also registered Statement and UserStory in all THREE copies of the id-type list (guards.rs plus both python validators), which is what their instruction to implement into parsing literally required."; }
        part dcIdentityPresentDoDR1 : TestResult { :>> id = "b0e6d942-51a7-4c38-8065-2fd93be71c4a"; :>> outcome = VerdictKind::pass; :>> judgedAgainst = "890b2dd"; :>> judgedAt = "2026-08-20"; :>> judgedBy = "claudeOpus5"; }
        action dcIntakeChain;
        verification dcIntakeChainDoD : Test { :>> id = "6b09fa42-8d75-4c31-b028-e5710af9c634"; :>> method = VerificationMethod::test; :>> procedureText = "Implements D0166 (accepted). `EngineIntake` in schema/core declares Statement (verbatim text, saidBy, saidAt, channel), UserStory (asA/iWant/soThat, implication, triageNote) and `metadata def Implicates`, so #Implicates is a legal marker and `implicates` a traversable edge kind derived from the declaration rather than restated in code. ImplicationKind carries THEIR nine members verbatim plus five that answer their question about others from categories this session actually produced - question, priority, attestation, correction, convention - and `none` so that implicating nothing is a recorded decision. `keel intake` reports three gaps that were not computable before: unparsed (direction nothing translated), unrouted (triaged then dropped - worse than untriaged because it looks handled), unsourced (downstream items with no statement behind them, stated as a FLOOR on the record rather than a claim about the human). Wired as a CLI command AND a computed view, so the console and the deck reach it through the one dispatch table. VERIFIED END TO END on their own words: 3 statements, 3 user stories, 0 unparsed, 0 unrouted, 0 stories without a source, 7 of 479 downstream items now sourced, byImplication bug/need/process = 1/1/1. Process and skill registered as a pair (process-skill PASS at 19)."; }
        part dcIntakeChainDoDR1 : TestResult { :>> id = "f31c7ed5-06b8-4a29-9754-2ba08cf16e37"; :>> outcome = VerdictKind::pass; :>> judgedAgainst = "a7050c2"; :>> judgedAt = "2026-08-20"; :>> judgedBy = "claudeOpus5"; }
        action dcMintCommand;
        verification dcMintCommandDoD : Test { :>> id = "2c3b9eb4-8ad6-4173-a58a-ebfe69ad3241"; :>> method = VerificationMethod::test; :>> procedureText = "us019 (their words: we should be programatically creating UUIDs, not via AI diligence). DONE MEANS: `keel mint [N]` prints N (default 1) freshly generated v4 UUIDs, lowercase, one per line, nothing else on stdout - composable into any authoring script. Advertised in the help catalogue (its coverage test fails the build without the line). Unit tests assert: every minted id satisfies guard 38's uuid_shaped; 10000 mints contain no duplicate; N=0 and a non-numeric arg are refused with usage, exit 2, per the positional_arg convention (issue179)."; }
        part dcMintCommandDoDR1 : TestResult { :>> id = "3d4ca0c5-9be7-4284-b69b-0cbf70be4352"; :>> outcome = VerdictKind::pass; :>> judgedAgainst = "36f226e"; :>> judgedAt = "2026-08-21"; :>> judgedBy = "claudeOpus5"; }
        action dcSprintScaffold;
        verification dcSprintScaffoldDoD : Test { :>> id = "4e5db1d6-0cf8-4395-c7ac-1dda81cf5463"; :>> method = VerificationMethod::test; :>> procedureText = "us019, the largest uuid-by-hand consumer: every sprint file hand-authors ~14 ids plus the 7-gate skeleton, and two hand ids have already been mangled (issue170). DONE MEANS: `keel new sprint <number> <slug>` writes .tracking/delivery/sprint<number>_<slug>.sysml containing the Story and the seven ceremony gates (refine, standup, implement, review, closeOut, retro, DoD) with EVERY id minted by the engine, createdAt/judgedAt stamped from the real clock, owner/createdBy from the bound actor (REFUSED if none - the provenance rule, never defaulted), and every procedureText set to a FILL-ME placeholder that `keel gate --fast` REJECTS, so an unfilled skeleton cannot pass a gate or be committed. Refuses to overwrite an existing file. Advertised in the help catalogue. Unit test scaffolds into a temp tree: file validates structurally, all ids pass uuid_shaped and are unique, and the placeholder is rejected by the fast gate."; }
        part dcSprintScaffoldDoDR1 : TestResult { :>> id = "5f6ec2e7-1d09-44a6-d8bd-2eeb92da6574"; :>> outcome = VerdictKind::pass; :>> judgedAgainst = "74ecefb"; :>> judgedAt = "2026-08-21"; :>> judgedBy = "claudeOpus5"; }
        action dcDecisionFollowThroughView;
        verification dcDecisionFollowThroughViewDoD : Test { :>> id = "6a7fd3f8-2e10-45b7-e9ce-3ffc03eb7685"; :>> method = VerificationMethod::test; :>> procedureText = "us020 (their issue174 note: the scaffolding under a decision isn't being made - backlog items? user stories? verification test cases?). DONE MEANS: `keel decision-follow-through` is a first-class computed view (not a lens buried in `keel hardening`): for EVERY accepted Decision it lists the tracked items reaching it by typed edge (#CharteredBy, #DerivedFrom, #Resolves, satisfy), each item's evidence state from its DoD results, and a GAPS section naming accepted Decisions with ZERO downstream tracked items. JSON is the authority; a table renders for humans; served at /api/computed/decision-follow-through; advertised in the help catalogue. VERIFIED against three hand-checked anchors: D0173 shows sprints 379/380 chartered and green; at least one known-bare accepted Decision appears in GAPS; and the gap count reconciles with the hardening lens it supersedes there, or the difference is explained in the view's own output."; }
        part dcDecisionFollowThroughViewDoDR1 : TestResult { :>> id = "7b80e409-3f21-46c8-fadf-400d14fc8796"; :>> outcome = VerdictKind::pass; :>> judgedAgainst = "245d2d3"; :>> judgedAt = "2026-08-21"; :>> judgedBy = "claudeOpus5"; }
        action dcDecisionScaffoldingGuard;
        verification dcDecisionScaffoldingGuardDoD : Test { :>> id = "8c91f510-4032-47d9-0bea-511e25ad9807"; :>> method = VerificationMethod::test; :>> procedureText = "us020's enforcement half, gated on their st014 (depends on WHAT is being asserted) - so step one is a PROPOSED DECISION, not a guard. DONE MEANS: a proposed Decision is authored and queued for their signature that names the exact assertion - the candidate: an ACCEPTED #ProspectiveChange Decision must, by the close of the sprint that lands it, be reachable by at least one tracked item edge, enforced as a guard whose scope starts forward-only from acceptance (no retro-failing history) - including the hard-vs-warning choice, the D0163 removal path, and what dcDecisionFollowThroughView must exist to compute first. IMPLEMENTED only per whatever they sign: guard registered in GUARD_NAMES with dispatch and doc row, unit-tested against a synthetic tree with one covered and one bare decision, green over the real tree at the forward-only boundary. If they reject, the rejection is recorded and this item is superseded by it."; }
        part dcDecisionScaffoldingGuardDoDR1 : TestResult { :>> id = "7cf0319e-3678-4981-b6a8-854170150e1e"; :>> outcome = VerdictKind::pass; :>> judgedAgainst = "06742e4"; :>> judgedAt = "2026-08-21"; :>> judgedBy = "claudeFable5"; }
        action dcDeckWorkSurface;
        verification dcDeckWorkSurfaceDoD : Test { :>> id = "5f28c1a3-7d60-4b94-8e17-03ba69dc5f42"; :>> method = VerificationMethod::inspect; :>> procedureText = "Resolves issue161-165, the artifact-idea half of their requested UX critique. NOT STARTED. Five defects, one theme: the deck is a QUEUE and they need a WORK SURFACE. (161) regeneration overwrites unsubmitted marks - ordering rule mitigates, diff-and-merge would fix. (162) no notification; they must remember to look. (163) no history; it cannot show what was decided before. (164) three buttons, four meanings - a schema-vs-user vocabulary gap, not a display one. (165) they can judge but not act; every verdict round-trips through me. UNSCOPED DELIBERATELY: 164 wants a schema conversation and 165 wants a write path from an artifact to this machine, which D0158 makes local-only by decision. Their direction is needed before any of it."; }
        part dcDeckWorkSurfaceDoDR1 : TestResult { :>> id = "c94b0f75-1e38-4a26-b503-7fd28ea61c90"; :>> outcome = VerdictKind::fail; :>> judgedAgainst = "PENDING"; :>> judgedAt = "2026-08-20"; :>> judgedBy = "claudeOpus5"; }
        action dcLegibleOutput;
        verification dcLegibleOutputDoD : Test { :>> id = "8d1a67f0-3b52-4c94-a806-7e25fb019c43"; :>> method = VerificationMethod::inspect; :>> procedureText = "Resolves issue160. NOT STARTED beyond the review deck, where the duplication is already cut: a title losing its self-referential prefix, the class stated once in its heading rather than per card, and one line per item in the export. THE ENGINE-WIDE WORK IS UNSCOPED ON PURPOSE and needs their direction, because each part trades something: a cap on procedureText loses detail that a gate's own text is supposed to carry; suppressing the 52 legacy-actor warnings hides real pre-convention debt; a human mode for `keel orient` means a second surface to keep truthful. VERIFY by a legibility test I cannot write alone - can a reader answer WHAT DO I DO NEXT from one screen of output without grep."; }
        part dcLegibleOutputDoDR1 : TestResult { :>> id = "e740b3c8-95d1-4a26-b073-1cf85ea6209d"; :>> outcome = VerdictKind::fail; :>> judgedAgainst = "PENDING"; :>> judgedAt = "2026-08-20"; :>> judgedBy = "claudeOpus5"; }
        action dcLiveDoc;
        verification dcLiveDocDoD : Test { :>> id = "0b53e971-8c24-4d36-a170-e6f2b8940a5c"; :>> method = VerificationMethod::demo; :>> procedureText = "Resolves issue159. The review deck is now an artifact LIVE DOC (`capabilities: {artifact: {}}`, runtime contract 0.2.9): the page's markup is the document, so a verdict tap and a typed note are appended as the human and reach the watching session with NO copy step. The export survives as a fallback for a read-only view and now copies ON OPEN rather than charging a second click. Contract rules honoured and each one would have failed silently: shared content authored as HTML and mutated only in gesture handlers (the localStorage restore is deleted - a load-time mutation saves nothing and a second record would contradict the document); per-viewer chrome on `data-local-open`; notes as `<input>` because textarea values are not captured; read-only detected as a body-level `claude:sync-off` REJECTION rather than assumed. METHOD IS demo and the result stays FAILING until the human confirms a tap reached me without a paste - D0160 means I cannot execute the page, and this is the ninth browser behaviour this session I would otherwise be asserting unobserved."; }
        part dcLiveDocDoDR1 : TestResult { :>> id = "3a7f14c8-06e5-4b92-8d31-72cb50fe6a94"; :>> outcome = VerdictKind::fail; :>> judgedAgainst = "PENDING"; :>> judgedAt = "2026-08-20"; :>> judgedBy = "claudeOpus5"; }
        action dcObligationDeck;
        verification dcObligationDeckDoD : Test { :>> id = "9c40b768-2e51-4a83-b109-57fd6e2c8340"; :>> method = VerificationMethod::demo; :>> procedureText = "The human asked for a skill that renders outstanding items as STATIC HTML usable as an artifact on mobile. Delivered as `obligation-review` (D0040: a recurring task with no skill becomes the skill first), deploying `.engine/tools/obligation_canvas.py`. It shells out to the `keel` binary for orient/authority-queue/dispositions/sitting-coverage, so the deck cannot disagree with `keel orient` and needs NO running server - which is the point, since `keel serve` requires a shell, a server and a localhost browser and their obligations do not wait for those conditions. 86 items across four classes, one hue each. Verdict (accept/needs-work/reject) and note per item, stored in localStorage keyed by each item's MINTED UUID rather than its label, with a content signature so an item edited after being judged re-surfaces with a `changed` badge. Copy for Claude emits markdown for paste-back. Verified: counts match the computed views (4/27/22/33); zero non-ASCII bytes in the output, because the artifact runtime supplies the head and this file cannot declare a charset; the only synthetic uid is an aggregate authority row whose item is a sentence, not an item. METHOD IS demo - whether it is usable on their phone is theirs to judge, and the skill records nothing until they paste the export back."; }
        part dcObligationDeckDoDR1 : TestResult { :>> id = "1e8a4d05-6b39-4c72-8e04-fa93c1257b6d"; :>> outcome = VerdictKind::fail; :>> judgedAgainst = "PENDING"; :>> judgedAt = "2026-08-20"; :>> judgedBy = "claudeOpus5"; }
        action dcViewpointActivation;
        verification dcViewpointActivationDoD : Test { :>> id = "6e07b325-4c81-4a97-b06d-51fe8a29d340"; :>> method = VerificationMethod::test; :>> procedureText = "Implements the human's direction in their D0159 acceptance (viewpoints activatable like processes) under D0164, and resolves issue156. `.engine/contracts/activation.toml` gains a `[viewpoints]` section read by the same loader under the same rule as processes: absent means all active, declared-but-empty means none. Observed in `surfaces_json` (the one derivation behind the console nav and the act obligation bar) and in the `viewpoint-renderer` guard; deliberately NOT observed in concern-coverage, because suppressing an inactive lens there would let a project reach full concern coverage by switching off the concerns it was failing. VERIFIED BY ROUND TRIP, not by the command's own report: deactivate archDriftVP, then `keel activation` shows INACTIVE, the manifest carries both sections with all six active processes preserved, and /api/surfaces stops mentioning it (grep count 1 -> 0); reactivate and delete the manifest restores everything active. That round trip is what caught issue156 - the broken version printed the same success message. Re-run after the clippy refactor that extracted switch_viewpoint. 191 tests, clippy clean, 36 guards ALL PASS."; }
        part dcViewpointActivationDoDR1 : TestResult { :>> id = "b4f28e51-9a06-4d73-8c25-1e73fb0a6d92"; :>> outcome = VerdictKind::pass; :>> judgedAgainst = "93b9447"; :>> judgedAt = "2026-08-19"; :>> judgedBy = "claudeOpus5"; }
        action dcOneClickToAct;
        verification dcOneClickToActDoD : Test { :>> id = "5a92f30c-7e18-4b64-a207-93cd6e15b482"; :>> method = VerificationMethod::demo; :>> procedureText = "Resolves issue155. The SERVER names the discharging panel per obligation class in the same pass that computes the count, so the card lands on the panel with the controls in ONE click instead of opening a read-only view that offers a bridge. `discharge_panel(cmd)` is stated per command with a reason rather than inferred from payload shape - a wrong guess would send the human to a panel that cannot act, which is the defect issue154 addressed. None is a first-class answer, so a newly declared act viewpoint still needs no console change and its card reads `click to view (read-only)` rather than overpromising. Verified live: acceptances-pending -> review, authority-queue -> review, findings-awaiting-disposition -> dispositions, sitting-review-due -> none. METHOD IS demo: whether a click now lands in one hop is a browser behaviour D0160 says we cannot execute, and I have asserted unobserved browser behaviour three times this session already."; }
        part dcOneClickToActDoDR1 : TestResult { :>> id = "d7014e83-2b65-4c39-8f10-6ae82b537c94"; :>> outcome = VerdictKind::fail; :>> judgedAgainst = "PENDING"; :>> judgedAt = "2026-08-19"; :>> judgedBy = "claudeOpus5"; }
        action dcActionableDestination;
        verification dcActionableDestinationDoD : Test { :>> id = "7d3e15a2-6b48-4c09-9e71-84fa20b5cd67"; :>> method = VerificationMethod::demo; :>> procedureText = "Resolves issue154. A panel holding work it cannot discharge now carries a warning-bordered note stating that nothing on it is a control, plus a bridge to the panel that can act - keyed on the PAYLOAD's shape (kinds matching accept/confirm, or a pendingAcceptances array) rather than a list of viewpoint names, so a later-declared class gets it with no console change. The orient panel gained the bridge and an `Awaiting YOUR acceptance` card it had never rendered despite orient always returning the data. The bridge travels as `data-panel` through the same document-level delegation as card targets, so it cannot be orphaned by a re-render. METHOD IS demo, NOT test, and no passing result is recorded from my side: D0160 records that we cannot execute the page, and this is the fourth time I would have been asserting a browser behaviour I cannot observe. The human closes this one."; }
        part dcActionableDestinationDoDR1 : TestResult { :>> id = "c56b09d7-3f81-4e26-a940-1b78ec25f0a3"; :>> outcome = VerdictKind::fail; :>> judgedAgainst = "PENDING"; :>> judgedAt = "2026-08-19"; :>> judgedBy = "claudeOpus5"; }
        action dcConsoleSelfReport;
        verification dcConsoleSelfReportDoD : Test { :>> id = "4c7f2b98-1a30-4d65-b842-e0193fa6c57d"; :>> method = VerificationMethod::demo; :>> procedureText = "Resolves issue152, and it is NOT resolved by shipping the diagnostics - it is resolved when the human reports what the page says. DELIVERED: click delegation moved to `document` and registered immediately after the element handles, so no later top-level error and no replaced node can orphan it; a targeted click announces `opening <viewpoint>...` before any await; an untargeted card click reports how many targeted cards exist in the DOM; and the file's LAST statement stamps `js ok` plus the clickable-card count into the header. VERIFICATION IS A DEMONSTRATION BY THE HUMAN because D0160 records that we cannot execute the page - the honest method here is `demo`, not `test`, and no passing result may be recorded from my side. THE ONE OBSERVATION THAT DISCRIMINATES: if the header does not read `js ok`, the script threw before its end; if it does, the listener is attached and the click message says whether a target was found."; }
        part dcConsoleSelfReportDoDR1 : TestResult { :>> id = "e83a15c6-70b4-4e29-9d07-2b56cf1a94e0"; :>> outcome = VerdictKind::fail; :>> judgedAgainst = "PENDING"; :>> judgedAt = "2026-08-19"; :>> judgedBy = "claudeOpus5"; }
        action dcOversightAdvisory;
        verification dcOversightAdvisoryDoD : Test { :>> id = "9a24e70f-6c53-4b18-8d92-1fe0b57ca346"; :>> method = VerificationMethod::test; :>> procedureText = "Resolves issue150. (a) `keel serve` runs from a COPY of the binary so it no longer blocks rebuilds - verified by rebuilding while the console kept answering, and recorded in CLAUDE.md section 6. (b) When the model is GREEN, `keel hook stop` advises - never blocks - if items are waiting on the human and no console answers on 127.0.0.1:7777. Verified BOTH WAYS live: with the console down it reported 70 items and named the command to run; with the console up it was silent. The check asks /api/version and requires `apiVersion` in the response, so a foreign process on the port cannot be reported as a console. The count comes from `serve::obligations_json`, extracted to one home so the advisory and the console cannot disagree. Controlled by the_oversight_advisory_never_blocks (the green branch of hook_stop must contain no block decision and must emit a systemMessage) and the_advisory_counts_what_the_console_shows (the reused total must be computable and non-zero here)."; }
        part dcOversightAdvisoryDoDR1 : TestResult { :>> id = "c1b85f30-4d67-4e29-a074-6b3ea9c25d81"; :>> outcome = VerdictKind::pass; :>> judgedAgainst = "3859cf7"; :>> judgedAt = "2026-08-19"; :>> judgedBy = "claudeOpus5"; }
        action dcActivationSurface;
        verification dcActivationSurfaceDoD : Test { :>> id = "3e58c701-9d42-4b86-a137-6f0ba4c92d18"; :>> method = VerificationMethod::test; :>> procedureText = "Resolves issue149. `keel activation` now lists every process file in `.engine/processes/`, marking those that assert no guard as `[always] asserts no guard - nothing to switch off`, and the `keel deactivate` refusal distinguishes an unknown process name from a declared-but-unswitchable one, saying what to do instead. Activation semantics are UNCHANGED: it still governs guards (D0138), and no guard changed state - this is a reporting fix, because the mechanism was right and only its surface lied. Verified by declared_processes_is_every_file_not_only_the_guard_bearing_units, which asserts the declared set strictly exceeds the unit set and that every unit is also declared, plus a live read: 18 processes listed where 6 were before, and the two refusal messages differ correctly for `knowledge-graph-memory` versus `no-such-process`."; }
        part dcActivationSurfaceDoDR1 : TestResult { :>> id = "0c96b4f8-7e31-4a25-b968-24da51e0c73f"; :>> outcome = VerdictKind::pass; :>> judgedAgainst = "a6d6545"; :>> judgedAt = "2026-08-19"; :>> judgedBy = "claudeOpus5"; }
        action dcBatchGitReads;
        verification dcBatchGitReadsDoD : Test { :>> id = "1f47ae0c-6b28-4d91-8305-9ca2e7b41f60"; :>> method = VerificationMethod::test; :>> procedureText = "Resolves issue147. DO: (1) finish the instrumentation - count spawns at all ~25 a raw `Command::new` git spawn sites, not just the two shared helpers, so the reported total stops understating; (2) replace the per-element historical-content reads with ONE `git cat-file --batch` process fed every (sha, path) pair on stdin. VERIFY on a warmed binary with five samples, and verify with the SPAWN COUNTER as well as the clock - the count is the direct measurement and the clock is the consequence. TARGET: 483 spawns to fewer than 10, and `assured` from ~21s toward the ~6s that remains once 15s of spawn cost is removed. DO NOT accept a wall-clock-only demonstration: a previous 31% improvement on this codebase was noise under five samples, and a previous 62% attribution was invalid because removing git changed the code path (D0050 makes grandfathered_under return None). The spawn counter is immune to both failure modes."; }
        part dcBatchGitReadsDoDR1 : TestResult { :>> id = "5b0c8f31-42d7-4e69-a814-c37e9b25f0da"; :>> outcome = VerdictKind::fail; :>> judgedAgainst = "PENDING"; :>> judgedAt = "2026-08-19"; :>> judgedBy = "claudeOpus5"; }
        part dcBatchGitReadsDoDR2 : TestResult { :>> id = "8f3d0a62-51c7-4b94-a70e-16de5b8c2947"; :>> outcome = VerdictKind::pass; :>> judgedAgainst = "a92e916"; :>> judgedAt = "2026-08-19"; :>> judgedBy = "claudeOpus5"; }
        action dcInstrumentAllGitSites;
        verification dcInstrumentAllGitSitesDoD : Test { :>> id = "6d17b40e-8c25-4f39-b082-a4e7139cf520"; :>> method = VerificationMethod::test; :>> procedureText = "The remaining half of issue147, split out so dcBatchGitReads can be honestly done. The spawn counter covers only `view::git_out` and `govern::git_lines` - two of about 25 a raw `Command::new` git spawn sites - so every reported total UNDERSTATES, and `orient` reports git x0 while demonstrably shelling out. DO: route every site through one counted helper, so the tally cannot silently omit a caller. VERIFY: `orient` reports a non-zero spawn count, and a grep for a raw `Command::new` git spawn outside the shared helper returns nothing - a static check, because a counter that depends on remembering to call it is the manual vigilance D0047 refuses."; }
        part dcInstrumentAllGitSitesDoDR1 : TestResult { :>> id = "a09e5c74-3b18-4d62-8f05-71ca4e39b8d6"; :>> outcome = VerdictKind::fail; :>> judgedAgainst = "PENDING"; :>> judgedAt = "2026-08-19"; :>> judgedBy = "claudeOpus5"; }
        part dcInstrumentAllGitSitesDoDR2 : TestResult { :>> id = "a7d88982-7928-44b9-8437-c64fc60fd8bc"; :>> outcome = VerdictKind::pass; :>> judgedAgainst = "9ef39ed"; :>> judgedAt = "2026-08-21"; :>> judgedBy = "claudeOpus5"; }
        action dcFingerprintEpoch;
        verification dcFingerprintEpochDoD : Test { :>> id = "7a1e5d38-2c60-4b94-8f17-e05b3c92a641"; :>> method = VerificationMethod::test; :>> procedureText = "Resolves issue145. ONE home for the content fingerprint (`crate::fingerprint`), replacing identical copies in view.rs and serve.rs, memoized by an EXPLICIT EPOCH rather than a timer: a CLI process is one epoch (one-shot, read-only), serve bumps per HTTP request so each request sees one snapshot and the request after a write re-reads, and the SSE change detector uses the uncached `compute` because it IS the detector. Measured with the new KEEL_PERF instrumentation on a warmed binary: `assured` fingerprint 1472ms to 41ms, stats 21,534 to 582, tree walks 74 to 2; `orient` 301ms to 36ms. Invalidation EXERCISED end to end against the running server, not asserted: the fingerprint changed after an edit to .tracking/issues.sysml. Two unit tests cover the memo being keyed by root as well as epoch, and an epoch bump forcing a re-walk. CLI `assured` wall clock did NOT improve materially and that is stated rather than glossed - it is dominated by 483 git spawns, which is a separate finding."; }
        part dcFingerprintEpochDoDR1 : TestResult { :>> id = "b6e04f27-91a3-4c58-8d06-2f73ea5c1849"; :>> outcome = VerdictKind::pass; :>> judgedAgainst = "dfd2677"; :>> judgedAt = "2026-08-19"; :>> judgedBy = "claudeOpus5"; }
        action dcComputedBindingSplit;
        verification dcComputedBindingSplitDoD : Test { :>> id = "c82f6a13-4d75-4e09-b731-05af9e2c6d14"; :>> method = VerificationMethod::test; :>> procedureText = "Resolves issue146. `computed_binding(cmd) -> Option<ComputedFn>` answers IS THIS BOUND from the dispatch table alone and returns the function; `computed_view` is that call plus an application. The old signature `Option<Result<String, _>>` folded boundness and computation into one value, so `api_computed` could only ask the cheap question by answering the expensive one - it computed the view to decide the status code, discarded it, then computed it again through the cache, defeating the per-fingerprint cache its own doc comment advertised. MEASURED SAME-SESSION on the eight endpoints the console requests, three samples each: warm burst 7197ms to 979/1227/1291ms; cold burst 12066ms to 5185/5277/5505ms. Both fixes (this and dcFingerprintEpoch) are in the after number and are not separated, which is stated rather than implied - the fingerprint instrument readings isolate that half directly."; }
        part dcComputedBindingSplitDoDR1 : TestResult { :>> id = "e5c19b04-7f26-4a83-9d15-38b0ce74f291"; :>> outcome = VerdictKind::pass; :>> judgedAgainst = "dfd2677"; :>> judgedAt = "2026-08-19"; :>> judgedBy = "claudeOpus5"; }
        action dcImpossibleEvidenceDate;
        verification dcImpossibleEvidenceDateDoD : Test { :>> id = "5c8f3b21-04ae-4d76-9137-a2e608bd5f49"; :>> method = VerificationMethod::test; :>> procedureText = "Resolves issue144. Guard 36 impossible-evidence-date: a TestResult may not cite a judgedAgainst commit made AFTER its judgedAt, because a judgment cannot be made against a commit that did not exist yet. HARD-blocking and forward-only from 2026-08-18 (D0162), keyed on the CITED COMMIT's date and not on judgedAt - the first draft keyed on judgedAt and exempted the very defect the guard exists for, since a day-old judgment stamped at today's commit is old by judgedAt and brand new by evidence. Verified BOTH WAYS against the live corpus: clean tree PASS at 3799 results scanned, and with the actual defect reintroduced at keel-console.sysml:136 it FAILS naming srConsoleObligationActionableConfirmR1. The thirteen grandfathered cases are two midnight-rollover sessions, each a single commit exactly one day later; five are the human's own attestations, which D0108 forbids me from editing, so the line is drawn rather than their dates rewritten."; }
        part dcImpossibleEvidenceDateDoDR1 : TestResult { :>> id = "e0a74c93-1b62-4f85-a3d0-96c72e5b148f"; :>> outcome = VerdictKind::pass; :>> judgedAgainst = "fd46d85"; :>> judgedAt = "2026-08-18"; :>> judgedBy = "claudeOpus5"; }
        action dcConsoleLoudFailure;
        verification dcConsoleLoudFailureDoD : Test { :>> id = "8e5b1a67-4c02-4d93-b718-6f3a0e29c845"; :>> method = VerificationMethod::test; :>> procedureText = "Resolves issue143. Three structural controls so a console failure can never again be indistinguishable from a console no-op: the page is served no-store and stamps the API version it loaded against, so a stale browser is detectable rather than arguable; a thrown render writes the failure INTO the panel instead of leaving the previous view up with a whisper in the status line; and a click announces its target BEFORE its first await, so a click that fired and failed is distinguishable from one that never fired. Verified by a_console_failure_can_never_look_like_nothing_happened (serve.rs), which asserts all four properties, and by the live server returning cache-control: no-store on /. NOT VERIFIED and stated as such: whether any of this fixes the human's reported failure, whose cause remains unknown because D0160 leaves us unable to execute the page."; }
        part dcConsoleLoudFailureDoDR1 : TestResult { :>> id = "b3d7f09a-52e1-4c86-9047-1ae6c85b2f73"; :>> outcome = VerdictKind::pass; :>> judgedAgainst = "cb53ba0"; :>> judgedAt = "2026-08-18"; :>> judgedBy = "claudeOpus5"; }
        action dcStaleGateProse;
        verification dcStaleGateProseDoD : Test { :>> id = "1e58a7c0-4d36-4b91-a2f7-83be05c14d29"; :>> method = VerificationMethod::test; :>> procedureText = "Resolves issue140. Six comments in keel-viewer.sysml claimed Business gates 2, 3 and 5 were PENDING while all three carry passing acceptance results, and one of them misled me into publishing a false claim in a landed critique. DO: rewrite all six to state what IS (no tombstones), correct the false clause in the critique with the correction left visible, and add a guard that fails on a PENDING-style claim within three lines of a PASSING acceptance result - precise enough that an honest PENDING note beside an unsigned gate is untouched. VERIFY both directions: the fixed corpus passes with the acceptance-result count reported, and re-injecting the exact stale comment FAILS with its file and line."; }
        part dcStaleGateProseDoDR1 : TestResult { :>> id = "6c3f19b5-0a74-4e82-95d1-27ef4a806b3c"; :>> outcome = VerdictKind::pass; :>> judgedAgainst = "6e16e18"; :>> judgedAt = "2026-08-17"; :>> judgedBy = "claudeOpus5"; }
        action dcViewpointEnumeration;
        verification dcViewpointEnumerationDoD : Test { :>> id = "5d29b7f4-3e60-4a18-9c73-81ea0f5d2b96"; :>> method = VerificationMethod::test; :>> procedureText = "Resolves issue139, and is a PREREQUISITE for dcUnitPortabilityScope: the viewpoint-renderer hard guard and concern-coverage read one hardcoded filename while the Model globs the views directory, so a viewpoint declared elsewhere escapes the guard - and splitting the registry per-viewpoint would therefore disable the guard for every one of them. DO: source both readers from the same enumeration the Model uses, so the engine holds ONE answer to 'what viewpoints exist'. VERIFY: a test declares a viewpoint OUTSIDE viewpoint-registry.sysml with an unknown renderer and asserts the guard FAILS on it - the direction that was broken, not just the green one; the scanned count rises to include it; concern-coverage reports it; and the existing 32 still behave identically."; }
        part dcViewpointEnumerationDoDR1 : TestResult { :>> id = "9b40e2d7-5c18-4f63-a091-38ec7a2b5f04"; :>> outcome = VerdictKind::pass; :>> judgedAgainst = "105da24"; :>> judgedAt = "2026-08-17"; :>> judgedBy = "claudeOpus5"; }
        action dcUnitPortabilityScope;
        verification dcUnitPortabilityScopeDoD : Test { :>> id = "a1f6c2b3-7d40-4e19-95c8-3ba7e0f24d18"; :>> method = VerificationMethod::inspect; :>> procedureText = "Resolves issue138. A viewpoint is the same portable UNIT shape as a process - files to copy plus names that must exist in the receiving project - but `keel process export` enumerates only activation units. DO: decide whether the unit machinery generalizes (processes and viewpoints as two KINDS of unit, one bundle format, one import that reports what the receiving binary lacks) or whether a viewpoint bundle is a separate command, and record it as a Decision before writing code. Scope the decision on the two facts already measured: 7 of 32 viewpoints have a .view.toml, and 21 of 32 name a keel subcommand as their renderer. VERIFY: the Decision states which way and why; if it generalizes, a viewpoint exported from one project imports into another and the import REPORTS a renderer the receiving binary does not have rather than importing a lens that cannot render."; }
        part dcUnitPortabilityScopeDoDR1 : TestResult { :>> id = "f47ac3b1-6e29-4d80-95a4-08bd2e57c916"; :>> outcome = VerdictKind::pass; :>> judgedAgainst = "7f09bc8"; :>> judgedAt = "2026-08-17"; :>> judgedBy = "claudeOpus5"; }
        action dcServeWarmCache;
        verification dcServeWarmCacheDoD : Test { :>> id = "3f80c1a7-6b24-4d95-8e13-07ba5ce29f41"; :>> method = VerificationMethod::test; :>> procedureText = "THE INTERACTIVE SURFACE IS FAST BECAUSE A CACHE HIT IS A CACHE HIT. Measured at the HTTP boundary on the six-request console arrival burst, warm, five samples, same tree: was 1.05-1.17s, now 0.02s. The finding that got there: a HIT cost 137-208ms and the fingerprint was ALL of it (`fp 180ms/604 stat, parse 0ms, build x0, git x0`), because the epoch advanced on every request and each of the six re-statted 604 files. Fixed by advancing the epoch on an OBSERVED CHANGE or a WRITE, never on a read (D0167), with one watcher task per server rather than one poll per open tab. Also: /api/obligations now computes through the shared store instead of a private local, so `orient` is computed once per arrival rather than twice; and the store is keyed by the VIEW rather than the ROUTE. DONE MEANS: the warm burst is under 100ms; an out-of-band edit is still observed and honestly labelled `stale` while it recomputes; a write through the server is visible to the very next read with no wait; and `the_epoch_is_advanced_by_writes_and_observations_not_by_reads` fails if the unconditional bump returns."; }
        part dcServeWarmCacheDoDR1 : TestResult { :>> id = "8d24e0b6-5f19-4a73-b0c8-31ea6d795f02"; :>> outcome = VerdictKind::pass; :>> judgedAgainst = "e5c376b"; :>> judgedAt = "2026-08-20"; :>> judgedBy = "claudeOpus5"; }
        action dcUuidWellFormed;
        verification dcUuidWellFormedDoD : Test { :>> id = "5b91d3e8-4f07-4a62-9c18-73ea20bd6f45"; :>> method = VerificationMethod::test; :>> procedureText = "Invariant 3 says identity is an immutable UUID. `identity-present` (guard 37) checks that an id EXISTS and `duplicate-identity` checks that two items do not SHARE one; NOTHING checks the string is a UUID. Verified by deliberate corruption: an id of `not-a-uuid-at-all` passes `keel validate` and all 37 guards. DONE MEANS: a guard rejects any id that is not 8-4-4-4-12 lowercase hex, over the same id-bearing declarations guard 37 already walks; it is verified BOTH WAYS on a clean tree and a corrupted one; the corpus is measured BEFORE the guard is written so the need for a grandfather line is known rather than discovered; and it is a text scan, so `Model::build` is never called and `keel assured` does not slow down (the rule sprint 347 set)."; }
        part dcUuidWellFormedDoDR1 : TestResult { :>> id = "fa4ea93e-bb7a-4c62-bf81-04ccf50693cf"; :>> outcome = VerdictKind::pass; :>> judgedAgainst = "3abc583"; :>> judgedAt = "2026-08-20"; :>> judgedBy = "claudeOpus5"; }
        action dcAuditInstrument;
        verification dcAuditInstrumentDoD : Test { :>> id = "6c14a8f2-3b57-4d90-8e26-71fa05cd3e84"; :>> method = VerificationMethod::test; :>> procedureText = "The hardening audit has NO reusable instrument, so every audit re-derives its probes as throwaway python and gets them WRONG. In this single pass four probes were wrong before they were right: a regex matching `: Process` also matched `: ProcessStep` (131 vs 24), help-text extraction failed twice (reporting `keel orient` as missing when it obviously exists, then 0-of-72 documented), and a registry probe reported 0 skills registered against 35 real ones. Each wrong number was one edit from becoming a recorded finding. DONE MEANS: the audit's questions are COMPUTED views with the rest of them - subcommand-help coverage, process enforcement census, decision follow-through, field-liveness - so the next audit reads numbers instead of inventing probes. This is the highest-leverage item in the pass because it is the one that makes the other findings re-checkable rather than re-derivable."; }
        part dcAuditInstrumentDoDR1 : TestResult { :>> id = "5e44c539-e9b0-4f2c-a4cf-a05725268f79"; :>> outcome = VerdictKind::pass; :>> judgedAgainst = "d951cff"; :>> judgedAt = "2026-08-20"; :>> judgedBy = "claudeOpus5"; }
        action dcHelpFromDispatch;
        verification dcHelpFromDispatchDoD : Test { :>> id = "b7e0396c-5d24-4a81-9f03-28ce74ab516d"; :>> method = VerificationMethod::test; :>> procedureText = "`keel --help` names 38 of 72 top-level subcommands; 34 are absent (47%), including `assured`, `intake`, `rootedness`, `suspect`, `reverify`, `dispositions`, `open-issues`, `indicators`, `concern-coverage` and `tier-satisfaction`. The CLI is the authority and the automation substrate (D0093), and nearly half of it is undiscoverable from its own front door - a reader who has not read CLAUDE.md cannot find the commands the discipline depends on. DONE MEANS: help is DERIVED from the dispatch table rather than hand-maintained beside it, and a test asserts every dispatch arm is reachable from help output. Hand-maintained help next to a hand-maintained match is two truths (section 1)."; }
        part dcHelpFromDispatchDoDR1 : TestResult { :>> id = "1ca654d3-2836-4b46-b690-47fa7517cbba"; :>> outcome = VerdictKind::pass; :>> judgedAgainst = "d951cff"; :>> judgedAt = "2026-08-20"; :>> judgedBy = "claudeOpus5"; }
        action dcProcessEnforcement;
        verification dcProcessEnforcementDoD : Test { :>> id = "2f8b51d0-7c46-4e93-a105-63da09be2c71"; :>> method = VerificationMethod::test; :>> procedureText = "13 of 19 processes assert NO guard - `keel activation` prints `asserts no guard - nothing to switch off` for actor-enrollment, architectural-critique, definition-of-done, definition-of-ready, deploy, diagram, distributed-collaboration, indicator, intake, introduction, knowledge-graph-memory, migration and report. D0141 says processes assert their constraints; for 68% of the catalogue the assertion is empty, which means the process cannot be enforced, `activate`/`deactivate` is a no-op on it, and adoption is a claim rather than a control. Some of these are genuinely unenforceable by a text guard (a critique is a judgment), and that is exactly the distinction nothing currently records. DONE MEANS: every process either asserts a guard or carries a recorded justification for why its constraint is not machine-checkable - and the ratio is an INDICATOR, since a guard cannot be conjured for a genuinely human step (invariant 7)."; }
        part dcProcessEnforcementDoDR1 : TestResult { :>> id = "db2073cb-eb2d-44ef-8ea5-cc540b4b7aa4"; :>> outcome = VerdictKind::pass; :>> judgedAgainst = "d951cff"; :>> judgedAt = "2026-08-20"; :>> judgedBy = "claudeOpus5"; }
        action dcDecisionFollowThrough;
        verification dcDecisionFollowThroughDoD : Test { :>> id = "9a45c7e1-8f30-4b62-9d17-50ba21ce7f39"; :>> method = VerificationMethod::test; :>> procedureText = "An ACCEPTED Decision can promise an artifact that is never built, and nothing notices. D0161 was accepted 2026-08-20 and its `.knowledge/` retrieval index DOES NOT EXIST. 64 of 161 accepted Decisions have no `#CharteredBy` work at all - most legitimately, because a policy Decision needs no implementation, and that ambiguity is the defect: the model cannot distinguish `accepted and needs nothing` from `accepted and abandoned`. That is the mechanism behind the human's report of half-baked implementations. DONE MEANS: a Decision that promises a named artifact declares it, and a computed view reports accepted Decisions whose promised artifact is absent. Not a gate - a Decision may be accepted long before it is built, and blocking would only push the promise out of the record."; }
        part dcDecisionFollowThroughDoDR1 : TestResult { :>> id = "c2efc4cf-e15f-4dc6-abd1-9ed28e0c389a"; :>> outcome = VerdictKind::pass; :>> judgedAgainst = "d951cff"; :>> judgedAt = "2026-08-20"; :>> judgedBy = "claudeOpus5"; }
        action dcActualHoursOrRetire;
        verification dcActualHoursOrRetireDoD : Test { :>> id = "4d72e0b9-1a68-4c53-8b04-95fc37ae2d16"; :>> method = VerificationMethod::test; :>> procedureText = "354 of 358 sprints record no `actualHours` - the field carries data in 1% of the corpus. D0072 accepted it as the record of AI time and `keel audit` reports the gap as `estimation_discipline`. A field populated 1% of the time is not discipline; it is either a dead field dressed as a practice, or a practice nobody performs. Both readings are worse than deciding. DONE MEANS: either the field is filled as a matter of course (a write-path default, since a human is not going to type it), or D0072 is superseded and the field is REMOVED with its audit metric - per the doc-removal rule, state what is, do not leave a tombstone. Recording an unpopulated field as a metric trains a reader to ignore the metric, which is issue160's warning-fatigue one layer down."; }
        part dcActualHoursOrRetireDoDR1 : TestResult { :>> id = "955d6bc7-1bc2-4531-aec2-893ec6a55640"; :>> outcome = VerdictKind::pass; :>> judgedAgainst = "d951cff"; :>> judgedAt = "2026-08-20"; :>> judgedBy = "claudeOpus5"; }
        action dcCharterProvenanceSplit;
        verification dcCharterProvenanceSplitDoD : Test { :>> id = "8e0c4a63-2d19-4f75-b830-16ca57de9241"; :>> method = VerificationMethod::test; :>> procedureText = "306 of 360 delivery Stories are chartered by a Decision I authored; 53 reach a Need; 1 is an orphan. The engine's stated purpose is tracking work that satisfies stakeholder needs, and 85% of its own work is self-chartered - which D0064 explicitly permits as decision-driven engine evolution, and that permission is what makes the number unfalsifiable. Paired with `keel intake` reporting 472 of 480 downstream items as unsourced, the model cannot currently distinguish legitimate engine evolution from work the AI invented. DONE MEANS: `decision_chartered` is split so that a charter tracing to a Decision that itself traces to a Statement or Need is counted separately from one that traces to nothing but my own judgment. The number is not the problem; the fact that one number covers both cases is."; }
        part dcCharterProvenanceSplitDoDR1 : TestResult { :>> id = "8d1cc480-9cdb-4eb3-b133-7678ef3c8188"; :>> outcome = VerdictKind::pass; :>> judgedAgainst = "d951cff"; :>> judgedAt = "2026-08-20"; :>> judgedBy = "claudeOpus5"; }
        action dcUnknownNameFails;
        verification dcUnknownNameFailsDoD : Test { :>> id = "c93e4b17-6f28-4d05-8a71-24be05cd7e39"; :>> method = VerificationMethod::test; :>> procedureText = "A read command given a name that does not exist returns EXIT 0 and a valid-looking empty result. `trace .` gives upstream [] downstream []; `trace-need .` gives trace []; `actor-trace .` and `governing-version .` answer as though the name were real; `boundary .` and `item .` return an `error` KEY with rc=0, which is dual signalling. D0093 makes the CLI the automation substrate, and a consumer reads that as 'this item has no relations', not 'there is no such item' - so a typo in a script becomes a silent wrong answer rather than a failure. `report`, `render` and `arch` already exit nonzero for an unknown argument, so the CLI is inconsistent with itself. DONE MEANS: an unresolvable name exits nonzero with a message naming the item, uniformly across every name-taking read command, and a test pins it."; }
        part dcUnknownNameFailsDoDR1 : TestResult { :>> id = "69686eef-4c98-431e-b102-0f49841d4a54"; :>> outcome = VerdictKind::pass; :>> judgedAgainst = "d951cff"; :>> judgedAt = "2026-08-20"; :>> judgedBy = "claudeOpus5"; }
        action dcAdvertiseApiSurface;
        verification dcAdvertiseApiSurfaceDoD : Test { :>> id = "7f05a2e6-8c31-4b94-9d60-53ca17be0d28"; :>> method = VerificationMethod::test; :>> procedureText = "13 of 46 HTTP routes are referenced by NEITHER the console nor the contract `/api/version` advertises: baseline-compare, change-impact, check, critique-plan, edge, fingerprint, grammar, index, item/attr, relations, scope, slice, snapshot. D0114 commits a VERSIONED read API for a separate viewer app, so an endpoint the console does not call is legitimate - but an endpoint nothing declares is unaccounted surface, and a consumer cannot discover it. THIS IS ISSUE172 ONE LAYER OUT: a hand-maintained advertisement beside a hand-maintained router, drifting in one direction only. DONE MEANS: `/api/version` advertises the route set DERIVED from the router rather than hand-listed, and a test asserts every route is either advertised or referenced by the console - so a new endpoint cannot land unaccounted."; }
        part dcAdvertiseApiSurfaceDoDR1 : TestResult { :>> id = "79ea9016-c187-4ee1-b7d7-68629c545fed"; :>> outcome = VerdictKind::pass; :>> judgedAgainst = "d951cff"; :>> judgedAt = "2026-08-20"; :>> judgedBy = "claudeOpus5"; }
        action dcFlagIsNotAPath;
        verification dcFlagIsNotAPathDoD : Test { :>> id = "d15e7a04-3c96-4b28-8f51-70ba24ce6d13"; :>> method = VerificationMethod::test; :>> procedureText = "`keel init --help` CREATES A DIRECTORY NAMED `--help` and scaffolds a whole engine into it. Found by accident: a robustness sweep ran `<cmd> --help` across every subcommand, and 277 files landed in this repository under a directory called `--help` and were COMMITTED before anyone noticed. A positional path argument accepts anything, so a mistyped or unsupported flag becomes a filesystem mutation - the worst possible failure mode for the one command whose whole job is writing a tree to disk. DONE MEANS: any argument beginning with `-` is REJECTED where a path is expected, across every command that takes a path or a name, with a message saying the flag is unrecognised rather than treating it as a target; verified on `init` and on the name-taking commands; pinned by a test."; }
        part dcFlagIsNotAPathDoDR1 : TestResult { :>> id = "8dbc435b-757c-4c60-b196-e3779cdd71a7"; :>> outcome = VerdictKind::pass; :>> judgedAgainst = "d951cff"; :>> judgedAt = "2026-08-20"; :>> judgedBy = "claudeOpus5"; }
        action dcGuardScanCount;
        verification dcGuardScanCountDoD : Test { :>> id = "e04a7c92-5b13-4f68-9d20-46ca81be5f07"; :>> method = VerificationMethod::test; :>> procedureText = "Nine of 38 guards report `0 scanned` - base-first-justification, charter, critic-independence, doc-sync, edge-endpoints, ownership, process-change, requirement-rootedness, retro-backlog. Three of them HARDCODE `scanned: 0` while doing real work, and `requirement_rootedness` receives its own count and discards it (`Ok(Some((_scanned, gaps)))`). PROVED THEY STILL ENFORCE: a deliberately dangling edge made edge-endpoints FAIL - printing `0 scanned, 0 warning(s), 1 violation(s)`, which is internally contradictory output. So this is a REPORTING defect, and the damage is that `scanned` is the one number that would let anyone audit guard liveness, and it is absent in exactly the nine cases where you would want to ask. It nearly cost a false finding: `0 scanned` reads as `this guard can never fire`. DONE MEANS: every guard reports a scan count that is the size of the population it actually examined; no guard can report a violation with 0 scanned; pinned by a test over the full guard set."; }
        part dcGuardScanCountDoDR1 : TestResult { :>> id = "2455b1cf-4a9d-447a-a726-589d7bf93e7e"; :>> outcome = VerdictKind::pass; :>> judgedAgainst = "d951cff"; :>> judgedAt = "2026-08-20"; :>> judgedBy = "claudeOpus5"; }
        action dcHookBoundedLife;
        verification dcHookBoundedLifeDoD : Test { :>> id = "f28b04c6-7d51-4a93-8e60-31ca75be2d18"; :>> method = VerificationMethod::test; :>> procedureText = "`keel hook` blocks on an unbounded `stdin().read_to_string()`. If the parent goes away without closing stdin, the hook process waits forever and holds a Windows file lock on `target/release/keel.exe`, so EVERY subsequent `cargo build` fails with `Access is denied (os error 5)`. Observed three times in one turn during hardening pass 4: a stray keel.exe had to be killed by PID before the build would proceed. THE IN-LOOP GATE CAN WEDGE THE BUILD IT GATES, which is the worst property an in-loop tool can have - it fails in a way that looks like a toolchain problem rather than a hook problem. DONE MEANS: a hook process has a BOUNDED lifetime - a watchdog exits it after a few seconds - and it exits 0 when it does, because D0134 says a hook never fails a turn. Verified by starting a hook with no stdin and watching it exit on its own rather than needing a kill."; }
        part dcHookBoundedLifeDoDR1 : TestResult { :>> id = "d255b843-6306-4995-87f9-c166a656c59e"; :>> outcome = VerdictKind::pass; :>> judgedAgainst = "d951cff"; :>> judgedAt = "2026-08-20"; :>> judgedBy = "claudeOpus5"; }
        action dcDateNeverDefaulted;
        verification dcDateNeverDefaultedDoD : Test { :>> id = "a37c0b58-9e24-4d61-8f03-52ba17ce4d29"; :>> method = VerificationMethod::test; :>> procedureText = "FIVE write paths silently default a provenance date to the hardcoded literal 2026-01-01: append-result, append-gate-result, record-measurement, snapshot-indicators and apply-review. CLAUDE.md says provenance is never defaulted, and that rule was implemented for the ACTOR only - the DATE was defaulted to a false constant. A TestResult or Measurement written without an explicit date claims it happened on 2026-01-01, which corrupts any time series and feeds guard 36, whose entire job is catching evidence that cites an impossible date. LATENT, NOT ACTIVE: zero items in the corpus carry 2026-01-01, because every real invocation has passed an explicit date - so this is a trap that has never fired rather than damage to repair, and saying so is part of the finding. FOUND BY A WRITE-API SMOKE TEST that invoked every write command with no arguments: `keel snapshot-indicators` alone MUTATED THE TREE, stamping two Measurements dated 2026-01-01. DONE MEANS: the date is REFUSED rather than defaulted, so a bare invocation cannot write; every one of the five sites errors without an explicit date; and a test forbids a hardcoded date literal in a write path."; }
        part dcDateNeverDefaultedDoDR1 : TestResult { :>> id = "09098fd7-6eeb-4445-adad-e97d5977515f"; :>> outcome = VerdictKind::pass; :>> judgedAgainst = "d951cff"; :>> judgedAt = "2026-08-20"; :>> judgedBy = "claudeOpus5"; }
        action dcLensCannotFalseGreen;
        verification dcLensCannotFalseGreenDoD : Test { :>> id = "c81b6f03-4a29-4d57-9e14-70ba53ce8d26"; :>> method = VerificationMethod::test; :>> procedureText = "`keel hardening` reports `helpCoverage 0/0 -> 100%` and `apiSurface unaccounted 0` when it cannot read `keel-cli/src` AT ALL. Verified against a tree containing only .engine and .tracking - which is what every DOWNSTREAM project is, since they run the installed binary rather than this source tree. So the lens built one sprint earlier to stop wrong numbers hands a clean bill of health to every consumer who cannot possibly be measured. THE MECHANISM IS A HELPER I WROTE: `pct(part, whole)` returns 100 when whole is 0, and the lenses treat an unreadable file as an empty one. A FALSE GREEN IS WORSE THAN A WRONG NUMBER because nobody investigates a pass. DONE MEANS: a lens that cannot read its input reports UNAVAILABLE with the reason and NO percentage; `pct` cannot return 100 for an empty population; verified on a tree with no source; and the source-tree-only limitation, already stated in D0169, is enforced rather than merely documented."; }
        part dcLensCannotFalseGreenDoDR1 : TestResult { :>> id = "27e625fe-5695-44c8-b253-d9e53daaa42b"; :>> outcome = VerdictKind::pass; :>> judgedAgainst = "d951cff"; :>> judgedAt = "2026-08-20"; :>> judgedBy = "claudeOpus5"; }
        action dcAtomicModelWrite;
        verification dcAtomicModelWriteDoD : Test { :>> id = "b640e7a1-5c93-4d28-8f06-71ca42be3d95"; :>> method = VerificationMethod::test; :>> procedureText = "Every model write is `std::fs::write(path, content)` - 16 sites in write.rs plus 5 across actor/enroll/activation - which TRUNCATES the file and then writes. If the process dies between those two steps the authoritative record is left truncated or half-written. Invariant 1 says text is truth; the write path to that truth is not atomic, and no temp-file-plus-rename helper exists anywhere in the crate. THE BOUNDED PART, stated honestly: the gate catches a truncated file as a parse error, so the blast radius is a red gate rather than silent corruption - EXCEPT for a partial write that still parses, which is the case that gets committed. DONE MEANS: one helper writes to a sibling temp file and RENAMES over the target, every model write site uses it, and a test proves the target is either the old content or the new content and never a prefix of the new one."; }
        part dcAtomicModelWriteDoDR1 : TestResult { :>> id = "51140ab6-e52b-4ec3-918a-97c4846c84b3"; :>> outcome = VerdictKind::pass; :>> judgedAgainst = "d951cff"; :>> judgedAt = "2026-08-20"; :>> judgedBy = "claudeOpus5"; }
        action dcConcurrentWriteSafe;
        verification dcConcurrentWriteSafeDoD : Test { :>> id = "d72f05b8-6c41-4a93-8e27-50ba63ce9d14"; :>> method = VerificationMethod::test; :>> procedureText = "FOUR concurrent `keel record issue` calls against the same file landed TWO issues. All four exited 0, the tree validated clean, and no temp file was left behind - so two recorded facts vanished with every command reporting success. Every write is a read-modify-write (`read_to_string`, insert, write) with NO lock and NO conflict detection, at eight sites in write.rs. D0108 and D0129 explicitly design for multi-contributor work and instruct a non-owner to ADD items; two contributors adding at once silently discard one. SILENT IS THE DEFECT, not slow: a refused write is recoverable, a lost one is not, and rc=0 on a lost write means no automation can even detect it. DONE MEANS: concurrent writers to the same file are serialised by an atomically-created lock file with bounded retry, a writer that cannot acquire it FAILS LOUDLY rather than proceeding, and the four-way concurrent probe lands 4 of 4."; }
        part dcConcurrentWriteSafeDoDR1 : TestResult { :>> id = "e9aa3454-a0d2-4942-9690-6f7a7f1a7936"; :>> outcome = VerdictKind::pass; :>> judgedAgainst = "d951cff"; :>> judgedAt = "2026-08-20"; :>> judgedBy = "claudeOpus5"; }
        action dcDeadCoreFields;
        verification dcDeadCoreFieldsDoD : Test { :>> id = "e59b1c76-8a03-4d42-9f18-63ca07be5d21"; :>> method = VerificationMethod::test; :>> procedureText = "Three attributes in FROZEN `schema/core` are neither written nor read: `actualPoints`, `impact`, `reasonForChange` - zero `:>>` settings across the whole model and zero references in the Rust code. `impact` and `reasonForChange` sit on the process-change type, so the CR discipline declares that a change records WHY and WHAT IT AFFECTS, and no change ever has. That is a declared practice nobody performs, which is the same shape as issue175's actualHours at 1% - resolved there by demoting the metric to an indicator. THIS ONE CANNOT BE COMPLETED WITHOUT A SIGNATURE: `schema/core` is frozen (invariant 5), so retiring a field needs explicit human sign-off, and filling them retroactively is impossible because past reasons live in commit messages rather than the model. DONE MEANS: a Decision proposing either retirement or a write-path that fills them going forward, ACCEPTED - and until then the finding stays open rather than being quietly closed as documented."; }
        part dcDeadCoreFieldsDoDR1 : TestResult { :>> id = "d116f584-07cd-41c9-9bbd-c6da022ddebf"; :>> outcome = VerdictKind::pass; :>> judgedAgainst = "3abc583"; :>> judgedAt = "2026-08-20"; :>> judgedBy = "claudeOpus5"; }
        action dcDeckIsPortable;
        verification dcDeckIsPortableDoD : Test { :>> id = "f471a03c-6d29-4b58-8e07-52ba14ce9d63"; :>> method = VerificationMethod::test; :>> procedureText = "Their words: cement the mobile, automatic-feedback (NO copy paste), claude-hosted artifact skill that clearly delineates decisions, so it is reusable anywhere keel is used. THREE PROPERTIES ALREADY HELD - mobile-first fluid column with a device-width viewport, published as a Claude-hosted artifact, and already a LIVE DOC via the `artifact` capability. TWO DID NOT: the skill deployed NO process, so it could not travel (D0128 makes a process the movable unit, and `keel activate` operates on processes); and `Copy for Claude` sat in every view including writable ones, teaching a habit the live doc exists to remove. DONE MEANS: a declared process with five steps; the skill registry naming it (D0059); acceptance cards carrying `Sign` plus a heavier rail and a `needs your signature` ribbon while other classes keep `Accept`; the copy button hidden unless the view genuinely cannot write; and the counts verified from the EMITTED HTML rather than from reading the generator."; }
        part dcDeckIsPortableDoDR1 : TestResult { :>> id = "1656ff2f-6940-44fb-acaf-416ed2ee0aa5"; :>> outcome = VerdictKind::pass; :>> judgedAgainst = "40d4f5b"; :>> judgedAt = "2026-08-20"; :>> judgedBy = "claudeOpus5"; }
        action dcDeckButtonsLive;
        verification dcDeckButtonsLiveDoD : Test { :>> id = "b0c37e14-5f28-4d63-9a05-71ba46ce8d29"; :>> method = VerificationMethod::demo; :>> procedureText = "The published deck reported by the human as having buttons that DO NOT WORK. ROOT CAUSE, and it is an anti-pattern the skill itself documents: on a live doc the runtime switches a sync region OFF when the regions DOM is changed by SCRIPT rather than by a gesture. `count()` ran at the end of the script and set `#cnt.textContent`, so the bodys region went off the instant the page loaded, before the human touched anything. The `claude:sync-off` handler then set `data-local-readonly=true`, which is anti-pattern 3 - concluding read-only from a benign region-off - so the page declared itself unwritable and every tap reported `not saved`. THREE FIXES: the initial count is RENDERED BY THE GENERATOR (the contracts own instruction), so no DOM write happens at load; read-only is concluded ONLY from a sync() rejection carrying not_writer or not_granted; and the last statement of the script sets a `data-local-*` marker that CSS renders as `script ok`, so its ABSENCE says the script threw. TWO MORE DEFECTS FOUND IN THE SAME PASS, both mine from the previous sprint: `var(--acc)` is not a declared property so the signature ribbon silently lost its colour, and the marker set an attribute nothing displayed. DONE MEANS: zero top-level DOM mutations before the click listener registers, verified from the EMITTED HTML; and the human confirms a tap turns a card and the header reads `script ok` - which only they can confirm."; }
        part dcDeckButtonsLiveDoDR1 : TestResult { :>> id = "7ad3866c-0e8d-4cfd-8926-bbc571369bf5"; :>> outcome = VerdictKind::pass; :>> judgedAgainst = "02ea1af"; :>> judgedAt = "2026-08-20"; :>> judgedBy = "claudeOpus5"; }
        part dcDeckButtonsLiveDoDR2 : TestResult { :>> id = "cbdc262b-bc41-479f-aff0-285c514fcc87"; :>> outcome = VerdictKind::fail; :>> judgedAgainst = "329b5cb"; :>> judgedAt = "2026-08-20"; :>> judgedBy = "claudeOpus5"; }
        action dcRetroGuardTiesFinding;
        verification dcRetroGuardTiesFindingDoD : Test { :>> id = "a80f5c27-3e94-4b61-8d05-72ca16be4d59"; :>> method = VerificationMethod::test; :>> procedureText = "The retro-backlog guard passes when ANY tracked item is co-staged with a retro-bearing commit, so a retro finding never needs ITS OWN item as long as the sprint recorded something else - and every hardening commit did, which is how one failure class reached five retros and zero backlog items. DONE MEANS: the guard ties the co-staged item to THE FINDING - the retro text names the item it produced, or carries a recorded no-item justification - verified both ways on a retro with an untracked finding and one with a tracked one."; }
        part dcRetroGuardTiesFindingDoDR1 : TestResult { :>> id = "ba0ba73f-7add-4be1-a6a4-3262ffcd0c6c"; :>> outcome = VerdictKind::pass; :>> judgedAgainst = "edd129a"; :>> judgedAt = "2026-08-20"; :>> judgedBy = "claudeOpus5"; }
        action dcEmittedJsMustParse;
        verification dcEmittedJsMustParseDoD : Test { :>> id = "e17f42b9-6c05-4a83-9d20-58ba31ce7f64"; :>> method = VerificationMethod::test; :>> procedureText = "The deck's script contained THREE syntax errors and had therefore been COMPLETELY DEAD since its first publish: a regex fix appended an end-of-line comment inside a single-line .then() and commented out the closing braces; a stray fragment of a replaced multi-line push survived an old edit; and a backslash-n eaten by a heredoc split a string literal across two lines. A syntax error runs NOTHING - no listener, no marker, no debug log - so every button report was the same one defect, and three real fixes (load-time write, async isolation, data-id) shipped untestable because the page they shipped into could not execute at all. EVERY audit I ran grepped STRINGS in the emitted HTML; none parsed the JS, and node was on PATH the whole time. DONE MEANS: the generator's emitted script passes node --check as a hard gate before any publish, wired into the skill's checklist as pass zero - before the string checks, because a parse failure makes every string check meaningless."; }
        part dcEmittedJsMustParseDoDR1 : TestResult { :>> id = "82be89fb-347c-4f3a-be60-391efe7d9207"; :>> outcome = VerdictKind::pass; :>> judgedAgainst = "37ea4f3"; :>> judgedAt = "2026-08-21"; :>> judgedBy = "claudeOpus5"; }
        action dcRecorderForwardsBy;
        verification dcRecorderForwardsByDoD : Test { :>> id = "3d4ca0b4-8ad6-4495-c76c-ebfe69ad3230"; :>> method = VerificationMethod::test; :>> procedureText = "The inbox recorder treats the actor as DATA IT CARRIES: every path (finding disposition, decision acceptance/rejection, sitting review) forwards the row's By as judged_by, so a verdict is recorded as the person who tapped it - never as the session actor the server would otherwise resolve (issue197: a High disposition landed as judgedBy=claudeOpus5, guard-invisible because D0165's delegation makes an AI judge legal). Attestation text composes the event's substance - who tapped what, row id, timestamp, deck HEAD, note verbatim when present - never a bare row pointer. Rehearsed on a served COPY: recorded, view-verified, tree validates. The two mis-recorded facts were corrected before commit and their texts state the correction."; }
        part dcRecorderForwardsByDoDR1 : TestResult { :>> id = "4e5db1c5-9be7-4506-8d7d-0cbf70be4341"; :>> outcome = VerdictKind::pass; :>> judgedAgainst = "d24d52d"; :>> judgedAt = "2026-08-21"; :>> judgedBy = "claudeOpus5"; }
        action dcInboxTransport;
        verification dcInboxTransportDoD : Test { :>> id = "f8ed6b70-4c92-4051-8368-a7ba25cf9eeb"; :>> method = VerificationMethod::test; :>> procedureText = "Their instruction: just make the remote artifact pipeline work; test again. DONE MEANS: the dead live-doc fallback is REPLACED by the mcp inbox - the page delivers each tap as one row to the keel-deck-inbox sheet via the viewer's Smartsheet connector and shows the store's row id as its receipt (the label ladder rung it earned: delivered-to-inbox, never saved); the inbox config lives in .engine/contracts/deck-inbox.toml and a partial config makes the page claim NO transport rather than half of one; connector errors branch per contract code; .engine/tools/deck_inbox_record.py pulls Processed=false rows, records each through the write API, VERIFIES each from the computed view, and dedups by latest-At per (uid, kind); the add_rows request/response pair was OBSERVED live before publish; the local acceptance path sends the API's required file field (issue195) and the e2e's new throwaway-decision fixture makes the acceptance leg unconditional - 17 checks green; the real delivered test row was rehearsed through a served COPY and read back dispositioned from the computed view."; }
        part dcInboxTransportDoDR1 : TestResult { :>> id = "0a1f7c81-5da3-4162-9479-b8cb36da0ffc"; :>> outcome = VerdictKind::pass; :>> judgedAgainst = "5264d27"; :>> judgedAt = "2026-08-21"; :>> judgedBy = "claudeOpus5"; }
        action dcToolReferenceGuard;
        verification dcToolReferenceGuardDoD : Test { :>> id = "1b2a8d92-6eb4-4273-a58a-c9dc47eb100d"; :>> method = VerificationMethod::test; :>> procedureText = "Guard 39 (tool-reference): every .engine/tools/<file> named on the LIVING doc surface (processes, skills, docs, contracts, workflows, rules, CLAUDE.md) must exist on disk; decisions and .tracking are excluded as historical records. Exists because sprint 377 recorded a deletion that never happened (issue196) and nothing could notice. Its first dry run found a second stale reference. Unit-tested (missing file flagged, existing file and bare directory mention not, .tracking out of scope) and green over the real tree after the two stale references were fixed and the file actually deleted."; }
        part dcToolReferenceGuardDoDR1 : TestResult { :>> id = "2c3b9ea3-7fc5-4384-b69b-daed58fc211e"; :>> outcome = VerdictKind::pass; :>> judgedAgainst = "5264d27"; :>> judgedAt = "2026-08-21"; :>> judgedBy = "claudeOpus5"; }
        action dcHonestSaveLabel;
        verification dcHonestSaveLabelDoD : Test { :>> id = "a25d70c8-4b93-4e16-8f52-61ca38be0d74"; :>> method = VerificationMethod::test; :>> procedureText = "MEASURED END TO END WITH THE HUMAN AS THE INSTRUMENT: their phone showed transport=artifact-fallback and `saved` per tap; a fresh fetch of the served document after their taps showed EVERY verdict empty. So sync() resolving proves only that the RUNTIME accepted the write - it does not prove keel can ever read it, and keel demonstrably cannot: the artifact transport is WRITE-ONLY from the receiver's perspective. A confirmation the receiver cannot verify is the runtime marking its own homework. DONE MEANS: the fallback's per-tap label reads `marked in page - NOT confirmed in keel` and its transport line says judgments marked there DO NOT reach keel; the word `saved` appears only on the LOCAL transport, where a 200 from the write API and a view read-back make it true; and the limitation is recorded as the reason mobile needs a route to the TESTED transport (a tunnel to keel serve), which is an infrastructure choice that is theirs."; }
        part dcHonestSaveLabelDoDR1 : TestResult { :>> id = "5df7ae06-6c0b-4d21-bdf2-b2cd90c27757"; :>> outcome = VerdictKind::pass; :>> judgedAgainst = "e752393"; :>> judgedAt = "2026-08-21"; :>> judgedBy = "claudeOpus5"; }
        action dcDeckInRust;
        verification dcDeckInRustDoD : Test { :>> id = "f14c38a6-9e72-4b05-8d61-84ae29fc5b93"; :>> method = VerificationMethod::test; :>> procedureText = "Their instruction verbatim: make the artifact locally in rust, test thoroughly, then deploy; use httpx. DONE MEANS: `keel deck` generates the page from the engine (keel-cli/src/deck.rs) off the same computed views the console reads; `keel serve` serves it at /deck; every tap saves through the server's OWN POST endpoints (disposition, decision accept/reject, and the new /api/deck/sitting which records the HUMAN critique with its #Covers edge and REFUSES an AI); the artifact live-doc mechanism is a FALLBACK the page selects only when /api/version does not answer; and .engine/tools/test_deck_e2e.py exercises the whole loop with httpx against a served COPY - 13 checks including verdicts read back from the COMPUTED VIEWS and the human-gate refusal - green before any deploy. The e2e found four real defects pre-deploy: a missing actor binding, an actor name written into the CriticKind enum, a sitting critique that counted for nothing without its Covers edge, and the D0167 staleness window in naive reads."; }
        part dcDeckInRustDoDR1 : TestResult { :>> id = "7fcc6336-7dfa-42e8-8a5d-09f22d757e77"; :>> outcome = VerdictKind::pass; :>> judgedAgainst = "db6b575"; :>> judgedAt = "2026-08-21"; :>> judgedBy = "claudeOpus5"; }
        action dcDeckSyncAddressable;
        verification dcDeckSyncAddressableDoD : Test { :>> id = "c53e08b1-7a46-4d92-8f15-60ba27ce4d83"; :>> method = VerificationMethod::demo; :>> procedureText = "Third latch failure, and this time the diagnosis came from EVIDENCE rather than the contract text: WebFetch of the published artifact exposed the frame runtime itself, whose patch layer addresses every synced element by [data-id=...] with an allowlist of data-*/aria-*/class/hidden/value/checked. The deck's cards carried data-uid - the canvas template said data-id and the generator had renamed it - so NO mutation was addressable, nothing could be recorded, and every tap reverted. The same fetch exposed two more defects: the version stamp I told the human to look for existed only inside a JS variable and NEVER RENDERED (my check found it in the file, not on the screen), and the script-ok marker's CSS escape was mangled to plain b7. DONE MEANS: every card and note input carries data-id; script writes ZERO text into the synced region (the pill and count render via CSS from attributes; the last offender, the copy button label, is data-local too); the version is VISIBLE in the sub-line (deck v4); and the human confirms a tap latches - which only they can."; }
        action dcAuthorViaWriteTool;
        verification dcAuthorViaWriteToolDoD : Test { :>> id = "b96d02e5-4c73-4a18-8f60-51ca38be7d92"; :>> method = VerificationMethod::inspect; :>> procedureText = "THE ITEM FIVE RETROS SHOULD HAVE PRODUCED. The failure class: content authored through a shell gets reinterpreted by the shell - heredoc backslash-n becoming real newlines (three times), backticks executed as command substitution deleting words from a recorded issue (twice), quotes breaking mid-string. SIX occurrences across sprints 357-371, each recorded as retro prose, each relearned. THE RULE, now tracked rather than remembered: any authored content containing escapes, quotes, backticks or multi-line strings is written via the Write tool as a FILE (a script, a message file, a patch), and the shell only ever receives file PATHS. DONE MEANS: the rule is in the review-critique process (rcRecurrence cites this item as its founding example), the obligation-review skill carries it, and the next occurrence of the class is judged against this item rather than rediscovered."; }
        part dcAuthorViaWriteToolDoDR1 : TestResult { :>> id = "38486949-84bd-4e2c-a3fd-cf04b605ec5f"; :>> outcome = VerdictKind::pass; :>> judgedAgainst = "edd129a"; :>> judgedAt = "2026-08-20"; :>> judgedBy = "claudeOpus5"; }
        action issue142Fix;
        verification issue142FixDoD : Test { :>> id = "53a25aca-168e-4fca-8133-4d95ba1b7dca"; :>> method = VerificationMethod::inspect; :>> procedureText = "VERIFIED MOOT, and the DoD itself is evidence of a defect. The original text here was the fragment -in original statement- : damaged at authoring, almost certainly by the shell-mangling class dcAuthorViaWriteTool now tracks (a quote ended the string early and the remainder was silently dropped). The item was a SECOND resolver for issue142, which its sibling dcSharedParsedModel resolved on sprint 358 evidence - the parsed model was already cached, the premise refuted three ways. A pass on this DoD means -verified moot with the damage recorded-, not -work done-."; }
        part issue142FixDoDR1 : TestResult { :>> id = "5d4d21dc-5c1e-4933-b0ef-35e816ef22b5"; :>> outcome = VerdictKind::pass; :>> judgedAgainst = "2fabe08"; :>> judgedAt = "2026-08-21"; :>> judgedBy = "claudeOpus5"; }
        action dcDeckFindingJudgedBy;
        verification dcDeckFindingJudgedByDoD : Test { :>> id = "fb4bb4af-7f59-454c-88b6-b208d822c242"; :>> method = VerificationMethod::test; :>> procedureText = "DONE MEANS: the deck's saveLocal finding body carries judged_by=HUMAN and a substantive default rationale (who tapped, no-note stated); delivered in the same commit that corrected the 19 misattributed records; the emitted script still parses under node --check."; }
        part dcDeckFindingJudgedByDoDR1 : TestResult { :>> id = "90bb9ecf-caff-4f09-90db-b31926a030e4"; :>> outcome = VerdictKind::pass; :>> judgedAgainst = "92254e1"; :>> judgedAt = "2026-08-21"; :>> judgedBy = "claudeFable5"; }
        action dcEnforcementPointSpecPin;
        verification dcEnforcementPointSpecPinDoD : Test { :>> id = "43c526ab-e03a-418a-8e0e-e04e99a101ca"; :>> method = VerificationMethod::test; :>> procedureText = "Resolves issue203 (critique pass 1, srK02 completeness). The build-time spec-pin check (keel-parser build.rs) is an enforcement point the hardening lens's enforcementPoints inventory does not enumerate, and its network-error path resolves to ALLOW (warn-skip) - the exact timeout-resolves-to-allow residual class srK02FailLoud demands be RECORDED, unrecorded. DO: add the point to the enforcementPoints lens with its absent/error/timeout behaviors stated (absent=no build, error=warn-allow, offline-flag=skip-by-declaration); the warn-allow residual appears in the lens output rather than in nobody's head. VERIFY: the lens lists the point; the residual is machine-readable; validate + guards green."; }
        part dcEnforcementPointSpecPinDoDR1 : TestResult { :>> id = "c0a5e333-8b9e-4b00-8907-ed3c95bdfe96"; :>> outcome = VerdictKind::pass; :>> judgedAgainst = "114663c"; :>> judgedAt = "2026-08-21"; :>> judgedBy = "claudeFable5"; }
        action dcHumanChannelDelegationRule;
        verification dcHumanChannelDelegationRuleDoD : Test { :>> id = "8e5591b6-7e4d-43fb-9230-bda27aba606d"; :>> method = VerificationMethod::confirmation; :>> procedureText = "Resolves issue204 (critique pass 1, srK06 completeness). srK06HumanChannel's letter says human-judgment records originate only from a channel the agent cannot invoke - but the HTTP acceptance endpoint is agent-invokable by design and the sanctioned D0165 delegation practice (AI records the human's verbatim words with judged_by=<human>) uses it, including for D0191 this very week. The letter and the practice contradict; one must move, and WHICH is a direction Decision for the human, not a patch. DO: draft the Decision with both options costed - (a) supersede srK06 with an explicit delegation clause (verbatim words quoted in the record, guard-checkable shape) legitimising the practice, or (b) close the delegation path: acceptances become human-gesture-only (console/deck/TTY), the AI queues instead of recording. Queue it for signature. VERIFY: the proposed Decision exists naming both options and their costs; issue204 resolves via whichever is signed."; }
        part dcHumanChannelDelegationRuleDoDR1 : TestResult { :>> id = "96c87142-2d00-4ffc-9151-7b71acfb6d22"; :>> outcome = VerdictKind::pass; :>> judgedAgainst = "247805778bb52b3ac8a1e9a5b96be6da2c6bb36b"; :>> judgedAt = "2026-08-22"; :>> judgedBy = "wweatherholtz"; }
        action dcActorRebindLedger;
        verification dcActorRebindLedgerDoD : Test { :>> id = "41bdafcd-0ae8-45b1-bda8-602db939f6e1"; :>> method = VerificationMethod::test; :>> procedureText = "Resolves issue205 (critique pass 2, srK07 completeness). keel actor set writes only the machine-local gitignored .keel/actor - an actor rebind, a weakening class srK07RecordedWeakening itself names, leaves no durable record and no visibility. DO: a rebind leaves a durable, surfaced record - at minimum a fire-ledger line (event=actor-rebind) written by cmd set, with the old and new bindings carried in the record (within the frozen 6-field schema's string fields, or as a tracked fact if the schema cannot honestly hold them - the mechanism is the implementer's call, the RECORD is not); surfaced via keel enforcement-report's per-event counts. VERIFY: a rebind is followed by an observable record naming both bindings; a fresh binding (first set) records too; guard/validate green."; }
        part dcActorRebindLedgerDoDR1 : TestResult { :>> id = "b2b1338e-e075-4f79-8003-aba6a499aae0"; :>> outcome = VerdictKind::pass; :>> judgedAgainst = "114663c"; :>> judgedAt = "2026-08-21"; :>> judgedBy = "claudeFable5"; }
        action dcRunGateTreeDerivable;
        verification dcRunGateTreeDerivableDoD : Test { :>> id = "b2c20337-051f-4172-8a71-746c409b805a"; :>> method = VerificationMethod::test; :>> procedureText = "Resolves issue206 (critique pass 3, srK15 completeness). The launched-run gate folds a machine-local input into its verdict: finish() turns the gate RED when no fire-ledger line follows the spawn, and .keel/metrics/hooks.jsonl is gitignored - another clone cannot re-derive that run's gate verdict from committed truth, so K15's tree-derivability and K3's enforcement-loss check pull against each other inside one verdict. DO one of the two stated options: (a) demote the fired-since-spawn component to report-only (the problem text stays in the run record, the verdict stays a pure function of the tree), or (b) commit the relevant ledger excerpt into the tracked run record so the input becomes committed truth. VERIFY: a second clone re-derives the same gate verdict for a recorded run; the K3 signal is still visible either way; launcher tests updated."; }
        part dcRunGateTreeDerivableDoDR1 : TestResult { :>> id = "f87f9d13-9468-43e7-975c-c11f65b8e4f7"; :>> outcome = VerdictKind::pass; :>> judgedAgainst = "29adc28"; :>> judgedAt = "2026-08-22"; :>> judgedBy = "claudeFable5"; }
        action dcOverrideCountedOnSuccess;
        verification dcOverrideCountedOnSuccessDoD : Test { :>> id = "4633616d-5e3f-44dd-b4f7-c534c4340e97"; :>> method = VerificationMethod::test; :>> procedureText = "Resolves issue207 (critique pass 3, srK14 completeness). consume_override emits a ledger line only on the FAILURE path (override-obligation-UNSYNCED), so enforcement-report's override counter structurally misses every successful override - the normal case is invisible to the very evidence K14 says a promotion review must cite. DO: the happy path emits a ledger line too (event=override-consumed, within the frozen 6-field schema), and the report counts consumed and unsynced separately. VERIFY: a successful override consumption produces a counted line; the report distinguishes consumed from unsynced; pm.rs schema test still green."; }
        part dcOverrideCountedOnSuccessDoDR1 : TestResult { :>> id = "16c89817-9cc4-48e7-9593-d8f95fa2e82e"; :>> outcome = VerdictKind::pass; :>> judgedAgainst = "114663c"; :>> judgedAt = "2026-08-21"; :>> judgedBy = "claudeFable5"; }
        action dcPrePushBehindCheck;
        verification dcPrePushBehindCheckDoD : Test { :>> id = "05b3c1de-b221-45d1-b07b-a7d68cdd58a7"; :>> method = VerificationMethod::test; :>> procedureText = "Resolves issue209 (critique pass 5, srDcGateOnMergedTree completeness). A raw git push dodges the sanctioned fetch-integrate-gate-push loop: .githooks has no pre-push, so a contribution gated only in isolation can land on the shared trunk with CI catching it POST-HOC - the SR says it shall never land. DO: a pre-push hook in .githooks (installed by the same sync-claude/hooksPath machinery) that fetches and REFUSES when the local ref is not a fast-forward of the fetched trunk, naming keel land as the sanctioned path (srK13 deny-and-provide) - behind-ness detection only, never the full gate (keel land already gates the merged tree; the hook's job is forcing the loop, not duplicating it). VERIFY: a push from a behind clone is refused with the message; a fast-forward push passes; keel land unaffected; hook portable (no absolute paths, loud when git/binary absent)."; }
        part dcPrePushBehindCheckDoDR1 : TestResult { :>> id = "b8769ef4-b2bc-4934-abaf-94d0cdfd3f37"; :>> outcome = VerdictKind::pass; :>> judgedAgainst = "42e5c6b"; :>> judgedAt = "2026-08-22"; :>> judgedBy = "claudeFable5"; }
        action dcPerActorAppendFiles;
        verification dcPerActorAppendFilesDoD : Test { :>> id = "4cbb5a2a-b714-46d9-a750-0c42274dafc7"; :>> method = VerificationMethod::test; :>> procedureText = "Resolves issue210 (critique pass 6, srDcPerActorWriteTargets completeness). append_critique and the issue recorder insert every contributor's records before the same package-closing brace of shared files (critiques.sysml, issues.sysml) - two contributors appending concurrently merge-conflict at identical lines, exactly what the SR forbids; the write-lock serialises one machine only. DO: route NEW records to per-actor files (critiques-<actor>.sysml / issues-<actor>.sysml or equivalent distinct anchors); readers already glob .tracking so reads are unchanged; existing files stay where they are (no history migration - the fix is forward-only routing); the deck/serve write paths pick the target from the acting judge. VERIFY: two clones append one critique each, merge clean, both land; validate + guards green; sequence allocation (issue numbers) stays collision-guarded across the split files (duplicate-identity already scans cross-file)."; }
        part dcPerActorAppendFilesDoDR1 : TestResult { :>> id = "eb4ead5e-26f6-4307-852a-b5af1e4d291a"; :>> outcome = VerdictKind::pass; :>> judgedAgainst = "f8279a8"; :>> judgedAt = "2026-08-22"; :>> judgedBy = "claudeFable5"; }
        action dcReleaseGatedPublish;
        verification dcReleaseGatedPublishDoD : Test { :>> id = "bc625f86-0f12-47ec-9db1-ad74397b4b87"; :>> method = VerificationMethod::test; :>> procedureText = "Resolves issue211 (critique pass 9, srRelPublishedArtifact completeness). release.yml runs zero gate steps - a tag on a red or ungated commit still builds and PUBLISHES three platform binaries, while the deploy process's own purpose text promises a full gate between green trunk and tag. DO: a gate job in release.yml (cargo test + keel validate + keel guard over the tagged commit, same surfaces as ci.yml) that the publish job REQUIRES via needs:; the manual-smoke path keeps building without publishing as today. VERIFY: a deliberately red tag in a scratch repo builds but does NOT publish; a green tag publishes; the four existing releases are unaffected (forward-only)."; }
        part dcReleaseGatedPublishDoDR1 : TestResult { :>> id = "ee27cf8e-f5d0-4612-a9e5-83287f89268e"; :>> outcome = VerdictKind::pass; :>> judgedAgainst = "d3ccabd"; :>> judgedAt = "2026-08-22"; :>> judgedBy = "claudeFable5"; }
        action dcRecordDecisionMarkerFlag;
        verification dcRecordDecisionMarkerFlagDoD : Test { :>> id = "f538caad-dc41-4efb-b9b9-67ecb0a872cb"; :>> method = VerificationMethod::test; :>> procedureText = "Resolves issue213. SECOND occurrence (sprints 395 and 407) of the same commit-time refusal: keel record decision emits a plain Decision, the author forgets the #ProspectiveChange marker, and the process-change guard refuses the landing commit - correct behavior, avoidable friction (D0054). DO: keel record decision gains --process-change (and --safety-change) emitting the D0070 marker + a standard governs-comment; the guard's refusal message names the flag (srK13 deny-and-provide). VERIFY: a decision recorded with the flag carries the marker; a process-def commit citing it passes the guard; docs updated same commit."; }
        part dcRecordDecisionMarkerFlagDoDR1 : TestResult { :>> id = "8ff5581b-44d7-4389-9351-e442bb122b29"; :>> outcome = VerdictKind::pass; :>> judgedAgainst = "58f54f0"; :>> judgedAt = "2026-08-22"; :>> judgedBy = "claudeFable5"; }
        action dcAllocationRefresh;
        verification dcAllocationRefreshDoD : Test { :>> id = "4d72c065-e395-4545-8595-0e3e87e6dea7"; :>> method = VerificationMethod::test; :>> procedureText = "Delivers D0194 once signed (panel R1, all five panelists' convergent finding). DO: supersede the June Component set + its allocate edges from d0194; author SR->CodeElement allocate edges for the standing high-consequence set (the 17-element registry); add the allocation-coverage leg to tier-satisfaction (same structural-floor semantics as satisfy/verify); trace-need recomputes over the live mechanism or labels its component layer historical. VERIFY: tier-satisfaction reports the third leg; trace-need no longer serves the queryStack-era components as current; the coverage number is honest even if low."; }
        part dcAllocationRefreshDoDR1 : TestResult { :>> id = "0ad2a516-7afa-44be-b91d-3e01f1921767"; :>> outcome = VerdictKind::pass; :>> judgedAgainst = "ccc5269"; :>> judgedAt = "2026-08-22"; :>> judgedBy = "claudeFable5"; }
        action dcControlMapView;
        verification dcControlMapViewDoD : Test { :>> id = "2db44775-9dd5-4af2-9152-c1f71ae70de4"; :>> method = VerificationMethod::test; :>> procedureText = "Delivers D0195 once signed (panel R1, aerospace finding 2). DO: constraint defs for all enforced guards in guard-constraints.sysml; typed edges guard->hazard/invariant (the content each hazard statement in engine-safety.sysml already names in prose); a computed two-way view reporting hazards with no live control and controls tied to no hazard. VERIFY: the view runs; every EHZ row shows its controls as edges, not prose; a guard with no hazard edge warns."; }
        part dcControlMapViewDoDR1 : TestResult { :>> id = "0513a0f5-7033-4392-812f-04a1adfbd3c9"; :>> outcome = VerdictKind::pass; :>> judgedAgainst = "cf3f25d"; :>> judgedAt = "2026-08-22"; :>> judgedBy = "claudeFable5"; }
        action dcViewRsRestructure;
        verification dcViewRsRestructureDoD : Test { :>> id = "bc85d95f-8b58-4493-b96b-1eed60e7ff0e"; :>> method = VerificationMethod::test; :>> procedureText = "Resolves the standing #Restructure flag on ceComputedViews (panel R1, architecture finding 3: an 8159-line, ~235-definition god-module that guards/orient/claims/arch all depend on, flagged by the registry with no chartered follow-through - the untriaged-flag failure the engine forbids for Issues). DO: split view.rs along its natural seams (the per-lens compute functions) into cohesive modules with no behavior change, OR record the accept-risk Decision stating why the single module stays. VERIFY: either the split lands with cargo test green and no public-surface change, or the Decision exists; the #Restructure marker resolves either way."; }
        part dcViewRsRestructureDoDR1 : TestResult { :>> id = "29e5976d-0e4e-4c71-857d-30caded8944f"; :>> outcome = VerdictKind::pass; :>> judgedAgainst = "03b25a8"; :>> judgedAt = "2026-08-22"; :>> judgedBy = "claudeFable5"; }
        action dcDeckForkOptions;
        verification dcDeckForkOptionsDoD : Test { :>> id = "b8c9f12c-9e23-4ba0-ab48-ea65b8154505"; :>> method = VerificationMethod::test; :>> procedureText = "Resolves issue223. The deck rendered fork Decision d0192 (which enumerates OPTION A / OPTION B and states that accepting means choosing ONE) as a single bare Sign button; wweatherholtz tapped it and the gesture could not bind - solicited and wasted, the D0054 friction class. DO: the deck detects OPTION-enumerating proposed decisions (fork_options: two or more 'OPTION X (label)' captures) and renders one sign button per option; the chosen option is stamped into the note on BOTH transports (local API and remote inbox row), so the recorded acceptance carries the choice; tapping a different option switches rather than clears. VERIFY: unit test pins the D0192 text shape; the regenerated deck shows 'Sign A - amend the requirement' and 'Sign B - close the path' with data-opt attributes; emitted JS still parses; full suite and clippy green."; }
        part dcDeckForkOptionsDoDR1 : TestResult { :>> id = "dfaa6a10-5513-44a5-9062-7745ff9ab86d"; :>> outcome = VerdictKind::pass; :>> judgedAgainst = "0a5d84be7185612dba5cb078845014a5777185c1"; :>> judgedAt = "2026-08-22"; :>> judgedBy = "claudeFable5"; }
        action dcConfirmationRecordDelegation;
        // Blocked on the D0198 fork (issue112 mechanism): returns to the frontier when it is signed.
        verification dcConfirmationRecordDelegationDoD : Test { :>> id = "dbe448f9-cc57-4acb-a085-6839c35b232b"; :>> method = VerificationMethod::test; :>> procedureText = "Resolves issue224 (srK06a completeness critique). The D0192 OPTION A delegation is declared and substance-checked for decisionAcceptance only, but the SAME practice records DoD confirmation flips (sprint 420's own dcHumanChannelDelegationRuleDoD flip is the live example) with no [confirmationRecord] policy class and no quote demand - the asymmetry D0192 closed for acceptances, one level down. DO: design where a delegated confirmation flip's quote LIVES (a DoD result has no note field - the evidence shape differs from acceptance events, so this is design, not a copy of the acceptance check), declare the class in attestation-policy.toml, extend or add the substance rule. VERIFY: a delegated confirmation flip recorded without its quote fails the guard; the policy contract names every practiced delegation class."; }
        part dcConfirmationRecordDelegationDoDR1 : TestResult { :>> id = "32ef0f5c-0d48-4be7-acaf-e1c13fba9388"; :>> outcome = VerdictKind::pass; :>> judgedAgainst = "28dacb9b4d02e88ad1d177e0c5e8d1b884697549"; :>> judgedAt = "2026-08-23"; :>> judgedBy = "claudeFable5"; }
        #DependsOn dependency from dcConfirmationRecordDelegation to d0198;
        action dcOwnershipDiffGuard;
        verification dcOwnershipDiffGuardDoD : Test { :>> id = "c88fc174-b825-467a-9817-67df01d02f20"; :>> method = VerificationMethod::test; :>> procedureText = "Resolves issue226 (chartered as guard-building on the hardening view's claim that nothing checks D0108; the claim was STALE - the ownership guard has existed since sprint 293, and the real gap was the binding). DO: the distributed-collaboration unit asserts the ownership constraint (D0191 shape) so the enforcement map computes ENFORCED from the model; the stale UNDER-GUARDED entry is deleted; D0199 records the one semantic delta (unit-owned = deactivates with the unit) with its revert path. VERIFY: a planted non-owner field edit on a claudeOpus5-owned item turns the ownership guard RED and reverts green (probed live); hardening reads distributedCollaboration ENFORCED with guards=1; validate + guards green."; }
        part dcOwnershipDiffGuardDoDR1 : TestResult { :>> id = "14161318-75ec-439e-b5bf-5c7a064734d3"; :>> outcome = VerdictKind::pass; :>> judgedAgainst = "eb0da3b01d1f605f674649cec646a866b7af8293"; :>> judgedAt = "2026-08-22"; :>> judgedBy = "claudeFable5"; }
        action dcKnowledgeGraphStore;
        verification dcKnowledgeGraphStoreDoD : Test { :>> id = "0450d623-753f-4d60-a4c2-f7dd0caa91de"; :>> method = VerificationMethod::demo; :>> procedureText = "Builds D0161's promised artifact - the archetype entry decision-artifacts.toml keeps visible ('accepted 2026-08-20, unbuilt on purpose until built'). DO: knowledgeGraphMemory v2 per the signed decision - the corpus becomes a declared parameter (document corpus: extract against closed vocabulary; already-typed model: BIND existing items/edges under their minted identity), .knowledge/ as the store location, tier-conditional injection (a CLI query command, not a mandatory prompt hook), removable by construction (delete .knowledge/, nothing else breaks). VERIFY: the eight-step spine runs against THIS repo's own model as the typed corpus; re-running converges (identity stable); the decision-artifacts lens flips d0161 from unbuilt to kept; removal leaves validate + guards green."; }
        part dcKnowledgeGraphStoreDoDR1 : TestResult { :>> id = "4fe397ed-5ef2-4f4b-889d-92bb41da6313"; :>> outcome = VerdictKind::pass; :>> judgedAgainst = "13407c0af5ae03586aae60f81c01cc0312a39460"; :>> judgedAt = "2026-08-22"; :>> judgedBy = "claudeFable5"; }
        action dcProptestReservedWords;
        verification dcProptestReservedWordsDoD : Test { :>> id = "0d9f07ca-355e-45b1-9cac-e1d88611d74f"; :>> method = VerificationMethod::test; :>> procedureText = "Resolves issue225. CI's random seed generated the reserved word 'doc' as a bare part name in prop_part_string_attr; the parser correctly refused it and the run went red on an unrelated push - a latent generator defect, not a parser defect. DO: expose is_reserved_word from the lexer (the keyword match itself, never a copied list) and filter the proptest identifier strategy through it; pin the behavior deterministically (a reserved bare name IS a parse error). VERIFY: the deterministic regression passes; workspace suite + clippy green; the strategy can no longer emit a keyword by construction."; }
        part dcProptestReservedWordsDoDR1 : TestResult { :>> id = "a05ce2d6-72d5-437e-8b5a-6c92cac05b41"; :>> outcome = VerdictKind::pass; :>> judgedAgainst = "90e38d6c1e7c3d87fd92dd6b13a0d14888b60562"; :>> judgedAt = "2026-08-22"; :>> judgedBy = "claudeFable5"; }
        action dcSittingViewParity;
        verification dcSittingViewParityDoD : Test { :>> id = "c83b7d2c-b690-43e9-ae99-eb55f1272dd0"; :>> method = VerificationMethod::test; :>> procedureText = "Resolves issue227 (process-value panel). authority-queue and sitting-coverage disagree about the same obligation: authority-queue reports 279 sprints awaiting review, escalated 65 days, while sitting-coverage honors the D0155 grandfathering attestation (313 grandfathered, due 6). DO: one computation, one answer - authority-queue consumes the same grandfather basis, reporting due-and-not-grandfathered with the grandfathered count beside it (never hidden). VERIFY: both views read back the same due population; the escalation clock starts from the oldest DUE item, not the oldest grandfathered one."; }
        part dcSittingViewParityDoDR1 : TestResult { :>> id = "3150342f-8a8f-410f-8e50-61b73b98fafe"; :>> outcome = VerdictKind::pass; :>> judgedAgainst = "55d1381fd9a618573ad73c204260e19ca706e139"; :>> judgedAt = "2026-08-22"; :>> judgedBy = "claudeFable5"; }
        action dcOversightRedesign;
        verification dcOversightRedesignDoD : Test { :>> id = "b9e181c0-7b14-472a-a8ba-d678954d945c"; :>> method = VerificationMethod::test; :>> procedureText = "Resolves issue228; delivers D0200 once signed (process-value panel, the most convergent human-side finding: 4 of 9 lenses). The sitting gate is measurably rubber-stamped - 62 percent of covered sittings signed in two batch utterances against cards showing a title plus the string unreviewed; observed override rate 0 percent; escalation changes nothing. DO per the signed option: risk-tiered sampling plus random audit; judgeable sitting cards (computed sprint delta: items added, decisions touched, guards changed, test outcomes); a DISTINCT batchAcknowledged verdict type so coverage reports read-reviews and batch-acks as separate numbers (the never-one-number discipline); an override-rate indicator; escalation consequences. VERIFY: sitting-coverage reads two numbers; the deck card renders the delta; the indicator computes; a batch verdict can no longer masquerade as a read review."; }
        part dcOversightRedesignDoDR1 : TestResult { :>> id = "fac300ce-e797-4276-a077-25fdc8e8857e"; :>> outcome = VerdictKind::pass; :>> judgedAgainst = "aa548b4231eb141f84ac0d89afeff885f2b933bb"; :>> judgedAt = "2026-08-23"; :>> judgedBy = "claudeFable5"; }
        #DependsOn dependency from dcOversightRedesign to d0200;
        action dcClaimLandCheck;
        verification dcClaimLandCheckDoD : Test { :>> id = "afa41a27-3e05-4383-9678-9d7b3760ca8a"; :>> method = VerificationMethod::test; :>> procedureText = "Resolves issue229 (process-value panel, multi-agent lens - two concrete interleavings). Claims gate selection but not landing, and claimedAt is authored and trusted where nothing else in the system is. DO: (a) keel land re-checks computed holdership - landing facts touching an item another actor holds LIVE warns and auto-records the contention Issue (uses existing held_by_others); (b) a guard validates claimedAt against the introducing commit's ancestry (a claim dated before its own commit's parent is refused - D0013 applied to claims, closing deterministic backdating theft). VERIFY: a planted stale-claim landing produces the contention Issue; a planted backdated claim turns the guard red; two-clone convergence stays green."; }
        part dcClaimLandCheckDoDR1 : TestResult { :>> id = "1b8e003e-22b4-444c-8c03-edbaecbb3b1e"; :>> outcome = VerdictKind::pass; :>> judgedAgainst = "d57af6a2024dcf60a4b552b3d4612671b4e7f40c"; :>> judgedAt = "2026-08-22"; :>> judgedBy = "claudeFable5"; }
        action dcAdvisoryInstrumentation;
        verification dcAdvisoryInstrumentationDoD : Test { :>> id = "41c71aae-c6aa-4134-9947-d1c957c0f584"; :>> method = VerificationMethod::test; :>> procedureText = "Resolves issue230 (process-value panel: empiricist, skeptic and AI-safety lenses all found the zero-advisory-blocks datum uninformative - it cannot distinguish deterrence from dead weight, so D0197's declared revisit condition can never trigger). DO: the fire-ledger records, for advisory fires that SAY something, a content hash of the advisory message and whether the flagged action was subsequently changed within the turn (the frozen 6-field schema gains what D0193's contract allows or D0193 is amended); enforcement-report computes advisory-heeded vs advisory-ignored. VERIFY: a heeded advisory and an ignored advisory produce distinguishable ledger records; the report reads both; D0197's revisit condition becomes computable."; }
        part dcAdvisoryInstrumentationDoDR1 : TestResult { :>> id = "0f69d184-c403-4eae-9680-1d545b5bf521"; :>> outcome = VerdictKind::pass; :>> judgedAgainst = "d6c341701aefa9bf1cad16c900bc6391cf24f305"; :>> judgedAt = "2026-08-23"; :>> judgedBy = "claudeFable5"; }
        action dcParserCoverageRatchet;
        verification dcParserCoverageRatchetDoD : Test { :>> id = "ac7f35aa-c6c4-421c-ae1a-89510f15018a"; :>> method = VerificationMethod::test; :>> procedureText = "Resolves issue231 (process-value panel, formal-methods lens: the parser is the TCB of every view - issues 102/109/119 are the incident class - and parser-coverage is a warning the count of which can grow silently). DO: (a) ratchet - the guard goes RED when the skipped-statement count EXCEEDS its committed baseline (currently 7 succession statements), never on presence (avoiding the D0132 all-or-nothing trap); baseline lives in a contract file updated only with the commit that changes it; (b) property-based round-trip - generate random models from the schema vocabulary, assert parse-print identity and zero skipped statements (the ShardStore lightweight-formal-methods pattern), seeded deterministically for CI. VERIFY: a planted new skipped-statement class turns the guard red; the PBT suite runs in CI within budget; baseline updates are visible diffs."; }
        part dcParserCoverageRatchetDoDR1 : TestResult { :>> id = "7d902f3e-d181-4ebc-94ad-1edc5b2c52b7"; :>> outcome = VerdictKind::pass; :>> judgedAgainst = "f760170eb8b54758875aa8b071a0ccd2139148ca"; :>> judgedAt = "2026-08-22"; :>> judgedBy = "claudeFable5"; }
        action dcControlEvaluation;
        verification dcControlEvaluationDoD : Test { :>> id = "51e1779b-1a90-42aa-a8bc-6a174d0150cb"; :>> method = VerificationMethod::demo; :>> procedureText = "Process-value panel recommendation 3 (AI-safety lens 1, empiricist 3, formal-methods differential oracle). keel measures whether controls fire on honest work, never whether they hold under attack - the field's required claim is 'controls were attacked and held' (Redwood control evaluations). DO: a scripted red-team campaign in a THROWAWAY worktree, human-approved before each run: attempt (a) a hollow pass, (b) a fabricated delegated quote, (c) a weakened guard, (d) a backdated claim, (e) an unfilled-scaffold land; record per-tier catch/miss as TestResults against the controls exercised; every miss becomes an issue plus a control per D0047. VERIFY: a catch-rate table exists with per-attack provenance; at least one previously-unmeasured control has a measured verdict; nothing from the campaign lands outside the worktree."; }
        part dcControlEvaluationDoDR1 : TestResult { :>> id = "28bb1089-8b11-4771-a21d-48f7b56cfa6c"; :>> outcome = VerdictKind::pass; :>> judgedAgainst = "e14fbfbccab54785510fd0e2a74eabefc59347af"; :>> judgedAt = "2026-08-24"; :>> judgedBy = "claudeFable5"; }
        action dcHeterogeneousCritics;
        verification dcHeterogeneousCriticsDoD : Test { :>> id = "4201dbf0-fc47-45b1-8516-e9c902042dc1"; :>> method = VerificationMethod::demo; :>> procedureText = "Process-value panel recommendation 4 (4 of 9 lenses; the debate literature's single strongest lever - same-model panels carry correlated blind spots and honestly claim only convergence). DO: enroll at least one DIFFERENT-MODEL actor (actor-enrollment process, kind ai, model identity recorded), route at least one Core-3 lens or one panel seat per review through it, and record the critic's model in critiquedBy provenance so critic-independence can distinguish cognition-distinct review from role-distinct review. BLOCKED ON: the human supplying access to a second model. VERIFY: a critique record exists whose judgedBy resolves to a non-Claude-lineage actor; the panel process doc's convergence-not-independence note gains its first true exception."; }
        action dcDeckJudgeableCards;
        verification dcDeckJudgeableCardsDoD : Test { :>> id = "2a46a61c-3a2d-4047-a2c7-8a33a47ccf5c"; :>> method = VerificationMethod::test; :>> procedureText = "Resolves issue233 and issue234 (their direct feedback, 2026-08-23). DO: (a) fork cards highlight ONLY the tapped option (data-sel stamped by JS, generic accept styling restricted to non-option buttons) - all option buttons lighting up made the deck look multi-selected and produced eleven contradictory d0201 rows; (b) every decision card carries a collapsible deciding-context panel rendering the decision's own context and decision text, so a signature can be a judgment rather than a trust gesture. VERIFY: regenerated deck shows one highlighted option per fork card and a why-panel per decision card; emitted JS parses; suite green."; }
        part dcDeckJudgeableCardsDoDR1 : TestResult { :>> id = "56f82afc-1287-4dcc-bb6d-cd91c788fefb"; :>> outcome = VerdictKind::pass; :>> judgedAgainst = "71f645386eaae707123ee7016522851a1da61347"; :>> judgedAt = "2026-08-23"; :>> judgedBy = "claudeFable5"; }
        action dcGithubGestureSubstance;
        verification dcGithubGestureSubstanceDoD : Test { :>> id = "da17c33a-a48e-4f98-9fdc-3d3504c9c21a"; :>> method = VerificationMethod::test; :>> procedureText = "Resolves issue235. The confirmation-authenticity substance scanner (quotes_conversational_words) recognized only deck/console as named human gestures, so a one-letter fork answer on a GitHub decision issue ('A') failed the check - the channel D0205 built could not record through its own gesture. DO: the scanner accepts a GitHub comment citation (github comment / github.com URL in the note) as a valid gesture, since a 2FA-authenticated timestamped comment subsumes the device HMAC (D0201-B). VERIFY: a note citing a GitHub comment passes; a bare unquoted assertion still fails; unit test pins the option-letter case; the D0208 recording completes via the sweeper once landed."; }
        part dcGithubGestureSubstanceDoDR1 : TestResult { :>> id = "7f8012f1-66f8-410e-acbb-4eb0c7a251f2"; :>> outcome = VerdictKind::pass; :>> judgedAgainst = "b40bebab8ec345380782139568af87efc2b69ffd"; :>> judgedAt = "2026-08-24"; :>> judgedBy = "claudeFable5"; }
        action dcRulesUnderKeystone;
        verification dcRulesUnderKeystoneDoD : Test { :>> id = "4a794bb4-45bf-43f7-a367-1be47d1d189c"; :>> method = VerificationMethod::test; :>> procedureText = "Resolves issue236 (D0208 control evaluation, HIGH). The control-eval proved an agent could downgrade a blocking ElementRule to a warning in .engine/rules/ and NO guard fired - process-change's is_process_def did not cover the rules directory, so the enforcement DEFINITIONS were editable by the monitored without a signed decision (the AI-safety panel's self-modification gap, made concrete). DO: is_process_def includes .engine/rules/*.sysml so any rule edit requires a co-committed #ProspectiveChange/#SafetyChange Decision - a human-signed act. VERIFY: a committed rule severity-flip turns process-change RED (probed live in the throwaway worktree: was PASS scanned-0, now FAIL scanned-1); the real tree's rule edits this sprint ride a marked decision."; }
        part dcRulesUnderKeystoneDoDR1 : TestResult { :>> id = "fbdc8fad-df74-4884-b2e2-532a69516443"; :>> outcome = VerdictKind::pass; :>> judgedAgainst = "e14fbfbccab54785510fd0e2a74eabefc59347af"; :>> judgedAt = "2026-08-24"; :>> judgedBy = "claudeFable5"; }
        action dcDanglingResultAtGate;
        verification dcDanglingResultAtGateDoD : Test { :>> id = "54bf0295-1933-4c6a-af4f-818310a4d9da"; :>> method = VerificationMethod::inspect; :>> procedureText = "Resolves issue237 (D0208 control eval, LOW). A free-floating TestResult whose judgedAgainst SHA does not resolve passes validate+guard: the commit gate does not check SHA resolvability. The TRACKED case is covered - orient invalidEvidence flags a task whose evidence SHA dangles, and CI audit-history re-derives verdicts - so an UNREFERENCED garbage-SHA result is inert (computes nothing). DO: decide whether the commit gate should reject a dangling judgedAgainst at write time, or whether orient+audit-history coverage of the tracked case suffices; if the latter, this is accept-risk with the reason recorded. VERIFY: either a guard flags a dangling-SHA result, or the disposition records why the existing tracked-case coverage is sufficient."; }
        part dcDanglingResultAtGateDoDR1 : TestResult { :>> id = "d596d572-a509-4c2b-b4d1-6e599e3b708d"; :>> outcome = VerdictKind::pass; :>> judgedAgainst = "e14fbfbccab54785510fd0e2a74eabefc59347af"; :>> judgedAt = "2026-08-24"; :>> judgedBy = "claudeFable5"; }
        action dcProcessAdherenceAudit;
        verification dcProcessAdherenceAuditDoD : Test { :>> id = "63b9254f-cef4-4c07-b929-e4a1bcc90cbd"; :>> method = VerificationMethod::test; :>> procedureText = "Delivers D0209 clause 1. A CI process-adherence audit that re-derives from the git tree ALONE, on infra the agent cannot touch, that the enforcement signature never weakened unsigned across the pushed range - guard-set/rule-severity monotonicity, the issue236 self-modification class caught independently even when the commit-time hook is bypassed. DO: keel audit-adherence [--since REF] reads each commit's rule severities + guard-constraint bindings via git show (no checkout, CI-fast), flags any weakening/vanishing vs the parent unless that commit co-commits a marked Decision, and EXITS NON-ZERO (a gate, unlike audit-history's report); wired into ci.yml. VERIFY: the real history PASSes; a hook-BYPASSED unsigned rule weakening in a throwaway worktree returns exit 1 with the rule named; unit tests pin the severity ranking."; }
        part dcProcessAdherenceAuditDoDR1 : TestResult { :>> id = "c3633170-aefe-4799-9196-039269069e0f"; :>> outcome = VerdictKind::pass; :>> judgedAgainst = "be3e4c1692b29e9502e3047bc866a27259b3e2fe"; :>> judgedAt = "2026-08-24"; :>> judgedBy = "claudeFable5"; }
        action dcFreezeEnforcementSurface;
        verification dcFreezeEnforcementSurfaceDoD : Test { :>> id = "7e6b601e-109f-4655-a736-b4e47896c794"; :>> method = VerificationMethod::test; :>> procedureText = "Delivers D0209 clause 2. Generalize the rules-dir keystone fix so EVERY path a guard reads its own definition from needs a human-signed marked Decision - the enforcement surface (guard source, hook config, CI workflow files) joins is_process_def, and an audit diffs is_process_def against the actual set of guard-definition paths so a new one cannot be added outside the lock. VERIFY: editing guard source / a hook config / a CI workflow without a marked decision fails the keystone; the diff-audit flags any guard-definition path not covered."; }
        part dcFreezeEnforcementSurfaceDoDR1 : TestResult { :>> id = "283f33b2-8ec1-45f5-ad48-89b43c22dd33"; :>> outcome = VerdictKind::pass; :>> judgedAgainst = "087afa2f10c2dfdde6b014ebeab60c744da08d1d"; :>> judgedAt = "2026-08-23"; :>> judgedBy = "claudeFable5"; }
        action dcProcessCursor;
        verification dcProcessCursorDoD : Test { :>> id = "bc127739-f217-47b1-80e5-d4bc7a220584"; :>> method = VerificationMethod::demo; :>> procedureText = "Delivers D0209 clause 3. Promote the declared ProcessStep state machine from a reference the AI reads into an EXECUTED one: keel tracks the current step and keel advance refuses step N+1 until step N's verify-Tests pass (the D0098-deferred order-gating, bounded, no topology inversion). VERIFY: advancing past an unpassed step is refused; the cursor is computed from the tree, not stored."; }
        part dcProcessCursorDoDR1 : TestResult { :>> id = "6ac5b71e-ce3d-4b47-b632-8f1849a173aa"; :>> outcome = VerdictKind::pass; :>> judgedAgainst = "cdd6fab87566075cee5338e2d549ccc43adc43df"; :>> judgedAt = "2026-08-23"; :>> judgedBy = "claudeFable5"; }
        action dcProactivePostEdit;
        verification dcProactivePostEditDoD : Test { :>> id = "6b1d386b-2001-4fc7-97c5-6e98decfb022"; :>> method = VerificationMethod::demo; :>> procedureText = "Delivers D0209 clause 4. Expand the post-edit hook into proactive 'that change just broke X' prevention: on each .sysml edit, compute what the edit made suspect or what edges it broke and surface it in-loop (guidance, non-blocking). VERIFY: an edit that dangles an edge or drifts a verified item's criterion prints the specific downstream item affected."; }
        part dcProactivePostEditDoDR1 : TestResult { :>> id = "f12d735f-95b3-4d10-8497-2f3ae1e935ee"; :>> outcome = VerdictKind::pass; :>> judgedAgainst = "ea77d8a76f7d747b081861eb62f3d3930c78cf9d"; :>> judgedAt = "2026-08-24"; :>> judgedBy = "claudeFable5"; }
        action dcOverrideThreadEveryAccept;
        action dcPaletteIsDeclared;
        verification dcPaletteIsDeclaredDoD : Test { :>> id = "2182c48c-d1b1-4a91-b2ad-6c4a7d6bfb78"; :>> method = VerificationMethod::test; :>> procedureText = "Resolves issue241 (HIGH). `keel process list|search|show|export` iterate act.unit_names() (process_cmd.rs rows()), so the 12 processes that assert no guard are DENIED rather than listed: `keel process show intake` returns 'error: no process intake' while .engine/processes/intake.sysml exists. That violates srPortModularProcessUnit (accepted must: a unit carries its definition, deploying skill and rules/guards so it can be moved between projects whole) and it is the un-swept half of issue149, whose remedy reached `activation`/`activate`/`deactivate` and not the process catalogue - a D0047 correct-at-the-root failure. DO the minimal fix the panel converged on: point rows() at the already-existing, already-tested activation::declared_processes(), mark unit-less rows non-switchable (keep the accurate refusal - a zero-guard unit must NOT become deactivatable, which would re-create 'deactivate reported success and changed nothing'), keep is_process_active true for zero-guard units so no adopted process flips to INACTIVE, and sweep activation-manifest's scanned count (reports 11 of 23). VERIFY: all 23 appear in list/search/show; export works for a guard-less process; the existing declared_processes_is_every_file_not_only_the_guard_bearing_units test still passes; no process changes activation state; an activate/deactivate round-trip does not rewrite the manifest."; }
        part dcPaletteIsDeclaredDoDR1 : TestResult { :>> id = "1d6539f6-a836-4cf9-ae79-91d288c77839"; :>> outcome = VerdictKind::pass; :>> judgedAgainst = "bca4265a4f02db2dcddf566db43035103e0a76f3"; :>> judgedAt = "2026-08-24"; :>> judgedBy = "claudeFable5"; }
        action dcArmedNotDeclared;
        verification dcArmedNotDeclaredDoD : Test { :>> id = "80fc1764-2629-490c-917b-59db14b76d0b"; :>> method = VerificationMethod::test; :>> procedureText = "Resolves issue240 (HIGH). The commit gate was DISARMED on this machine (core.hooksPath = nul, so git resolved hooks to a nonexistent dir and .githooks/pre-commit never ran) while three shipped surfaces reported it armed: keel hardening says the pre-commit point is present=true failMode=fail-closed, keel orient printed no warning, keel controls reported uncoveredHazards=[]. Root cause: the wiredness predicate is 'git config core.hooksPath returned non-empty', a PROXY for the control being reachable rather than the control being reachable. DO: compute armed-ness as 'the resolved hooksPath directory exists AND contains an executable pre-commit', report ARMED vs DECLARED distinctly for every ctl* with a runtime binding, and add hooksPath=nul as a regression test. VERIFY: with hooksPath=nul the surfaces say NOT ARMED and orient warns; with .githooks armed they say armed; the negative test pins it."; }
        part dcArmedNotDeclaredDoDR1 : TestResult { :>> id = "50a54ea3-02b6-48a4-8232-8bd012242837"; :>> outcome = VerdictKind::pass; :>> judgedAgainst = "60dc411f4858899910a2b83ca9ccb7ef9677435a"; :>> judgedAt = "2026-08-24"; :>> judgedBy = "claudeFable5"; }
        action dcAdherenceCoversActivation;
        verification dcAdherenceCoversActivationDoD : Test { :>> id = "650c5f02-7b35-4715-b329-13e0bece1c02"; :>> method = VerificationMethod::test; :>> procedureText = "Resolves issue242 (HIGH). Two ways to disarm a control that audit-adherence (D0209 clause 1) cannot see, because signature() reads only .engine/rules/ trees: (a) adding one `assert constraint <guard>` line to a guard-less process file makes a CORE (never-deactivatable) guard become that process's switchable property - guard_state returns Core only when NO unit claims the guard, so claiming it demotes it, and the CLI's own remediation text ADVISES the edit; (b) narrowing activation.toml's active list disarms every guard the removed process owns. Both land inside the keystone at commit time but D0209's premise is independent re-derivation for when the hook is bypassed - and the hook WAS bypassed here (issue240). DO: extend the enforcement signature to include the per-commit effective guard state (Core/Active/Inactive per guard name) derived from processes + activation.toml, so a Core->Inactive or Active->Inactive transition ranks as a weakening needing a signed Decision; stop advising the assert-to-make-switchable remedy. VERIFY: a committed core-guard capture and a committed activation narrowing each return exit 1 naming the guard; the real history still passes."; }
        part dcAdherenceCoversActivationDoDR1 : TestResult { :>> id = "be5e5d35-7bfc-43b1-96dd-4d295365c7f4"; :>> outcome = VerdictKind::pass; :>> judgedAgainst = "543e1fa967b8d9d301925a2e6c9d5152c01a0902"; :>> judgedAt = "2026-08-24"; :>> judgedBy = "claudeFable5"; }
        action dcHonestSurfaceEverywhere;
        verification dcHonestSurfaceEverywhereDoD : Test { :>> id = "a3e2de80-797e-4bb0-8f08-77d62180bd11"; :>> method = VerificationMethod::test; :>> procedureText = "Resolves issue239 (HIGH). nConsoleNeverMisleads (N-C2, human-accepted 2026-08-16) already requires that absence of information be distinguishable from information about absence, that a view which could not be computed never render as a negative result, and that stale content never show as current - but its only satisfying requirement (srConsoleViewStatusExplicit) is scoped to the CONSOLE, while CLAUDE.md/D0093 make CLI/JSON the authority. Every violation found this session was on the CLI side: a catalogue denying processes that exist, a wiredness proxy reporting an unreachable hook as armed, a ratio published without its denominator or floor caveat. DO: widen the invariant to the authority substrate - for every computed answer, on any surface, the answer states which of {computed-with-content, computed-empty, could-not-compute, true-as-of-T} it is and the population it was computed over; derive the requirement, then pick the enforcement leg. VERIFY: the three CLI instances above each report their status and population; a view that cannot compute says so rather than returning empty."; }
        part dcHonestSurfaceEverywhereDoDR1 : TestResult { :>> id = "56cd9990-146a-4d00-928b-7ba6aeec212d"; :>> outcome = VerdictKind::pass; :>> judgedAgainst = "26c68ff2c02be662974360d5a34efa9a1a74d5d0"; :>> judgedAt = "2026-08-24"; :>> judgedBy = "claudeFable5"; }
        action dcControlsReportArming;
        verification dcControlsReportArmingDoD : Test { :>> id = "53b808f8-96ca-4588-b683-b08df829c1f1"; :>> method = VerificationMethod::test; :>> procedureText = "Follow-on from issue240, stated as a residual rather than silently claimed closed. keel controls (D0195) is a purely DECLARATIVE hazard/control diff: it reported uncoveredHazards=[] for ehz2/ehz4 while their covering control (ctlCommitGate, .githooks/pre-commit + CI) was unreachable, because the view has no notion of runtime arming at all - it cannot distinguish a control that is declared from one that can fire. dcArmedNotDeclared fixed the two predicates that made a POSITIVE false claim (orient, hardening); this closes the third surface. DO: declare, per control, whether its arming is machine-checkable and how (ctlCommitGate -> gitx::commit_gate_armed; CI -> a workflow file naming the gate), then have controls report DECLARED vs ARMED coverage as separate numbers rather than one - a control whose arming is not checkable must say so rather than counting as armed. VERIFY: with the commit gate unreachable, controls reports ehz2/ehz4 as declared-but-not-armed; with it armed they read armed; a control with no checkable binding is reported as such and never silently counted."; }
        part dcControlsReportArmingDoDR1 : TestResult { :>> id = "57848329-2b7d-4c24-b110-7cb6589e1ae3"; :>> outcome = VerdictKind::pass; :>> judgedAgainst = "9ca8eeb2afb111f7da277d7cd72bdb531df8c917"; :>> judgedAt = "2026-08-24"; :>> judgedBy = "claudeFable5"; }
        action dcNoFalseCleanRange;
        action dcChannelUnitTravels;
        action dcSkillRegistersBesideItself;
        action dcChannelLogicInBinary;
        action dcTransferabilityIsComputed;
        action dcDecisionAuthoringIsCore;
        action dcNoShellInjectionIntoRecords;
        action dcProjectOnboarding;
        // Blocked on the D0227 FORK: the fix reverses a requirement the human themselves stated
        // (one issue per decision, to keep the gesture unambiguous), so it waits for their letter.
        // The CAPABILITY half landed - a gesture may name the decision it reverses - and is inert
        // under today's behaviour; only the policy half is held.
        action dcWhichProject;
        verification dcWhichProjectDoD : Test { :>> id = "f1d2266f-4619-4b8b-8e3e-2be678256fb9"; :>> method = VerificationMethod::test; :>> procedureText = "Resolves issue268 (D0233), reported by the author while using the console. INVESTIGATED FIRST and the finding changed the answer: the server side of their suggested feature already existed - /api/projects discovers sibling keel projects and names the active one, POST /api/project switches and refuses a non-project - and NOTHING RENDERED EITHER, so a capability shipped with no surface. DO: the startup banner prints the ROOT before anything else; the page TITLE becomes project-dot-keel, substituted server-side so the browser TAB is right on first paint and right even if the page JavaScript never runs; the header carries a project badge whose tooltip is the full root, beside a switcher populated from /api/projects that POSTs to /api/project and reloads, hidden when only one project is reachable; a display_path helper strips the Windows verbatim prefix at every display site. VERIFY AGAINST A RUNNING SERVER, not by reading: the banner names the root; the title reads sysmlv2-ai-toolkit dot keel; a POST switch flips it to Penumbra dot keel; C:/Windows is REFUSED with the active project unchanged and the reason reported; switching back restores it; nine reachable projects are discovered so the switcher is populated."; }
        // RAN: live server on 127.0.0.1:7892: banner names the root; GET / title = 'sysmlv2-ai-toolkit . keel'; POST /api/project -> Penumbra flips the title; POST root=C:/Windows -> HTTP 400 refused, active unchanged; switch back restores; GET /api/projects -> 9 reachable. cargo test --workspace -> 271+9+2+1+32; clippy 0 errors
        part dcWhichProjectDoDR1 : TestResult { :>> id = "1af30219-a6d5-44f6-85a2-26fd5dcf3959"; :>> outcome = VerdictKind::pass; :>> judgedAgainst = "f81ffbecd116ed7320078d8c015b70c7e53d845c"; :>> judgedAt = "2026-08-25"; :>> judgedBy = "claudeFable5"; }
        action dcObligationRecorderValidates;
        verification dcObligationRecorderValidatesDoD : Test { :>> id = "773e6537-d1c0-4bd7-8530-38cc086ee768"; :>> method = VerificationMethod::test; :>> procedureText = "Resolves issue274. The obligation recorder emitted a file importing only EngineElement, while Issue is defined in EngineWork and the Resolves edge in EngineRelationships - so RECORDING an obligation made the tree INVALID with an unresolved type reference. Self-defeating for a record whose purpose is to say the tree needs a correction pass, and it put the recorder in the one position it must never occupy: unable to record without breaking the thing it reports on. DO: the template carries both imports. VERIFY: a freshly recorded obligation validates clean; the instance already on disk validates; validate over the whole tree is clean."; }
        // RAN: cargo test --release --test init_smoke => 2 passed 0 failed incl recording_an_obligation_keeps_the_tree_valid | disable-and-rerun: template EngineWork import removed => FAILED with 'unresolved type reference Issue' at override-58a0b47d.sysml:8, restored => pass | keel validate . => 526 tracking files clean
        part dcObligationRecorderValidatesDoDR1 : TestResult { :>> id = "934f63b5-84ee-496f-af13-63dd692c653e"; :>> outcome = VerdictKind::pass; :>> judgedAgainst = "e7d2683"; :>> judgedAt = "2026-08-27"; :>> judgedBy = "claudeOpus5"; }
        action dcWorkspaceDiscoveryIsComplete;
        verification dcWorkspaceDiscoveryIsCompleteDoD : Test { :>> id = "c6af8dff-56db-428d-839e-65d6293c877a"; :>> method = VerificationMethod::test; :>> procedureText = "Resolves issue275. Three panelists independently found that discovery stops at the first project on a branch and is bounded at depth 3, so a project nested inside another, or deeper than three, is invisible - and keel init refuses neither position. Verified: keel init . then keel init sub reports one project; a commit adding a broken sysml file plus a full rules downgrade in the invisible project exits 0 with the gate reporting clean. My own unit test asserted the broken shape as correct, pinning the bug as intended behaviour. DO: derive the project set from git ls-files rather than a bounded walk - exact, unbounded, no skip list; make init refuse a target inside an existing project; make the gate FAIL when a staged path lies under an undiscovered engine-plus-tracking directory. VERIFY: nested and depth-4 projects are discovered; the broken-file commit is BLOCKED; the misleading unit test is replaced."; }
        // RAN: see sprint472_workspaceGate RAN receipt: 11 test suites 0 failures; three-project git repo (root+nested+depth4) all discovered; C:/kt/w4 two-peer workspace armed at init, clean commit gated both, broken beta BLOCKED exit 1 (was exit 0 gate clean); init nesting refused exit 2; keel projects prints you-are-here and current:true; nine real repos one project each
        part dcWorkspaceDiscoveryIsCompleteDoDR1 : TestResult { :>> id = "2740393d-5ef7-4448-ae82-c24861c7394e"; :>> outcome = VerdictKind::pass; :>> judgedAgainst = "e7d2683"; :>> judgedAt = "2026-08-27"; :>> judgedBy = "claudeOpus5"; }
        action dcWorkspaceSurfaceIsOwned;
        verification dcWorkspaceSurfaceIsOwnedDoD : Test { :>> id = "9c18787c-8fe3-4c38-9223-501235b1f557"; :>> method = VerificationMethod::test; :>> procedureText = "Resolves issue276. In a workspace the repo-root enforcement surface belongs to no project, so the keystone lock can never fire on it: verified by replacing the single hook that gates every project with exit 0, staged alone with no Decision - gate --workspace reported 2 projects gated clean, exit 0, printing a line that NAMES the unowned file and passing anyway. Same for the root workflows directory. Also verified: staging the deletion of an entire project, 445 paths, passes the gate. DO: gate_cmd applies the keystone check to unowned staged paths against the repo root and EXITS NON-ZERO; a staged deletion of any engine path, owned or not, is a keystone event. VERIFY: the exit-0 hook replacement is BLOCKED; deleting a project is BLOCKED; a legitimate signed change still passes."; }
        // RAN: see sprint473_lockCoverage RAN receipt: 11 suites 0 failures; unsigned exit-0 hook swap BLOCKED exit 1 (was exit 0 with 2 projects gated clean); project deletion 447 paths BLOCKED 402 keystone events (was silent); signed change PASSES; unsigned rule weakening FAILS at three depths - repo root, inside the project, and deeper (one directory down previously PASSED); signed weakening PASSES; single-project parity measured - PASS, zero qualified keys, project_prefixes == empty
        part dcWorkspaceSurfaceIsOwnedDoDR1 : TestResult { :>> id = "12226141-65d6-42d8-b507-5e36b220cda9"; :>> outcome = VerdictKind::pass; :>> judgedAgainst = "09e4e87"; :>> judgedAt = "2026-08-27"; :>> judgedBy = "claudeOpus5"; }
        action dcAdherenceIsWorkspaceAware;
        verification dcAdherenceIsWorkspaceAwareDoD : Test { :>> id = "9f84b605-2ce1-4d04-8342-9fbbbbe44ebc"; :>> method = VerificationMethod::test; :>> procedureText = "Resolves issue277. The keystone added-file exemption from issue272 was justified by naming audit-adherence as the compensating control, and audit-adherence is BLIND in a multi-project repo: its pathspecs are repo-root-relative, which match nothing when projects live one directory down. Verified with an identical unsigned rule weakening - single-project FAIL exit 1; workspace PASS exit 0, both from the root and from inside the project. So one control was weakened while citing another that does not work in the arrangement the same Decision introduced. DO: iterate the discovered project set in the adherence signature and process-set reads, prefixing each pathspec with the project label, and fail loudly when a discovered project yields zero rule files; until that lands, gate the added-file exemption on a single-project repo. VERIFY: the unsigned weakening FAILS in a workspace at every depth; single-project behaviour unchanged."; }
        // RAN: see sprint473_lockCoverage RAN receipt: 11 suites 0 failures; unsigned exit-0 hook swap BLOCKED exit 1 (was exit 0 with 2 projects gated clean); project deletion 447 paths BLOCKED 402 keystone events (was silent); signed change PASSES; unsigned rule weakening FAILS at three depths - repo root, inside the project, and deeper (one directory down previously PASSED); signed weakening PASSES; single-project parity measured - PASS, zero qualified keys, project_prefixes == empty
        part dcAdherenceIsWorkspaceAwareDoDR1 : TestResult { :>> id = "4b3596c5-8508-408f-81e7-2d75b3c5d41f"; :>> outcome = VerdictKind::pass; :>> judgedAgainst = "09e4e87"; :>> judgedAt = "2026-08-27"; :>> judgedBy = "claudeOpus5"; }
        action dcWorkspaceIsWireable;
        verification dcWorkspaceIsWireableDoD : Test { :>> id = "238418b0-393a-4575-bc76-4e6660a42f4b"; :>> method = VerificationMethod::test; :>> procedureText = "Resolves issue278. A freshly created workspace is COMPLETELY ungated and nothing scaffolds the wiring: init writes hooks per project and only sets core.hooksPath when the target itself holds a git directory, so creating two projects in one repo leaves no repo-root hook and no hooksPath - verified, a commit then ran with zero pre-commit lines. Worse, the refusal message added in the same change advises keel hook pre-commit, which is not a hook event and exits 0 silently: anyone wiring it installs a gate that passes while checking nothing, reintroducing issue269 inside its own fix. DO: when init's target is not the repo root, write or merge the repo-root hook calling gate --workspace, set core.hooksPath, and print workspace-correct next steps; change the advice string to name a command that gates. VERIFY: a two-project workspace created only with documented commands is gated; the advice string names a command that actually gates."; }
        // RAN: see sprint472_workspaceGate RAN receipt: 11 test suites 0 failures; three-project git repo (root+nested+depth4) all discovered; C:/kt/w4 two-peer workspace armed at init, clean commit gated both, broken beta BLOCKED exit 1 (was exit 0 gate clean); init nesting refused exit 2; keel projects prints you-are-here and current:true; nine real repos one project each
        part dcWorkspaceIsWireableDoDR1 : TestResult { :>> id = "e8d3b3e0-6ec4-4aac-811a-3a5721839bcf"; :>> outcome = VerdictKind::pass; :>> judgedAgainst = "e7d2683"; :>> judgedAt = "2026-08-27"; :>> judgedBy = "claudeOpus5"; }
        action dcChannelQualifierRoundTrips;
        verification dcChannelQualifierRoundTripsDoD : Test { :>> id = "6656f49b-b928-4078-ab96-a2cd15b3770a"; :>> method = VerificationMethod::test; :>> procedureText = "Resolves issue279. The channel qualification is incomplete in four places, all verified. The DURABLE marker is written bare while every lookup is qualified, so no lookup can match what it wrote: the standing thread re-posts every run and two projects write byte-identical markers. decision_in_gesture drops the qualifier - a reject naming a qualified id yields the bare name - silently retargeting a human rejection to the ROOT project, which is the exact leak the split was added to prevent, and the opener instructs the human to type that very form. The human-gesture branch of the recorder never calls the splitter at all, so a fork acceptance is recorded against the wrong project or refused outright. And the decider table is read from the root, absent at a workspace root, so it authorises NOBODY. DO: write the qualified id in the marker; teach the gesture parser the label-slash-decision form; route the human branch through the splitter exactly as the auto branch does; resolve the decider table per project. VERIFY: each of the four with a test, plus a round-trip test pinning join and split as inverses."; }
        // RAN: see sprint474_channelQualifier RAN receipt: 11 suites 0 failures, 16 github tests incl join_and_split_are_inverses + 4 channel_script_tests reading the scripts; clippy 0 errors; opener qualify() live via the binary in all 3 cases (root stays bare in a multi repo); github-decider exercised 4 ways, nonexistent root authorises nobody; bash -n clean; validate 529 clean; guard 0 of 52 failing. NOT exercised: an end-to-end channel run against GitHub
        part dcChannelQualifierRoundTripsDoDR1 : TestResult { :>> id = "a1d88a2f-3f8d-4c1e-ac09-deca02fa5563"; :>> outcome = VerdictKind::pass; :>> judgedAgainst = "3576bba"; :>> judgedAt = "2026-08-27"; :>> judgedBy = "claudeOpus5"; }
        action dcLandGatesBeforeThePush;
        verification dcLandGatesBeforeThePushDoD : Test { :>> id = "c18ddc3e-96ae-4bd0-8c0f-08279d8e02d3"; :>> method = VerificationMethod::test; :>> procedureText = "Resolves issue280. D0234 claims land gates every project before a push. It does not: cmd_land pushes first and only reaches the gate after a REJECTION and merge, so on the success path nothing is gated. Verified with a bare remote - a project with a broken tracking file, committed with the skip flag, then land from a different project: landed, exit 0, and the broken file is in the remote. cmd_sync does gate unconditionally; only land is holed, and the Decision asserts a property it lacks. DO: gate before the first push. VERIFY: land REFUSES with a broken project anywhere in the workspace; a clean workspace still lands; the Decision text is corrected."; }
        // RAN: see sprint475_landGate RAN receipt: 12 suites 0 failures incl the new land_gate.rs against a real bare remote; disable-and-rerun proof (stubbed gate => 'land must REFUSE a broken workspace, but exited 0'); live repro: land from alpha with beta broken => exit 1 REFUSING to push, remote still at baseline; clean workspace => exit 0 landed, remote == local; clippy 0 errors
        part dcLandGatesBeforeThePushDoDR1 : TestResult { :>> id = "c3995b4a-fbaa-4cb8-b0c6-63ffaa80ee99"; :>> outcome = VerdictKind::pass; :>> judgedAgainst = "3bb8e77"; :>> judgedAt = "2026-08-27"; :>> judgedBy = "claudeOpus5"; }
        action dcNoCommandReportsGreenOverNothing;
        verification dcNoCommandReportsGreenOverNothingDoD : Test { :>> id = "3cecd67c-4a47-4e7d-8816-2ae60b1666be"; :>> method = VerificationMethod::test; :>> procedureText = "Resolves issue281. The issue269 refusal was applied to validate alone; the project predicate has exactly one non-test call site. So at a workspace root orient exits 0 with an empty ready list, zero done, 100 percent decomposed and answerStatus COMPUTED - the surface CLAUDE.md makes the AI's only legitimate state read, returning nothing-to-do for a repo full of work; whats-next prints COMPUTED-EMPTY over zero items; check-engine prints validated clean over zero files and is a blocking step in this repo's own gate. Separately find_repo_root has no git boundary while discovery does, so validate with no root argument walked OUT of the repository and validated a different repo's project. DO: a shared require-project precondition at every command that reads a model root, or aggregation across the discovered set; bound find_repo_root at the git root. VERIFY: each command refuses or aggregates at a workspace root; none reports a zeroed green; validate cannot answer for another repository."; }
        // RAN: see sprint476_noGreenOverNothing RAN receipt: 13 suites 0 failures incl the new no_green_over_nothing.rs sweeping 12 model readers both directions; live sweep of 22 commands at a 3-project workspace root all exit 2, 8 of 8 still work inside a project; repo boundary verified (nested separate repo => exit 2, plain subdir => exit 0); indicators positional root now honoured; clippy 0 errors
        part dcNoCommandReportsGreenOverNothingDoDR1 : TestResult { :>> id = "e9be9f32-357b-44d4-b6d8-94458e91b61e"; :>> outcome = VerdictKind::pass; :>> judgedAgainst = "3bb8e77"; :>> judgedAt = "2026-08-27"; :>> judgedBy = "claudeOpus5"; }
        action dcOneGateDefinition;
        verification dcOneGateDefinitionDoD : Test { :>> id = "e3c161db-5391-4b10-b4d3-13472150e31b"; :>> method = VerificationMethod::test; :>> procedureText = "Resolves issue282. There are three bodies of the gate with different bars: the workspace per-project gate runs validate plus guards plus declared rules, the scaffolded hook runs validate plus guard plus rules enforce, and the sync gate runs validate plus guards and NO rules - confirmed, that file contains zero occurrences of rules. The declared-rule layer is the one a downstream project uses to add a blocking control without writing Rust, so such a project has it enforced at commit and unenforced on the merged tree, which is exactly the class the sync gate exists to catch. Its own doc comment still claims it is deliberately the SAME entry point as the commit hook. DO: make the per-project gate public, have the sync gate and the hook path use it, delete the inlined copies. VERIFY: one definition and three callers; a declared-rule violation fails all three; the doc comment is true."; }
        // RAN: see sprint477_oneGateDefinition RAN receipt: 14 suites 0 failures incl the new one_gate_definition.rs; ISOLATED fixture (downstream ElementRule, validate clean + all guards clean, only the rule layer objects) fails all three callers - gate --workspace, land, sync; disable-and-rerun with the old sync body restored: land exited 0 and PUSHED the violating tree; a non-isolating untriaged-Issue fixture was discarded; clippy 0 errors
        part dcOneGateDefinitionDoDR1 : TestResult { :>> id = "09b4e166-2524-4b03-ba72-661538b577b7"; :>> outcome = VerdictKind::pass; :>> judgedAgainst = "3bb8e77"; :>> judgedAt = "2026-08-27"; :>> judgedBy = "claudeOpus5"; }
        action dcOwnerOfMatchesOnWindows;
        verification dcOwnerOfMatchesOnWindowsDoD : Test { :>> id = "45839853-5747-4947-8647-c4cdb0a301de"; :>> method = VerificationMethod::test; :>> procedureText = "Resolves issue284. keel projects advertises which project you are in and it never works on this platform: the command canonicalizes the working directory, which on Windows yields the extended-length prefix with backslashes, while discovery takes the root from git in forward-slash form, so the prefix comparison never matches. Verified: from inside a project no marker is printed and the JSON reports current false for every project, including in all eight real repos. Two panelists found it independently. The unit test passes only because it builds the structure by hand from POSIX literals, never through discovery. DO: normalise both sides once inside discovery, through the display-path helper D0233 already added. VERIFY: a test that goes through discovery on the real tree and asserts the owning project of the working directory is found."; }
        // RAN: see sprint472_workspaceGate RAN receipt: 11 test suites 0 failures; three-project git repo (root+nested+depth4) all discovered; C:/kt/w4 two-peer workspace armed at init, clean commit gated both, broken beta BLOCKED exit 1 (was exit 0 gate clean); init nesting refused exit 2; keel projects prints you-are-here and current:true; nine real repos one project each
        part dcOwnerOfMatchesOnWindowsDoDR1 : TestResult { :>> id = "eaee1ee3-8664-460a-b02e-ecceacf50de2"; :>> outcome = VerdictKind::pass; :>> judgedAgainst = "e7d2683"; :>> judgedAt = "2026-08-27"; :>> judgedBy = "claudeOpus5"; }
        action dcWorkspace;
        verification dcWorkspaceDoD : Test { :>> id = "d54a993d-23e5-44f7-a9c2-a5421e9d4ae6"; :>> method = VerificationMethod::test; :>> procedureText = "Resolves issue270 (D0234). The author wants one repo for several small projects and expects it to recur. BUILT AND RAN the arrangement rather than reasoning about it: three things already worked (root resolution walks up, drift is file-scoped per project, the write lock is per model root) and FOUR broke - decision numbering collides at d0001, the channel cannot tell two projects apart because its marker and GitHub lookup are repo-scoped, git allows ONE core.hooksPath so at most one project is gated, and land gates one root while pushing the whole repo. DO: a WORKSPACE is a git repo holding one or more projects, DISCOVERED as a directory with both .engine and .tracking by a depth-bounded walk; keel projects reports them; keel gate --workspace gates every project a commit touches and NAMES the skipped ones; the scaffolded pre-commit calls it when its own directory is not a project; sync and land gate EVERY project before pushing; validate REFUSES a non-project; the channel qualifies an id as alpha/d0001 only when the repo holds several, split in the binary so a human acceptance lands in the right tree. VERIFY LIVE: two projects in one repo with ONE repo-root hook gate a commit across both; a broken project BLOCKS the commit and the report names the project it skipped; a single-project repo is byte-identical - the qualification rule returns d0231 unchanged, and this repo reports exactly one project."; }
        // RAN: live two-project repos: ONE repo-root hook gated a commit across both projects and it landed (96e680e); a broken project BLOCKED the commit and named the project it skipped; a fresh single-project keel init + git add -A + commit now SUCCEEDS (98456c1) where it failed before; keel projects reports 2 in the workspace and 1 here; qualify() -> alpha/d0001 vs beta/d0001, d0231 unchanged; keel guard process-change -> PASS with the co-committed Decision found. cargo test --workspace -> 274+9+2+1+32; clippy 0 errors
        part dcWorkspaceDoDR1 : TestResult { :>> id = "b6483034-60bf-4372-902c-d2c895d00db4"; :>> outcome = VerdictKind::pass; :>> judgedAgainst = "f3567704fe492cf91920a24d80e9970ea8abeb20"; :>> judgedAt = "2026-08-26"; :>> judgedBy = "claudeFable5"; }
        action dcStagedFilesAreProjectScoped;
        verification dcStagedFilesAreProjectScopedDoD : Test { :>> id = "4f030a34-abbd-4ccf-95cd-137124cff34a"; :>> method = VerificationMethod::test; :>> procedureText = "Resolves issue271 (D0234). git diff --cached answers for the whole REPOSITORY no matter which subdirectory asks, so in a repo holding several keel projects every project's guards saw every other project's staged files and the workspace-level ones too. Found live: a two-project workspace failed BOTH projects' process-change guard over .githooks/pre-commit, a file belonging to neither. DO: staged paths are filtered to the asking project and re-based project-relative, using git rev-parse --show-prefix; a project that IS the repo root keeps today's behaviour exactly. VERIFY: in a two-project workspace each project's guard sees only its own staged files; the cross-project violation is gone; this single-project repo's guard output is unchanged."; }
        // RAN: live two-project repos: ONE repo-root hook gated a commit across both projects and it landed (96e680e); a broken project BLOCKED the commit and named the project it skipped; a fresh single-project keel init + git add -A + commit now SUCCEEDS (98456c1) where it failed before; keel projects reports 2 in the workspace and 1 here; qualify() -> alpha/d0001 vs beta/d0001, d0231 unchanged; keel guard process-change -> PASS with the co-committed Decision found. cargo test --workspace -> 274+9+2+1+32; clippy 0 errors
        part dcStagedFilesAreProjectScopedDoDR1 : TestResult { :>> id = "6e5e6f3a-88af-4d76-ab4d-3d99480be6d7"; :>> outcome = VerdictKind::pass; :>> judgedAgainst = "f3567704fe492cf91920a24d80e9970ea8abeb20"; :>> judgedAt = "2026-08-26"; :>> judgedBy = "claudeFable5"; }
        action dcKeystoneLockIsAboutChangeNotArrival;
        verification dcKeystoneLockIsAboutChangeNotArrivalDoD : Test { :>> id = "9a2f07f0-06dd-4cd6-b934-708f8224eef5"; :>> method = VerificationMethod::test; :>> procedureText = "Resolves issue272. A freshly scaffolded project COULD NOT MAKE ITS FIRST COMMIT: keel init stages every .engine/processes file, the keystone lock read that as a locked surface changing without a signed Decision, and the first thing a new user does failed - telling them to record a process-change Decision for a scaffold they did not author. NOT a workspace defect: reproduced on a plain single-project keel init. DO: the lock applies to MODIFIED and DELETED locked files, never merely ADDED, because an added control is one ARRIVING rather than being weakened. State the residual where it lives: an added process CAN weaken by asserting a constraint that claims a CORE guard, and audit-adherence's guard-state monotonicity is the check that catches that transition. VERIFY: keel init then git add -A then commit SUCCEEDS on a fresh project through the scaffolded hook; modifying a process definition without a marked Decision still FAILS; deleting one still fails."; }
        // RAN: live two-project repos: ONE repo-root hook gated a commit across both projects and it landed (96e680e); a broken project BLOCKED the commit and named the project it skipped; a fresh single-project keel init + git add -A + commit now SUCCEEDS (98456c1) where it failed before; keel projects reports 2 in the workspace and 1 here; qualify() -> alpha/d0001 vs beta/d0001, d0231 unchanged; keel guard process-change -> PASS with the co-committed Decision found. cargo test --workspace -> 274+9+2+1+32; clippy 0 errors
        part dcKeystoneLockIsAboutChangeNotArrivalDoDR1 : TestResult { :>> id = "7b3714dc-e11f-4bf0-b0ef-0a4cbba863da"; :>> outcome = VerdictKind::pass; :>> judgedAgainst = "f3567704fe492cf91920a24d80e9970ea8abeb20"; :>> judgedAt = "2026-08-26"; :>> judgedBy = "claudeFable5"; }
        action dcValidateRefusesANonProject;
        verification dcValidateRefusesANonProjectDoD : Test { :>> id = "20ec6596-e79a-4ecf-84e1-e023b0b03e22"; :>> method = VerificationMethod::test; :>> procedureText = "Resolves issue269. keel validate pointed at a directory that is NOT a keel project reports 0 tracking file(s) validated clean and exits 0 - a VACUOUS PASS, and the loudest possible one because validate is the first line of every gate. Found while testing whether several keel projects can share one git repo: run at the parent, validate says clean over nothing, so a commit hook placed at the repo root would gate NOTHING while reporting success. guard all in the same position correctly FAILS, so the two halves of the gate disagree about whether an empty population is an answer. DO: validate REFUSES a root with no .engine directory, naming what it looked for and where, exactly as the guard root resolver already does - an absent project is a usage error, not a clean tree. Keep exit 0 for a real project that genuinely holds zero tracking files, since that is a true statement about a real project. VERIFY: validate on a directory with no .engine exits NON-ZERO with a message naming the missing directory; validate on a freshly scaffolded project still exits 0; validate on this repo still reports its full file count; the pre-commit hook of a real project is unaffected."; }
        // RAN: live two-project repos: ONE repo-root hook gated a commit across both projects and it landed (96e680e); a broken project BLOCKED the commit and named the project it skipped; a fresh single-project keel init + git add -A + commit now SUCCEEDS (98456c1) where it failed before; keel projects reports 2 in the workspace and 1 here; qualify() -> alpha/d0001 vs beta/d0001, d0231 unchanged; keel guard process-change -> PASS with the co-committed Decision found. cargo test --workspace -> 274+9+2+1+32; clippy 0 errors
        part dcValidateRefusesANonProjectDoDR1 : TestResult { :>> id = "cb0fc728-a8bf-4d99-9c48-9c37c3cbb548"; :>> outcome = VerdictKind::pass; :>> judgedAgainst = "f3567704fe492cf91920a24d80e9970ea8abeb20"; :>> judgedAt = "2026-08-26"; :>> judgedBy = "claudeFable5"; }
        action dcEvidenceCited;
        verification dcEvidenceCitedDoD : Test { :>> id = "164702d8-8590-447c-9ab2-cac1e8a7c283"; :>> method = VerificationMethod::test; :>> procedureText = "Resolves issue266 (D0232). The human named the over-claiming directly and asked for a SYSTEMIC fix. Measured: of 5135 recorded TestResults exactly ONE recorded what produced it, so every pass was a testimony no third party could re-derive, and the 3.9 percent fail rate is the signature of a system recording that work happened. DO: (a) guard 52 evidence-cited requires an AI-judged method=test result to carry a RAN receipt naming what produced the verdict, written by append-result --evidence as a structured comment because schema core is frozen; a HUMAN-judged result is never in scope, by design rather than as a courtesy, because their word IS the evidence; forward-only from 2026-08-25 on the D0198 cutover shape. (b) keel attestation reports the census - results by judge kind, how many EXERCISED claims carry a receipt, the fail rate, and the count of uncited coverage claims - so the over-claim rate is a number anyone can read. (c) The third proposed control, gating verdict WORDING, was NOT built as a guard: three calibrations against the real corpus produced 111, 35 and 1 false positives, the last at 0 percent precision on live data, so it ships as part of the indicator with the counts recorded. VERIFY: the guard fires on an AI method=test result with no receipt and passes with one; a HUMAN-judged result is not even scanned; a pre-cutover date is out of scope - all four asserted by test; the guard fired on my own five results from the same session and they now carry real receipts; keel attestation reports 4749 AI results, 1146 exercised, and 318 human judgments counted separately."; }
        // RAN: cargo test --lib a_receipt_is_demanded_of_the_ai_and_never_of_the_human -> 1 passed (4 directions incl. the human exemption); keel guard evidence-cited -> 5 scanned 0 violations; keel attestation . -> ai 4749/1146 exercised, human 318 out of scope; cargo test --workspace -> 271+9+2+1+32 passed
        part dcEvidenceCitedDoDR1 : TestResult { :>> id = "89301768-6ecd-4d59-8cd1-29a271ffce0a"; :>> outcome = VerdictKind::pass; :>> judgedAgainst = "c84671a3f005feb4171d3087a0e11f76d6d81046"; :>> judgedAt = "2026-08-25"; :>> judgedBy = "claudeFable5"; }
        // RAN: verified after threading --evidence through append-gate-result too: keel guard evidence-cited -> 8 scanned 0 violations; cargo test --workspace -> all targets pass
        part dcEvidenceCitedDoDR2 : TestResult { :>> id = "bee21845-9d16-4ec4-8c10-3563f86fe49f"; :>> outcome = VerdictKind::pass; :>> judgedAgainst = "c84671a3f005feb4171d3087a0e11f76d6d81046"; :>> judgedAt = "2026-08-25"; :>> judgedBy = "claudeFable5"; }
        action dcForeignTreeIsTheTest;
        verification dcForeignTreeIsTheTestDoD : Test { :>> id = "74747820-7596-4095-8e25-3da33849a02f"; :>> method = VerificationMethod::test; :>> procedureText = "Resolves issue264. MEASURED, not impressions: 39 of 51 guards read only the authored model, 11 cross a boundary, and ZERO read another project tree - while 11 of the last 20 issues were discoveredInField and cluster at exactly that boundary (another project tree: 251, 252, 253, 259, 263; an external service: 260, 262; a shell layer: 255, 256; a different binary: 261; the human attention: 244, 258). Verification reports 99 percent EXAMINED and 91 percent EXERCISED, and 5120 recorded TestResults carry a 3.9 percent fail rate, so the measures are neither weak nor mis-thresholded - they point INWARD, at the artifact I author, and every recent failure happened where the engine meets something it does not author. DO: make adoption a CONTROL rather than an occasional act. A CI job scaffolds a fresh project with keel init, imports every declared unit into it, and gates that FOREIGN tree - validate, guard, check-engine - failing the build when a unit cannot land clean. This is precisely the manual act that found five of those defects, run every push instead of when someone remembers. VERIFY: the job FAILS on a deliberately broken unit (a process asserting a constraint the unit does not carry, which is issue263 exact shape) and PASSES on the current tree; the guard-target census is reported so the inward/boundary ratio stops being invisible; no unit is exempted silently."; }
        // RAN: keel adoption-check . -> 25/25 units clean both directions; cargo test --test adoption_check_can_fail -> 2 passed (the mutilated-bundle case turns the foreign gate RED); CI step log quoted at run 32851429166
        part dcForeignTreeIsTheTestDoDR1 : TestResult { :>> id = "f126ec22-20d0-4bda-9271-ea46c87cd5ca"; :>> outcome = VerdictKind::pass; :>> judgedAgainst = "3b2bb4912509f6a97b6465c992826831f6ffc3a7"; :>> judgedAt = "2026-08-25"; :>> judgedBy = "claudeFable5"; }
        action dcPinnedFirstBinary;
        verification dcPinnedFirstBinaryDoD : Test { :>> id = "b8565acc-1895-4b63-a2f5-16447628df86"; :>> method = VerificationMethod::test; :>> procedureText = "Resolves issue261 (D0230). penumbra commit gate was running THIS repository working build - keel on PATH resolved to a sibling target/release reporting 0.3.0+dirty - so a broken build here would break their gate, and a guard added here applied to their commits without them adopting anything (that is how issue259 happened). The author chose to decouple: pin to a release. DO: the scaffolded pre-commit resolves PINNED-FIRST - explicit KEEL_BIN, then a repo-local .keel/bin/keel or .keel/bin/keel.exe, then PATH - so dropping a released binary at that path IS the pin, with no wrapper and nothing to keep in sync, and .keel stays machine-local so no binary is committed. A project that does not create the directory is unaffected. VERIFY: a fresh keel init scaffold renders the pinned-first resolution; a stub placed at .keel/bin/keel is the binary the hook ACTUALLY invokes for validate, guard and rules, checked by running the hook rather than reading it; an unpinned scaffold still resolves from PATH."; }
        part dcPinnedFirstBinaryDoDR1 : TestResult { :>> id = "bdee4fba-0a04-4af1-bbf7-bc87dffa0e55"; :>> outcome = VerdictKind::pass; :>> judgedAgainst = "811a9a15ef0633a15b94f8abbf96b212fe12ec01"; :>> judgedAt = "2026-08-24"; :>> judgedBy = "claudeFable5"; }
        action dcGatingWorkflowHistory;
        verification dcGatingWorkflowHistoryDoD : Test { :>> id = "f8a71395-6c7d-4cf9-a22c-41daf73b1d58"; :>> method = VerificationMethod::test; :>> procedureText = "Resolves issue260 (D0229). Tagging v0.3.0, the release workflow FAILED - on the scan-count test, because claim-ancestry skips loudly on a shallow clone and actions/checkout defaults to depth 1. ci.yml carries fetch-depth 0 with a comment citing issue229, the exact fix for the exact reason; release.yml never got it, so the release gate had been RED since guard 48 landed weeks earlier and nobody could have known, because v0.2.3 was tagged before that guard existed. DO: (a) release.yml gate job checks out full history; (b) guard 51 gating-workflow-history refuses any workflow that RUNS the gate - judged by what it invokes, not by its name - while checking out shallow, because such a workflow reports a pass it never verified; (c) the scan-count test records claim-ancestry as legitimately empty on a shallow clone WITH the reason; (d) the per-file-not-per-job limitation is stated in the guard doc and guards.md rather than left to be found. VERIFY: the guard passes 3 scanned on the real tree and FAILS when release.yml depth is flipped to 1 (probed both ways); guard count reads 51; the release workflow goes green on a re-cut tag."; }
        part dcGatingWorkflowHistoryDoDR1 : TestResult { :>> id = "1e1363b0-3e0c-4b79-8eef-0699516c9bba"; :>> outcome = VerdictKind::pass; :>> judgedAgainst = "c444ca562706e2645424c27e03c66d39419b1f98"; :>> judgedAt = "2026-08-24"; :>> judgedBy = "claudeFable5"; }
        action dcGuardScopedToAdoption;
        verification dcGuardScopedToAdoptionDoD : Test { :>> id = "799685b1-c6ef-4dfc-a8ff-598a9e78b80f"; :>> method = VerificationMethod::test; :>> procedureText = "Resolves issue259 (D0228). Guard 50, landed hours earlier, failed the FIRST project keel was adopted onto 22 times out of 22 - a control that project never chose, breaking its commit gate, which is exactly the failure D0164 names. DO: scope the guard to adoption - it enforces nothing unless project-onboarding is present in the project, and REPORTS 0 scanned rather than skipping silently, so an out-of-scope guard stays visible. Not solved by claiming the guard from the process: a project lacking the unit has no claim either, so guard_state would return Core and enforce it anyway. VERIFY: penumbra goes from 22 violations to guard ALL PASS with the fixed binary; keel own count unchanged at 25 scanned; the unit test asserts both directions plus the out-of-scope zero."; }
        part dcGuardScopedToAdoptionDoDR1 : TestResult { :>> id = "82efc9b3-4ece-4aca-927d-1e94559ec356"; :>> outcome = VerdictKind::pass; :>> judgedAgainst = "f4417e9033b3d306085a2e5b34a9e89b2e708243"; :>> judgedAt = "2026-08-24"; :>> judgedBy = "claudeFable5"; }
        action dcChannelNotificationCost;
        verification dcChannelNotificationCostDoD : Test { :>> id = "66a0302c-3495-4a08-a75e-e7bac9491a69"; :>> method = VerificationMethod::test; :>> procedureText = "Resolves issue258. MEASURED before proposing anything: 22 GitHub issues exist and 20 were opened in a single day, one per proposed Decision, because D0207 gives every non-fork a forever-open override thread of its own; 94 workflow runs landed that same day, of which 28 CI runs failed and each failure emails the pusher; and the decision-record sweeper fires on a 30-minute cron. The override thread is the human ONLY route to reverse an auto-accepted Decision, so it cannot be removed - but it does not have to be a separate issue per Decision. DO: one STANDING override thread carrying a comment per auto-accepted non-fork, while a FORK still opens its own issue - which separates the FYI stream from the you-must-decide stream, so the human can mute the first and keep the second. That requires a gesture comment to be able to NAME its decision (reject d0225 because ...) rather than inheriting it from the issue body, which is the only code change on the parsing side. VERIFY: a comment naming a decision routes to that decision and one that does not still inherits from the issue; a fork opens its own issue; a non-fork appends to the standing thread and the receipt cites thread plus comment; the issues-per-decision rate drops from one to zero for non-forks; no auto-accepted Decision loses its override route. ALSO RESOLVES issue262, the two defects the FIRST LIVE RUN produced and the stubbed dry run could not: the thread was created TWICE because the lookup used the GitHub search index, which lags creation - now found by LABEL, which the API serves directly, plus an in-process cache and lowest-number-wins if a race ever leaves two; and the recorder CLOSED the standing thread after its receipt, destroying the reversal route for every auto-accepted decision at once - it now never closes a thread carrying the keel-standing label, while a fork's own issue still closes. VERIFY LIVE, not by dry run: exactly one open thread carrying the label; a non-fork produces ZERO new issues and one comment; a fork still opens its own assigned issue; the thread is still OPEN after a receipt lands on it."; }
        part dcChannelNotificationCostDoDR1 : TestResult { :>> id = "9fd07c9c-6d2d-4e80-a24d-b1177a1f0334"; :>> outcome = VerdictKind::pass; :>> judgedAgainst = "811a9a15ef0633a15b94f8abbf96b212fe12ec01"; :>> judgedAt = "2026-08-24"; :>> judgedBy = "claudeFable5"; }
        #DependsOn dependency from dcChannelNotificationCost to d0227;
    #DependsOn dependency from dcDecisionClausesAreAddressable to d0303;
        verification dcProjectOnboardingDoD : Test { :>> id = "fdc17e60-0390-487f-90dc-dcbdb9bf3dda"; :>> method = VerificationMethod::test; :>> procedureText = "Resolves issue257 (D0225, D0226), raised by the author as a precondition on the penumbra migration. keel init lays down a working project with every process active and never asks what is being built, so the author faces 25 processes with no basis to judge them. DO: (a) a project-onboarding process and skill that elicit the WORK - deploying business-elicitation so answers are Statements first - then match, research the gaps, recommend as an argument, and charter; NEVER offering the catalogue as a menu, because a chosen option is evidence about the menu (D0216); (b) an APPLIES-WHEN condition declared BESIDE each process, stating the SITUATION rather than a domain label, so a domain nobody listed is still served and the fact travels with the unit (D0222); (c) keel onboard as the computed view of charter state and conditions, never a gate (D0098); (d) guard 50 process-applicability so a new process cannot be added without a condition; (e) charteredBy in activation.toml naming the Decision, and keel chartering its own set as the first real use. VERIFY: 25 processes declare a condition and the guard passes 25 scanned; a Process file without one FAILS it, tested in both directions with the non-Process file out of scope; a FRESH keel init scaffold reports NOT CHARTERED, ships all 25 conditions and passes every guard; process audit reports project-onboarding TRAVELS WHOLE; keel onboard reports CHARTERED by d0226 on this project; every test target passes."; }
        part dcProjectOnboardingDoDR1 : TestResult { :>> id = "895c42f3-7138-4298-8b14-ed0ad67f41fc"; :>> outcome = VerdictKind::pass; :>> judgedAgainst = "64f2dea614166747b60f17c9fe97d283f8f06dbe"; :>> judgedAt = "2026-08-24"; :>> judgedBy = "claudeFable5"; }
        verification dcNoShellInjectionIntoRecordsDoD : Test { :>> id = "1e439734-4905-4c3b-a5ae-2566c7a3c48f"; :>> method = VerificationMethod::test; :>> procedureText = "Resolves issue255 and issue256. A BACKTICK inside a double-quoted shell argument is command substitution: recording D0223 the prose NAMED a keel command, sh RAN it, and roughly 2000 characters of JSON landed in the decision field of a governance record - caught only incidentally, because that JSON carried an escape the parser rejects. Investigating it found the same injection had ALREADY LANDED: D0214's context held 13,136 characters of console transcript, recorded, auto-accepted and pushed undetected. DO: (a) the write path REFUSES a prose field carrying captured tool output, in both observed shapes - a run of three or more quoted-key-colon pairs (JSON and dict repr) and four or more strong guard markers (a console transcript) - on record decision and record issue alike, with a message that names the backtick mechanism so the author learns it where it bites; (b) keel record decision --from FILE takes the prose from a draft file, key-value headers and verbatim sections, so no shell layer exists to run anything and the safe road is the easy one (D0054); (c) the landed D0214 dump is excised and its sentence restored, acceptance receipt untouched. VERIFY: the D0223 text and the D0214 transcript are both refused by name with the offending region quoted; a clean decision quoting guard names still records; the whole existing corpus of decision prose flags ZERO with the population asserted non-empty, so the check cannot pass vacuously; D0224 itself was recorded through --from; every test target passes."; }
        part dcNoShellInjectionIntoRecordsDoDR1 : TestResult { :>> id = "677cdbf3-0000-4a41-bdd5-0c770e3134f8"; :>> outcome = VerdictKind::pass; :>> judgedAgainst = "016cadaa627a5dda4345e66d1167859e60e8e5ec"; :>> judgedAt = "2026-08-24"; :>> judgedBy = "claudeFable5"; }
        verification dcDecisionAuthoringIsCoreDoD : Test { :>> id = "a925bae1-4d42-4ba2-abf5-857ae27ff531"; :>> method = VerificationMethod::test; :>> procedureText = "Resolves issue254 (D0223), human-directed. decision-authoring - the process by which a Decision is authored, which is how a process gets cemented here - CLAIMED five guards, and a guard is core precisely when no unit claims it. So keel deactivate decision-authoring switched off decisionRationale, acceptanceEvents, decisionRequirementLink, attestationSubstance AND confirmationAuthenticity - the guard that stops an AI recording a human acceptance that never happened. DO: the process asserts NO guard, making all five CORE and therefore never deactivatable AND more portable (an adopting project gets them with no activation step, since nothing claims them there either); the definition carries the reason and an explicit instruction not to re-add an assert; the process-to-guard link is recorded as core = [...] in process-enforcement.toml and hardening counts core guards as enforced, because otherwise a core-enforced process reports guards 0 and reads as NOT enforced. VERIFY: all five read CORE in keel activation; deactivate REFUSES with the accurate message; hardening moves decisionAuthoring from undeclared to enforced (15 to 16); audit-adherence treats Active to Core as a strengthening and does not flag it; every test target passes."; }
        part dcDecisionAuthoringIsCoreDoDR1 : TestResult { :>> id = "38f074d0-4ca7-4b6c-8984-d58473f73e2e"; :>> outcome = VerdictKind::pass; :>> judgedAgainst = "016cadaa627a5dda4345e66d1167859e60e8e5ec"; :>> judgedAt = "2026-08-24"; :>> judgedBy = "claudeFable5"; }
        verification dcTransferabilityIsComputedDoD : Test { :>> id = "ce656e18-8ef4-4b19-8039-0f5af60a7359"; :>> method = VerificationMethod::test; :>> procedureText = "Resolves issue253 (D0222). The human asked for a final pass on whether everything is easily transferable BEFORE migrating to penumbra. Twice already a unit had been declared transferable and was not, both times found by adopting rather than reading - so the answer had to be computed. DO: keel process audit reports per unit whether it would land GREEN in a project that lacks it (deploying skill present, the declaration binding skill to process travels, declared extras exist, no carried file cites a path the adopter will not have); then a committed migration transform MOVES all 36 AISkill declarations beside their skills, import RETIRES a central declaration an incoming per-skill file supersedes, and the stale references are swept. VERIFY: the audit goes 23 LANDS-RED of 24 to 0; intake, migration, obligation-review and agile-workflow each export and import into a fresh project lacking them and leave it at guard ALL PASS; the penumbra case (skill declared centrally from an older engine) is simulated and import announces the retirement with duplicate-identity clean; the migration reconciles 36 found = 36 moved = 0 skipped; the audit is narrowed twice against the real corpus so a directory convention and a placeholder are not flagged."; }
        part dcTransferabilityIsComputedDoDR1 : TestResult { :>> id = "2652f128-7b09-4001-acc4-bef486297d33"; :>> outcome = VerdictKind::pass; :>> judgedAgainst = "43a7b10f0a9662043e4099dccbb746a280d1d850"; :>> judgedAt = "2026-08-24"; :>> judgedBy = "claudeFable5"; }
        verification dcChannelLogicInBinaryDoD : Test { :>> id = "9a3f0f48-c089-4d29-970d-51935d8c47c6"; :>> method = VerificationMethod::test; :>> procedureText = "Delivers D0221 in part. The human: I do not want all these bespoke scripts - if we need something consistently, build it into keel, or into a process if we need it flexible. The channel shipped 272 lines of bespoke shell and python whose recurring defects all came from that: record_decision.sh RE-GREPPED the login table the binary owns (two implementations of one rule, the D0219 drift), parsed the gesture with a shell case and a locale-dependent tr that nothing unit-tested, and was invisible to every keel surface. DO: move the DETERMINISTIC text logic into the binary - gesture parsing, the decision-marker read, idempotency, and the decider lookup - as keel github-gesture emitting JSON, with the vocabulary in ONE place; leave gh effects in the script as I/O only; keep policy in the process definition. VERIFY: five unit tests pin the documented vocabulary AND that nothing unrecognised (lgtm, yes, acceptable, accept BB) ever reads as an accept, because a misread gesture is a fabricated human attestation; the live command returns the right JSON for B / accept / reject <why> and exit 1 for unparsed; record_decision.sh contains NO decision logic afterward. REMAINING (stated, not claimed): open_decision_issues.py still composes the issue body in python, and the scripts still exist as the I/O layer - the target of `.github/scripts/` disappearing is not reached."; }
        part dcChannelLogicInBinaryDoDR1 : TestResult { :>> id = "856132e8-c54c-41a6-8c83-a2d460a21c8b"; :>> outcome = VerdictKind::pass; :>> judgedAgainst = "9253f3c907438e52e00817b954b5e410661922da"; :>> judgedAt = "2026-08-24"; :>> judgedBy = "claudeFable5"; }
        verification dcSkillRegistersBesideItselfDoD : Test { :>> id = "31c69d7d-770b-4dce-a086-d5ad12ac480d"; :>> method = VerificationMethod::test; :>> procedureText = "Resolves issue252 (D0220), found by ACTUALLY adopting the channel on penumbra rather than testing the export here. The skills-registry entry that binds skill to process lives in one shared file holding all 37 skills and stayed home, so process-skill FAILED in the receiving project on its first run - a new project met an adopted unit as a red gate it could only clear by hand-editing a shared file. DO: a skill may declare its deployment beside itself in any .sysml under .engine/skills/, and BOTH readers (the process-skill guard and activation::deploying_skills) scan the directory rather than the single file; move decisionChannelSkill into .engine/skills/decision-channel/registry.sysml and have unit_files carry it. VERIFY: export carries 7 files; after import penumbra reports validate clean, process-skill 22 scanned 0 violations and guard ALL PASS where the same adoption previously FAILED; this repo stays green at process-skill 24/0; duplicate-identity refuses a copy so the entry must be MOVED."; }
        part dcSkillRegistersBesideItselfDoDR1 : TestResult { :>> id = "f5032649-32a4-4f43-8ea4-d0ad251ba53a"; :>> outcome = VerdictKind::pass; :>> judgedAgainst = "232c0cd491c0a3cb15250180df1a2c689c3c8867"; :>> judgedAt = "2026-08-24"; :>> judgedBy = "claudeFable5"; }
        verification dcChannelUnitTravelsDoD : Test { :>> id = "87c706bb-0dea-482d-8666-bb72d47225ef"; :>> method = VerificationMethod::test; :>> procedureText = "Resolves issue251 (D0219). The human asked to activate the GitHub decision channel on another project (asirobots/penumbra) with the constraint that they must not be forced to own every project. FOUR defects: the unit exported 3 files while the 5 that ARE the channel stayed home (srPortModularProcessUnit violation); the opener assigned to github.repository_owner which is an ORG for that repo, so gh issue create would FAIL; the decider login was a literal in the workflow in 3 places, forcing every adopter to fork the mechanism; and keel init shipped THIS project github-actors.toml verbatim, so every new project inherited my login as its authorized decider. DO: unit-extras.toml declares per-unit files and prerequisites carried by export and listed by show; keel github-decider is the single implementation of who-may-decide read from the committed table, with the workflow condition structural only and authorization a step that leaves an outsider comment GREEN; assignment goes to declared deciders or nobody; github-actors.toml joins the init instance-contract reset and starts empty. VERIFY: export yields 6 files + unit.toml at exit 0; a round trip into a throwaway inited project lands the workflows and scripts in .github/ with the project own keel-gate.yml intact; a fresh init declares NO decider and refuses any login with the remedy; both the fresh-import and --update loops share one destination mapper, closing two bugs that had reported success while copying a file onto itself and writing into .engine/.github/."; }
        part dcChannelUnitTravelsDoDR1 : TestResult { :>> id = "28d2a64a-0634-4943-ae8a-90e1e215784e"; :>> outcome = VerdictKind::pass; :>> judgedAgainst = "d129343588ed2ab4dd901d9c28b4c598bc3be2bb"; :>> judgedAt = "2026-08-24"; :>> judgedBy = "claudeFable5"; }
        action dcTestsAssertRepoNotMachine;
        verification dcTestsAssertRepoNotMachineDoD : Test { :>> id = "23f2f0af-4eeb-4325-8cbf-9735f031b5e4"; :>> method = VerificationMethod::test; :>> procedureText = "Resolves issue248. The sprint447 test this_repos_commit_gate_is_armed asserted that THIS repository has an armed local git hook, which is a property of a MACHINE and not of the repository: a CI checkout configures no core.hooksPath and correctly needs none, because CI is the hook-INDEPENDENT layer (K15/D0179). Every push went red from issue243 onward. My own sprint447 review gate had named the risk verbatim and I overrode it. DO: state the CONDITIONAL invariant instead - IF core.hooksPath is configured it must resolve to a directory holding pre-commit - which still fails the exact issue240 state (configured to a null device) while an unconfigured checkout is not a violation. VERIFY: the test passes locally where a hooksPath is configured and reachable, passes on CI where none is configured, and the unchanged negative test still fails an unreachable path; CI green on main."; }
        part dcTestsAssertRepoNotMachineDoDR1 : TestResult { :>> id = "737ffdc4-9b9e-4757-a252-1935f9373d9f"; :>> outcome = VerdictKind::pass; :>> judgedAgainst = "dfae3ca847e41f040906a06b4dd92bf53bd7b4e1"; :>> judgedAt = "2026-08-24"; :>> judgedBy = "claudeFable5"; }
        verification dcNoFalseCleanRangeDoD : Test { :>> id = "fef137fb-9286-425b-8dd8-44e8ae60d0ad"; :>> method = VerificationMethod::test; :>> procedureText = "Raised by sprint448 retro: the negative-probe-range error has now occurred THREE times (sprint440, sprint441, sprint448). audit-adherence prints `fewer than 2 commits in range - nothing to compare. Clean.` and exits 0, so a probe run with --since HEAD~1 against a REAL unsigned weakening reports CLEAN - a false clean from the gate built to prevent false cleans. Manual vigilance has now failed three times, which D0047 says is not a control. DO: a range that cannot compare anything is a USAGE error, not a clean result - exit non-zero with the remedy (widen the range so the parent is included), and never print the word Clean for a population of one. VERIFY: --since HEAD~1 exits non-zero naming the range problem; --since HEAD~2 over the same pair still detects the weakening; a genuinely clean 2+ commit range still passes; the CI invocation is unaffected because github.event.before spans more than one commit."; }
        part dcNoFalseCleanRangeDoDR1 : TestResult { :>> id = "8cfcd528-84b2-4cb0-ba22-450ad4a7572c"; :>> outcome = VerdictKind::pass; :>> judgedAgainst = "220b1ba5564b4f7128bddc0110634f7ae05b81d4"; :>> judgedAt = "2026-08-24"; :>> judgedBy = "claudeFable5"; }
        action dcWarningsAreRead;
        verification dcWarningsAreReadDoD : Test { :>> id = "93756efd-fae0-4c80-9256-21b82b393170"; :>> method = VerificationMethod::test; :>> procedureText = "Resolves issue244 (MEDIUM). `keel guard` prints [guard] ALL PASS while emitting 80 warnings across 10 guards, one of which is a live report-vs-truth contradiction that has been shipped and unread: 'tag v0.2.0 points at e2c812f but its Release item records commit 425145d - the recorded release and the shipped tag disagree (D0191)'. Detected-but-unread is the highest-frequency drift mechanism in this repo and it grows with every control added, which is why the panel refused a new detector. DO the SUBTRACTIVE fix: route the warning population into orient's non-blocking burndown (count + the guards carrying them + the oldest), so detected drift is read rather than re-detected; triage the release/tag contradiction. VERIFY: orient reports the warning count and it is non-zero today; the tag/Release disagreement is resolved or dispositioned."; }
        part dcWarningsAreReadDoDR1 : TestResult { :>> id = "c6ccd75d-ae92-4b97-b64c-855c39fc12c5"; :>> outcome = VerdictKind::pass; :>> judgedAgainst = "36694872766baf4eb45c4aec55dc23986743394d"; :>> judgedAt = "2026-08-24"; :>> judgedBy = "claudeFable5"; }
        action dcElicitationThroughIntake;
        verification dcElicitationThroughIntakeDoD : Test { :>> id = "dee9928f-0934-47ed-9e36-364d6d6aec6e"; :>> method = VerificationMethod::test; :>> procedureText = "Resolves issue245 (MEDIUM). keel's actual elicitation surface is the business-architecture SKILL (it runs a design/scoping dialogue Brief->Personas->Needs->UseCases and has authored 11 Briefs, 15 Personas, 69 UseCases, 75 Needs), but (a) it has NO process definition, so it appears in no catalogue, is enforced by nothing and is transferable by nothing - and the process-skill guard is one-directional (it requires every process to have a skill, never every skill to have a process), so nothing notices; and (b) it authors Needs from a conversation whose utterances are never recorded, which is the mechanical cause of the unsourced population and the D0157 'wider than the demand' risk - a Need with no cited utterance cannot be checked against what the human said. DO: give business-architecture a process definition; make its dialogue record each answer verbatim as a Statement before authoring the Brief/Needs, with every authored Need carrying #DerivedFrom to a UserStory citing one; make process-skill bidirectional. VERIFY: the skill appears in the catalogue and exports; a dialogue run produces Statements before Needs; a skill naming no process is flagged."; }
        part dcElicitationThroughIntakeDoDR1 : TestResult { :>> id = "b8ae6a98-2ca5-407a-9934-e5914ecf1210"; :>> outcome = VerdictKind::pass; :>> judgedAgainst = "00417f16318529a5d0ac04ede8df3293cd9658cd"; :>> judgedAt = "2026-08-24"; :>> judgedBy = "claudeFable5"; }
        action dcInitContractReset;
        verification dcInitContractResetDoD : Test { :>> id = "0e6a0c07-f5ce-4aae-b38a-5683bebf8aef"; :>> method = VerificationMethod::test; :>> procedureText = "Resolves issue243 (MEDIUM). `keel init` scaffolds the embedded .engine verbatim, so a fresh project inherits THIS repo's adoption declaration: the new tree's .engine/contracts/activation.toml is byte-identical to the self-build's (11 named active processes + 32 viewpoints) and `keel activation` there reports 'declared manifest: yes' for a declaration that project never made - falsifying CLAUDE.md's guarantee that an absent manifest means everything is active so a project that never adopted a control has not violated it. It also inherits unit-ids.toml, i.e. the self-build's EXCHANGE identity for units the new project never exported. DO: init emits a starter (or omits) activation.toml and does not copy unit-ids.toml/installed-units.toml - the same special-case shape init already uses for deliverable-manifest.txt. VERIFY: a fresh init declares nothing it did not choose; activation reports the honest default; no inherited unit ids."; }
        part dcInitContractResetDoDR1 : TestResult { :>> id = "9e194d94-5af3-4302-8cea-c753181221bc"; :>> outcome = VerdictKind::pass; :>> judgedAgainst = "7b7f7791c962e895238c3ab67023e1aa324be452"; :>> judgedAt = "2026-08-24"; :>> judgedBy = "claudeFable5"; }
        action dcDocCountsReconciled;
        verification dcDocCountsReconciledDoD : Test { :>> id = "c7029525-4be2-4ef6-8a9b-9f2aae4a024c"; :>> method = VerificationMethod::test; :>> procedureText = "Resolves issue246 (LOW). A number typed into prose beside a number the engine can compute, with no control tying them: CLAUDE.md and .engine/docs/guards.md both say '45 forward guards' while keel guard runs 48; the shipped activation.toml header still directs readers to .engine/contracts/process-units.toml, a file D0141 deleted. hardening.helpCoverage already proves the technique (88 dispatched / 88 documented), so the counter-measure is cheap. DO: reconcile declared counts against their computed source in the doc surface, and sweep the ghost reference. VERIFY: the doc counts match the computed ones and a deliberate mismatch is flagged."; }
        part dcDocCountsReconciledDoDR1 : TestResult { :>> id = "b8f2d3cf-a806-4f4b-92b7-b4e80a746856"; :>> outcome = VerdictKind::pass; :>> judgedAgainst = "766343d54c7f883b457b38f5b23f08fd66f560de"; :>> judgedAt = "2026-08-24"; :>> judgedBy = "claudeFable5"; }
        verification dcOverrideThreadEveryAcceptDoD : Test { :>> id = "55181156-ff00-4b9a-929d-5a975712275a"; :>> method = VerificationMethod::test; :>> procedureText = "Resolves issue238 (channel-bypass, caught by the human: I claimed D0209 was overridable on its GitHub issue but NO issue existed). D0205's githubChannel opens an override-thread issue only for PROPOSED decisions; a decision accepted locally (serve API / keel accept) before its push is already 'accepted' when the workflow runs, so the proposed-only issue-opener skips it and the human loses the override surface (confirmed: d0207 and d0209 had zero issues). DO: open_decision_issues.py gains ensure_override_threads() - for EVERY accepted decision numbered >= D0205 (the channel's birth) that has no thread on any state, it opens-and-closes an override-thread issue, regardless of acceptance path; run on every push. VERIFY: three mocked-gh dry-runs against the real decision-card set - none-exist targets exactly d0205..d0209 (5); all-exist targets 0; only d0207/d0209 missing targets exactly those 2 (the exact real bypass); a true decision is matched by name d + four digits, so acceptance-record cards (d0205AcceptR1) are excluded."; }
        part dcOverrideThreadEveryAcceptDoDR1 : TestResult { :>> id = "081106f7-d48f-49c7-8955-5981ee80e797"; :>> outcome = VerdictKind::pass; :>> judgedAgainst = "3b6570f"; :>> judgedAt = "2026-08-23"; :>> judgedBy = "claudeFable5"; }
    #Resolves dependency from dcNoOpInvarianceControl to issue310;
    // The #Verify edges these DoDs EARNED and never carried (found by the rigor audit,
    // 2026-08-30): the work was verified, the REQUIREMENT was not (issue082).
    #Verify dependency from dcLibraryReadSideDoD to srAvailabilityIsNotActivation;
    #Verify dependency from dcLibraryReadSideDoD to srLibraryAvailableWithoutInstall;
    #Verify dependency from dcPinBitesDoD to srProjectPinsItsEngine;
    #Verify dependency from dcPinBitesDoD to srWorkspacePinIsCoherent;
    // The decisions these tasks CARRY - authored by the rigor audit (2026-08-30) after finding
    // accepted decisions that promised mechanisms nobody was building (D0261).
    #CharteredBy dependency from dcAttestationBindsToDevice to d0201;
    #CharteredBy dependency from dcMigrationRollsBack to d0252;
    #CharteredBy dependency from dcUngroundedRatioTriggers to d0249;
    // d0236 promised the write path (delivered, dcIntakeHasAWritePath) AND a console tab flagging
    // what waits on the human - the tab is its unbuilt half, and this is the edge that says so.
    #CharteredBy dependency from dcTabsFlagWhatNeedsTheHuman to d0236;
    // ── The unattended-distribution plan (D0267): rollback FIRST, because verified-or-reverted
    // has no second half without it. Each task verifies the SystemRequirement it names.
    #Verify dependency from dcMigrationRollsBackDoD to srMigrationIsReversible;
    #Verify dependency from dcAutoUpdateVerifiedOrRevertedDoD to srUpdateIsVerifiedOrReverted;
    #Verify dependency from dcAutoUpdateVerifiedOrRevertedDoD to srUnprovenUpdateAsksRatherThanActs;
    #Verify dependency from dcLibraryStatusShowsDriftDoD to srDriftIsReportedPerUnit;
    #Verify dependency from dcScheduledCurrencyDoD to srUnattendedPullIsIdempotent;
    // Guard 56 already enforces this; the edge records that it does (added with the split, st063).
    #Verify dependency from dcNoOpInvarianceControlDoD to srUntrustedInputRoutesToADecision;
    #CharteredBy dependency from dcMigrationFixtureIsRealistic to d0275;
    // d0252 clause A promised the capability handshake would cover COMMANDS; only the guard half
    // shipped. This is the edge saying which item finally built the rest.
    #CharteredBy dependency from dcUnitDeclaresTheCommandsItInvokes to d0252;
    // D0313: the STPA-on-keel process, its skill, the first run and the stpa-currency guard.
    #CharteredBy dependency from dcStpaProcessForKeel to d0313;
    // D0314: the untrusted label travels with the derivation (guard 63).
    #CharteredBy dependency from dcUntrustedTaintClosure to d0314;
    // D0315: the terminal is the gesture.
    #CharteredBy dependency from dcTtyAcceptCitesTheGesture to d0315;
    // D0316: every hook resolves the pin before PATH.
    #CharteredBy dependency from dcHooksResolveThePinFirst to d0316;
    #CharteredBy dependency from dcMigratePreservesProjectSections to d0317;
    #CharteredBy dependency from dcAdoptionCheckReportsTheRealVerdict to d0318;
    #CharteredBy dependency from dcForwardOnlyCutoffIsTheProjectsOwn to d0319;
    #CharteredBy dependency from dcSurfaceDriftIgnoresLineEndings to d0320;
    // D0321 is the FORK dcProcessStepsBindToChecks was asked to write; it stays proposed for the human.
    #CharteredBy dependency from dcProcessStepsBindToChecks to d0321;
    #CharteredBy dependency from dcForkShapeIsDetected to d0322;
    #CharteredBy dependency from dcExternalFactGate to d0323;
    // The human's answers of 2026-09-05 ('d0312 B', 'd0321 A') charter the delivery of both forks.
    #CharteredBy dependency from dcProcessStepDeclaresItsCheck to d0321;
    #CharteredBy dependency from dcAdvanceRefusesAnyBoundStep to d0321;
    #DependsOn dependency from dcAdvanceRefusesAnyBoundStep to dcProcessStepDeclaresItsCheck;
    #CharteredBy dependency from dcProposedOutcomeTier to d0312;
    #CharteredBy dependency from dcSetJudgmentWritePath to d0312;
    #CharteredBy dependency from dcReplayableDemoStaysAPass to d0312;
    #DependsOn dependency from dcSetJudgmentWritePath to dcProposedOutcomeTier;
    #DependsOn dependency from dcReplayableDemoStaysAPass to dcProposedOutcomeTier;
    // D0324 is the FORK dcConsentIsScopedAndExpires was asked to write; it stays proposed for the human.
    #CharteredBy dependency from dcConsentIsScopedAndExpires to d0324;
    #CharteredBy dependency from recallRanksLinkedRecordsAsWellAsGrepDoes to d0325;
    #CharteredBy dependency from identifierMatchingAcceptsNaturalSpellings to d0328;
    // D0378 is the FORK dcRoutingNumberIsStable was asked to put to the human (which shape of routing
    // number the project buys); the item waits on their word and returns by itself.
    #DependsOn dependency from dcRoutingNumberIsStable to d0378;
    #DerivedFrom dependency from dcRoutingVerdictQuotesItsEvidence to us103;
    #DerivedFrom dependency from dcProcessStepsAreHookGateOrMemory to us102;
    #DerivedFrom dependency from dcRetroFindingIsAnIssueFirst to us110;
    #DependsOn dependency from dcRoutingVerdictQuotesItsEvidence to d0381;
    // D0382: the rig's repeated-run mode is an INVESTIGATION - findings, never a TestResult or a number.
    #DependsOn dependency from dcRoutingNumberIsStable to d0382;
    // issue415: the rig's first investigation found the CHECK at fault (D0381) - the fix is the next item in that lane.
    #DependsOn dependency from dcRoutingVerdictReadsTheWholeTurn to d0381;
    #CharteredBy dependency from shortDomainWordsCanSeed to d0327;
    // D0329 was found while dcPanelRecordCorrections corrected D0234: the fix that let the correction land.
    #CharteredBy dependency from dcPanelRecordCorrections to d0329;
    #CharteredBy dependency from dcPanelRecordCorrections to d0330;
    #CharteredBy dependency from kgTravelsWithTheEngine to d0332;
    #CharteredBy dependency from dcUngroundedRatioTriggers to d0333;
    // D0201 B delivered in two clauses (D0303): the device binding and the read-back.
    #CharteredBy dependency from dcAttestationBindsToDevice to d0334;
    #CharteredBy dependency from dcAttestationBindsToDevice to d0335;
    #CharteredBy dependency from dcAutoUpdateVerifiedOrReverted to d0336;
    // D0337 delivers the human's answer to D0324 (dcConsentIsScopedAndExpires).
    #CharteredBy dependency from dcConsentIsScopedAndExpires to d0337;
    #CharteredBy dependency from dcScheduledCurrency to d0338;
    #CharteredBy dependency from dcStandingWordsAreProjectLocal to d0340;
    #CharteredBy dependency from dcRemovedTypeScannerReadsSchemaNotProse to d0341;
    #CharteredBy dependency from dcSeededCacheIsVerified to d0342;
    #CharteredBy dependency from dcOneBinaryResolutionForEverySurface to d0343;
    #CharteredBy dependency from dcCharterMustResolve to d0344;
    #CharteredBy dependency from dcLibraryUnitRetirement to d0345;
    #CharteredBy dependency from dcRemainingCliFamilies to d0346;
    #DependsOn dependency from dcRemainingCliFamilies to d0399;
    #CharteredBy dependency from dcPublishSaysWhatMoved to d0347;
    #CharteredBy dependency from dcDeactivatedSkillSaysSo to d0348;
    #CharteredBy dependency from dcSurfaceStampNamesTheBuild to d0349;
    #CharteredBy dependency from dcRedYieldKeepsTheDiagnostic to d0350;
    #CharteredBy dependency from dcStopAdvisoryIsOneLine to d0351;
    #CharteredBy dependency from dcRecordDecisionDeclaresSupersedes to d0352;
    #CharteredBy dependency from dcLandRequiresASuiteReceipt to d0353;
    #CharteredBy dependency from dcStandingSummaryUsesTheKit to d0354;
    #CharteredBy dependency from dcDecisionReportIsArguable to d0355;
    #CharteredBy dependency from dcMigrateReportsTheFailingLines to d0357;
    #CharteredBy dependency from dcReleaseGateHasTheToken to d0358;
    #CharteredBy dependency from dcStopSaysNothingAboutDecisions to d0359;
    #CharteredBy dependency from dcControlProofStateIsComputed to d0360;
    #CharteredBy dependency from dcInstrumentsEnterThePropriety to d0361;
    #DependsOn dependency from dcRecallHitDefinitionIsStated to d0408;
    #DependsOn dependency from dcRetroFindingIsAnIssueFirst to d0467;
    #DependsOn dependency from dcStagedAcceptanceIsProbedAsACharter to d0465;
    // issue546 changes four CLI facts owned by claudeOpus5 (accept, reject, judge-set, override); the D0108 path
    // for that is #Supersede, which parse_cli_facts honours only once issue547 is resolved - hence the order.
    #DependsOn dependency from dcEveryProseFlagReadsAFile to dcCliFactSupersessionIsHonoured;
    // D0479 modularity pass (st126, 2026-09-14): the members in layer order, each after the layer it sits on.
    #CharteredBy dependency from dcWorkspaceHoldsTheLeafMembers to d0479;
    #CharteredBy dependency from dcGuardsViewOrientCycleIsBroken to d0479;
    #DependsOn dependency from dcGuardsViewOrientCycleIsBroken to dcWorkspaceHoldsTheLeafMembers;
    #CharteredBy dependency from dcModelAndWriteAreMembers to d0479;
    #DependsOn dependency from dcModelAndWriteAreMembers to dcGuardsViewOrientCycleIsBroken;
    #CharteredBy dependency from dcViewIsAMember to d0479;
    #DependsOn dependency from dcViewIsAMember to dcModelAndWriteAreMembers;
    #CharteredBy dependency from dcGuardsAreMembersPerFamily to d0479;
    #DependsOn dependency from dcGuardsAreMembersPerFamily to dcViewIsAMember;
    #CharteredBy dependency from dcSuiteIsAMember to d0479;
    #DependsOn dependency from dcSuiteIsAMember to dcModelAndWriteAreMembers;
    #CharteredBy dependency from dcProcessIsAMember to d0479;
    #DependsOn dependency from dcProcessIsAMember to dcViewIsAMember;
    #CharteredBy dependency from dcKeelIssuesIsAMember to d0480;
    #DependsOn dependency from dcKeelIssuesIsAMember to dcViewIsAMember;
    #CharteredBy dependency from dcServeAndGithubAreMembers to d0479;
    #DependsOn dependency from dcServeAndGithubAreMembers to dcKeelIssuesIsAMember;
    #DependsOn dependency from dcServeAndGithubAreMembers to dcProcessIsAMember;
    #CharteredBy dependency from dcKeelCliIsThinDispatch to d0479;
    #DependsOn dependency from dcKeelCliIsThinDispatch to dcServeAndGithubAreMembers;
    #DependsOn dependency from dcKeelCliIsThinDispatch to dcSuiteIsAMember;
    #DependsOn dependency from dcKeelCliIsThinDispatch to dcGuardsAreMembersPerFamily;
    #CharteredBy dependency from dcHooksAreAMember to d0479;
    #DependsOn dependency from dcHooksAreAMember to dcServeAndGithubAreMembers;
    #DependsOn dependency from dcKeelCliIsThinDispatch to dcHooksAreAMember;
    #CharteredBy dependency from dcSharedHelpersDescendBelowTheVerbs to d0479;
    #DependsOn dependency from dcSharedHelpersDescendBelowTheVerbs to dcHooksAreAMember;
    #CharteredBy dependency from dcTheFourStayingModulesAreMembers to d0479;
    #DependsOn dependency from dcTheFourStayingModulesAreMembers to dcSharedHelpersDescendBelowTheVerbs;
    #DependsOn dependency from dcKeelCliIsThinDispatch to dcTheFourStayingModulesAreMembers;
    #CharteredBy dependency from dcTouchedSetDescendsTheWorkspace to d0481;
    #DependsOn dependency from dcTouchedSetDescendsTheWorkspace to dcWorkspaceHoldsTheLeafMembers;
    #CharteredBy dependency from dcSuiteMeasuresTheWorkspace to d0479;
    #DependsOn dependency from dcSuiteMeasuresTheWorkspace to dcSuiteIsAMember;
    #CharteredBy dependency from dcSourceCitationsOnTheLivingDocsResolve to d0471;
    #DependsOn dependency from dcSourceCitationsOnTheLivingDocsResolve to dcProcessIsAMember;
    #CharteredBy dependency from dcOneRepoRootHelper to d0479;
    #DependsOn dependency from dcOneRepoRootHelper to dcModelAndWriteAreMembers;
    #CharteredBy dependency from dcScriptsResolveModuleHomesFromTheManifest to d0479;
    #DependsOn dependency from dcScriptsResolveModuleHomesFromTheManifest to dcModelAndWriteAreMembers;
    #CharteredBy dependency from dcScriptProbesRunInTheVerifyLadder to d0476;
    #CharteredBy dependency from dcQuotedProbeLineIsRefused to d0500;
    #CharteredBy dependency from dcArchDriftDropsSupersededElements to d0479;
    #DependsOn dependency from dcArchDriftDropsSupersededElements to dcModelAndWriteAreMembers;
    #CharteredBy dependency from dcRecordIssueRefusesANonResolverKind to d0479;
    #DependsOn dependency from dcRecordIssueRefusesANonResolverKind to dcModelAndWriteAreMembers;
    #CharteredBy dependency from dcGuardReceiptsKeyPerGuard to d0482;
    #DependsOn dependency from dcGuardReceiptsKeyPerGuard to dcGuardsAreMembersPerFamily;
    #CharteredBy dependency from dcWorkspaceLayeringIsGuarded to d0483;
    #DependsOn dependency from dcWorkspaceLayeringIsGuarded to dcWorkspaceHoldsTheLeafMembers;
    // GH#85 / GH#84 are UNTRUSTED sources (D0264): the resolvers wait on the held Decision, computed.
    #CharteredBy dependency from dcBareNameResolvesLocallyOrUniquelyOrRefuses to d0517;
    #CharteredBy dependency from dcGroundStepBindsToACheckThatReadsThePage to d0518;
    #CharteredBy dependency from dcSprintNamesTheItemItDelivers to d0515;
    #CharteredBy dependency from dcAuthorityQueueListsNeedsAwaitingAcceptance to d0534;
    #CharteredBy dependency from dcGuardsCatalogueNamesTheFamily to d0539;
    // The requirements wait on the Need's acceptance, and the acceptance is only READABLE once the
    // queue computes it - so the block is the queue task, not a sentence in the DoD.
    #CharteredBy dependency from dcCeremonyRequirementsDeriveFromTheVerificationNeed to d0534;
    #DependsOn dependency from dcCeremonyRequirementsDeriveFromTheVerificationNeed to dcAuthorityQueueListsNeedsAwaitingAcceptance;
}
