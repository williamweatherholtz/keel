// KNOWLEDGE RECORD (D0196) - the runner-daemon landscape spike: the field's practice, 122 user-reported weaknesses, and where the tool-owns-the-task design sets itself apart (D0541).
package KnowledgeRunnerDaemonLandscape20260921 {
    private import EngineElement::*;
    private import EngineVerification::*;

    verification kRunnerDaemonLandscape : Test {
        :>> id = "24fa4d59-cd15-4b03-91af-1d414f0c0ea9";
        :>> title = "Landscape: what a runner daemon is across 57 tools and protocols, 122 user threads dispositioned against our design (67 addressed, 45 vulnerable, 9 n/a) - a third of the field's complaints are a stored flag standing in for a live lease; nobody budgets human attention, kills the child on lease loss, or renews the job credential on the heartbeat";
        :>> createdAt = "2026-09-21"; :>> createdBy = "claudeFable5";
        :>> method = VerificationMethod::analyze;
        :>> procedureText = "REPLICATION (D0196). PROCESS: adversarialPanelReview (D0187, def pin 64f2dea), on the sprint 758 landscape-spike shape (D0540). TRIGGER: the human, 2026-09-21 (st188): 'browser only for the user, runner-facing (i.e. CLI, yes?) protocol is fine too.  as far as what the runner daemon actually is, etc., do some more research for best practices with existing frameworks, lookup complaints from 50 threads in forums to see user-identified weaknesses of their approach, and let's set ourselves apart.' - the runner-daemon question left open by D0540 in the tool-owns-the-task design under brainstorm since st181, unapproved. ROSTER: five read-only web-enabled lens agents dispatched in parallel with one shared brief (the review's Appendix 0, verbatim) and a tool list plus a minimum thread count each: A CI runner daemons (13 tools, 26 threads), B workflow-engine and queue workers (15 tools, 17 threads), C agent-harness runners (17 tools, 26 threads), D cross-cutting complaints about agents doing software work unattended (26 threads), E runner-facing wire protocols as specified (12 protocols, 27 threads); one round, no rebuttal. Each lens answered seven practice questions per tool (what the runner is; identity and enrolment; claim protocol and lease; credentials and network inside the job; reporting and run token; lifecycle, versioning, drain, zombies; one mechanism to copy and one to avoid) and tabulated user threads with date, venue, tool, a verbatim quote of at most 25 words, root cause, vendor response and a disposition against our design - ADDRESSED, VULNERABLE or N/A with a clause why. The synthesiser did not re-fetch the lenses' external facts; Reddit and Lobsters were unreachable to every lens; every lens claim about keel's own code was re-checked against source before use and names the check beside it (one count corrected: CLAUDE.md section 4 is 98 lines, not the 40 a lens wrote). Tally computed by scratchpad tally759.py over the appendix tables: 122 real threads, 67 ADDRESSED, 45 VULNERABLE, 9 N/A, 1 conditional. FINDINGS: (1) a runner daemon is seven things - enrol once, pull work, hold it under a renewing lease, get a per-job credential, run in something disposable, report so the server can check it, retire without losing work - and no tool in the five lenses does all seven; (2) the largest theme (35 of 122 threads) is the lease diverging from reality - zombies, orphans, phantom running, duplicates - and in every system it is a stored flag standing in for a live fact; (3) the field converges on pull-not-push, server-dictated heartbeat cadence, a three-tier credential split (enrolment, per-process session, per-job token dying with the job), secrets moved out of the agent phase behind an egress proxy, and ephemeral one-job runners; the proxy holding the one key is field consensus, not a differentiator; (4) nobody renews the job credential on the heartbeat, so the final report outlives its token (GitLab, Argo, Woodpecker, ARC); nobody kills the child process group on lease loss; nobody has a startup phase with its own failure class or an egress denial receipt naming the host; nobody records claim attempts and refusals for a human to read; (5) the agent-harness field alone carries two themes the CI and queue fields never see - review load nobody budgets (9 threads, maintainers walking away) and trust in text (11 threads: success by assertion, permissions by prompt, rules that governed nothing) - and no tool meters human minutes per accepted change; (6) the honest vulnerabilities of our design are the UNCONSTRAINED step in a real checkout with ambient credentials, human attention unbudgeted until the queue cap exists, gates only as strong as the tests bound, 98 lines of prose rules a runner cannot enforce, and the daemon's own resources unreported. DECISION: D0541 - saved as a spike, no tool adopted, no backlog item against the unapproved design; twenty-one design changes the findings force are listed as inputs to the design draft. KEY LEARNING: the field's runners are built by people who own the executor and rent the tracker; ours is built by people who own the tracker - which is why the field stops at liveness plumbing and why facts about the work (claim refusals, human minutes, an unattested done, a credential renewed with the lease) are where we set ourselves apart, and why our unconstrained mode is the product the loudest threads complain about. ARTIFACTS: docs/reviews/runner-daemon-landscape-2026-09-21.md (synthesis with the practice table, the tally, ten ranked themes with thread ids, the seventeen-row set-apart table; Appendix 0 brief; Appendices A-E verbatim with sources); sprint 759; dcRunnerDaemonLandscapeIsRecorded.";
    }
    part kRunnerDaemonLandscapeR1 : TestResult {
        :>> id = "4f4958f0-2554-468d-b746-ab63860665c3";
        :>> outcome = VerdictKind::pass;
        :>> judgedAgainst = "0bef913f6be26971b81c752aacd7dbd1785df30f";
        :>> judgedAt = "2026-09-21";
        :>> judgedBy = "claudeFable5";
        :>> notes = "Five lenses in one round, 122 threads above the fifty asked, every thread dated, URL-cited and quoted verbatim, every row dispositioned; four lens claims about keel's own code re-checked against source, three kept, one count corrected in the synthesis.";
    }
    dependency from kRunnerDaemonLandscape to adversarialPanelReview;
    dependency from kRunnerDaemonLandscape to d0187;
    dependency from kRunnerDaemonLandscape to d0196;
    dependency from kRunnerDaemonLandscape to d0540;
    dependency from kRunnerDaemonLandscape to d0541;
    dependency from kRunnerDaemonLandscape to st188;
    dependency from kRunnerDaemonLandscape to runnerDaemonLandscapeSpikeStory;
    dependency from kRunnerDaemonLandscape to dcRunnerDaemonLandscapeIsRecorded;
}
