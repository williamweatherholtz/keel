// KNOWLEDGE RECORD (D0196) - the nine-critic, three-round adversarial panel on the tool-owns-the-task runner direction: not converged, seven forks handed to the human (D0542).
package KnowledgeRunnerDirectionPanel20260922 {
    private import EngineElement::*;
    private import EngineVerification::*;

    verification kRunnerDirectionPanel : Test {
        :>> id = "48890979-3869-45d8-ac3e-826f61f54cda";
        :>> title = "Panel run: nine critics, three rounds, four revisions of the runner direction - 2 accept / 7 object, then 0 / 9, then 3 / 6; convergence not reached, the residue is seven held forks, and slice one shrank to one verb in keel's own process";
        :>> createdAt = "2026-09-22"; :>> createdBy = "claudeFable5";
        :>> method = VerificationMethod::analyze;
        :>> procedureText = "REPLICATION (D0196). PROCESS: adversarialPanelReview (D0187, def pin 64f2dea), full nine-persona roster; SKILL: .claude/skills/adversarial-panel-review. TRIGGER: the human, 2026-09-22 (st190): 'critique this direction with a panel, make an artifact, and convince me this is the right direction.' - the direction being the tool-owns-the-task runner design under brainstorm since st181, shaped by the two landscape spikes (D0540, D0541). ROSTER: PESSIMIST-1 premise, PESSIMIST-2 operations, OPTIMIST-1 steelman, OPTIMIST-2 value, PEDANT-1 facts, PEDANT-2 consistency, PEDANT-3 mechanisms, REDUCER, SE kernel - nine read-only general-purpose subagents per round, dispatched in parallel with one shared brief carrying the artifact path, the repository root at f365cb7a for verification (never the artifact's own assertions), the honesty rule and the output contract (numbered findings with severity, evidence and the resolving change; a verdict with a minimal flip set); from round 2 each panelist also received a digest of every panelist's prior position and an invitation to rebut. ROUNDS: 1 against revision 1 (the eight-point protocol plus three forks) returned 2 ACCEPT / 7 OBJECT with 3 BLOCKER, 47 MAJOR, 33 MINOR - the blockers: the direction contradicts accepted D0209 'do NOT invert' with no supersession; a declared output could be a verdict record; three new controllers with no hazard analysis. Revision 2 resolved every flip set (sliced the design; eleven invariants; truth partition). Round 2 returned 0 / 9 with 0, 36, 35, converging on six defects revision 2 introduced: an unsatisfiable 'read set' clause; a slice-one CONSTRAINED class with no container and no credential boundary; a two-day claim on a dead run; a human-attention cap that was D0200's removed throttle renamed; D0182 and D0436 reversed silently; tracked hooks riding into the clone. Revision 3 resolved them (one BOUNDED class; subject/evidence split; F0 whole-clause; I-10 as a concurrency bound). Round 3 returned 3 / 6 with 0, 28, 27 - the three accepts conditional on edits; the objections named the residue: the claim clock is HEAD's commit date and cannot compute minutes; whose credential the slice-one agent holds cannot be minted or revoked on this provider; a replayed Decision would auto-accept under standing consent; a gate on a run ref leaves trunk ungated; the gate's cargo rungs execute harvested code as the invoker; steps whose governance outputs the write API cannot produce. Revision 4 landed every author-fixable item (host-stub liveness, merge-candidate gate, consent suspended at replay, hook-free spawn, Windows profile set, long paths) and named seven forks. The process's roughly-three-rounds limit was reached; the residue went to the human. Tally by scratchpad/panel_tally.py over the 27 reports, corrected once (issue672). FINDINGS: (1) the direction's core - assign, materialise, run, harvest declared outputs, replay governance through the write API, keel computes done on the merge candidate in a checkout the agent holds no handle to - survived three rounds; no panelist found a way for the child agent to make its step done by testimony; (2) three accepted Decisions stand in the direction's way and are now named and held: D0209 clause 5 (superseded whole, its keystone condition re-adopted as the run's code joining the process-change lock), D0182's single-writer clause (lifted for the run, kept for the gate), and D0094's auth clause if the pooled-key option is chosen; (3) the field's stored-flag defect was re-created twice by the author - a two-day claim, then a minute window on a commit-date clock - and caught both times by verification against source; (4) slice one has one step class and no daemon, lease server or proxy, and every operations finding fails the measured run the direction already owes; (5) the one control failure of the run itself: a read-only panelist wrote the tree and reversed it (issue671). DECISION: D0542 charter, accepted under standing consent; D0543-D0549 held - two SupersedeClause forks and five forks. KEY LEARNING: 'convince me' was answered honestly as a direction that survived forty-odd verified objections with seven choices only the human can make, not a verdict the author awards; and the panel's value was in the verification against source, not the personas. ARTIFACTS: docs/reviews/runner-direction-panel-2026-09-22.md (header, three briefs, four revisions, twenty-seven reports verbatim); the published brief (URL in the review); sprint 760; dcRunnerDirectionPanelIsRecorded; issue671, issue672.";
    }
    part kRunnerDirectionPanelR1 : TestResult {
        :>> id = "b9cafbf9-e0db-4ef0-86e8-b8df5702832f";
        :>> outcome = VerdictKind::pass;
        :>> judgedAgainst = "f365cb7a21cf0147a06d4c3c6b70e94e8007eacb";
        :>> judgedAt = "2026-09-22";
        :>> judgedBy = "claudeFable5";
        :>> notes = "Round 1: nine reports, 2 ACCEPT / 7 OBJECT, 3 BLOCKER / 47 MAJOR / 33 MINOR; every flip set resolved in revision 2.";
    }
    part kRunnerDirectionPanelR2 : TestResult {
        :>> id = "a25ce58d-011c-41ab-8e99-c8626e4ced8d";
        :>> outcome = VerdictKind::pass;
        :>> judgedAgainst = "f365cb7a21cf0147a06d4c3c6b70e94e8007eacb";
        :>> judgedAt = "2026-09-22";
        :>> judgedBy = "claudeFable5";
        :>> notes = "Round 2: nine reports, 0 ACCEPT / 9 OBJECT, 0 / 36 / 35 after the tally correction; six revision-2 defects resolved in revision 3.";
    }
    part kRunnerDirectionPanelR3 : TestResult {
        :>> id = "025c66a1-38dc-4ed4-aa3b-049407e4815e";
        :>> outcome = VerdictKind::pass;
        :>> judgedAgainst = "f365cb7a21cf0147a06d4c3c6b70e94e8007eacb";
        :>> judgedAt = "2026-09-22";
        :>> judgedBy = "claudeFable5";
        :>> notes = "Round 3: nine reports, 3 ACCEPT / 6 OBJECT, 0 / 28 / 27; convergence not reached; residue handed to the human as D0543-D0549; author-fixable items landed in revision 4.";
    }
    dependency from kRunnerDirectionPanel to adversarialPanelReview;
    dependency from kRunnerDirectionPanel to d0187;
    dependency from kRunnerDirectionPanel to d0196;
    dependency from kRunnerDirectionPanel to d0541;
    dependency from kRunnerDirectionPanel to d0542;
    dependency from kRunnerDirectionPanel to d0543;
    dependency from kRunnerDirectionPanel to d0546;
    dependency from kRunnerDirectionPanel to st190;
    dependency from kRunnerDirectionPanel to runnerDirectionPanelSpikeStory;
    dependency from kRunnerDirectionPanel to dcRunnerDirectionPanelIsRecorded;
    dependency from kRunnerDirectionPanel to issue671;
    dependency from kRunnerDirectionPanel to issue672;
}
