// LIVE ALLOCATION EDGES (D0194, sprint 416) — SystemRequirement -> CodeElement, the standing-code
// half of the sanctioned allocation mechanism (the other half is the charter chain: SR ->
// #CharteredBy work -> delivered code). AUTHORED JUDGMENTS, edge-per-line so a reviewer can dispute
// any single mapping; only mappings where the named unit genuinely CARRIES the requirement are
// recorded — an SR whose carrier is unregistered (CI workflows, claude_surface) has no edge here
// rather than a dishonest one, and the tier-satisfaction allocation leg reports that gap honestly.
// The June Component allocations remain in requirements.sysml as superseded history (D0194).
package LiveAllocations {
    private import EngineElement::*;

    // kernel invariants -> their carrying units
    allocate srK01ValidatedChannel to ceWriteApi;
    allocate srK02FailLoud to ceHookDispatch;
    allocate srK05ComputedCompletion to ceViewCore;
    allocate srK06HumanChannel to ceServeJudgment;
    allocate srK06HumanChannel to ceWriteApi;
    // D0192 OPTION A: the delegation clause lives in the same write surfaces plus the guard that checks quote substance.
    allocate srK06aDelegatedRecording to ceServeJudgment;
    allocate srK06aDelegatedRecording to ceWriteApi;
    allocate srK06aDelegatedRecording to ceGuards;
    allocate srK07RecordedWeakening to ceHookDispatch;
    allocate srK12VerdictTraceability to ceLauncher;
    allocate srK12VerdictTraceability to ceAuditHistory;
    allocate srK15TreeDerivable to ceAuditHistory;

    // distributed-collaboration invariants
    allocate srDcUniqueIdentityGuard to ceGuards;
    allocate srDcCollisionResistantIds to ceWriteApi;
    allocate srDcMergeOnlyIntegration to ceSyncIntegration;
    allocate srDcGateOnMergedTree to ceSyncIntegration;
    allocate srDcGateOnMergedTree to ceLandGate;
    allocate srDcActorIdentityBinding to ceActorProvenance;
    allocate srDcActorKindClassification to ceActorProvenance;
    allocate srDcWorkClaim to ceRecordClaim;
    allocate srDcWorkClaim to ceClaimHolderRule;
    allocate srDcStaleClaimExpiry to ceClaimHolderRule;
    allocate srDcSyncAwareOrient to ceOrient;

    // serve discipline
    allocate srServeApproveGateHuman to ceServeJudgment;
    allocate srServeApproveGateHuman to ceLauncher;
    allocate srServeSingleSpawnPoint to ceServeJudgment;

    // outward-publish boundary (srK16, D0195 clause 8)
    allocate srK16OutwardPublishGated to ceLandGate;
    allocate srK16OutwardPublishGated to ceSyncIntegration;

    // portability
    allocate srDcPortableGate to ceGitSpawn;

    // modular-members program (sprint 721, D0479): only the requirement a registered unit carries TODAY.
    // keel-model's orient.rs computes ready/blocked/done from the text and is the JSON+CLI lens's source;
    // the other seven wait for their carrier (keel-issues, the process member, the layering guard) and the
    // allocation leg of tier-satisfaction reports them as gaps until then.
    allocate srMemberStateIsComputedAndExposed to ceOrientMember;
}
